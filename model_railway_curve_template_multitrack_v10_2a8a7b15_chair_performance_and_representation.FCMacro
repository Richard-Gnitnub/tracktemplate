# -*- coding: utf-8 -*-
"""
Parametric model railway curve and straight-track template generator for FreeCAD.

Version 10.2A8A7B15 adds low-overhead whole-workflow profiling with reconciled stage percentages, recompute counts and durations, shape-object and generated sub-shape counts, cache reuse accounting and the largest three contributors. It reuses unchanged model-support and 2D layout results, caches compact physical plans and canonical S1/S1J 2D symbols, avoids copying unchanged timber records, and keeps detailed 3D construction outside routine layout work. The revised plan symbol follows the Templot 556b relationship between the rounded S1/S1J base, S1 jaws, wider S1J seat, rail-foot seat lines, two-rib outer jaw, one-rib inner jaw and a directional longitudinal key without changing the exact validation footprint. Version 10.2A8A7B14 adds automatic whole-workflow benchmarking across geometry, timbering, chair analysis, model support, 2D display, integration and optional export-chair preparation. It records wall time, process CPU time, current memory change and FreeCAD document-object change for every guided production stage, and adds a report/reset control without altering any accepted railway result. The routine 2D display now uses a low-detail Templot-guided S1/S1J plan symbol with a chamfered base, separate inner and outer jaw blocks and an optional key stroke, while retaining the exact source-dimensional footprint for validation. Version 10.2A8A7B13 adds a lightweight Templot-style 2D chair layout, an explicit bounded model-timber support stage and export-time-only 3D S1/S1J chair-body preparation. Required side extensions are derived from the actual rotated chair footprint, rounded upwards to 0.05 mm, kept separate from the prototype timber reference and rejected above the configured per-side limit. Version 10.2A8A7B12 adds transactional physical S1 and S1J chair-body generation and read-only fit validation against the fixed Templot5 556b C&L / EMGS / S4Soc Code 75 rev:A bullhead rail profile. It preserves unsupported and special chair positions as analytical records, leaves production readiness false while special chairs, keying and live fit remain outstanding, and changes no turnout, crossover, timber, host-integration or established exporter calculation. Version 10.2A8A7B11 removes redundant crossover metadata work by building final automatic-timbering and timber-analysis state once, serialising each persistent payload once, propagating the final state through one object pass, skipping property assignments whose values are already current, and updating the crossover catalogue once. It changes no railway geometry, sampling, tolerance, topology rule, timber decision, chair assignment or production record. Version 10.2A8A7B10 adds read-only live stage profiling around crossover timber analysis, shared long-timber solving, controlled conflict resolution, chair-position analysis, FreeCAD Part shape construction, diagnostic display updates and document recomputes. It changes no railway geometry, sampling, tolerance, acceptance rule or production record. Version 10.2A8A7B9 adds exact hierarchical path indexes, incremental analysis reuse and reduced FreeCAD display/recompute churn without changing any accepted railway result. Version 10.2A8A7B8 reduces chair-analysis and crossover-timbering run time without changing railway geometry, topology, timber placement rules, chair assignment rules or production exporters. It reuses identical in-memory timber analyses, removes duplicate final validation passes, batches timber-conflict diagnostics, builds only requested chair diagnostic layers, and uses a pre-indexed exact rail-projection path for chair-position discovery. Version 10.2A8A7B7 adds a shared guided turnout-and-crossover workflow panel which presents geometry, timbering, chair-position analysis, integration and finish actions as numbered human-readable steps. It calls the existing validated operations directly, hides specialist and maintenance controls by default, offers a safe Run next step action, and does not alter any turnout geometry, crossover solver, topology gate, timber calculation, chair calculation, host-integration calculation or exporter. Version 10.2A8A7B6 repairs the crossover topology regression by preserving each diverging branch end as a directed railway endpoint, using the outward Host A branch tangent and the reverse of the outward Host B branch tangent for connector traversal, rejecting tangent-continuous routes which leave towards a switch toe or intrude through either turnout, and extending operator diagnostics without altering turnout rail construction, timber-resolution limits, chair analysis, host integration or production exporters. Version 10.2A8A7B5 repaired curved-host crossover connector orientation by treating each turnout branch-end tangent as a bidirectional geometric line, selecting the direction which faces through the local connector chord, preserving host travel direction separately, prioritising the branch-end search region and expanding solver diagnostics. Version 10.2A8A7B4 adds a bounded arc-straight-arc local connector family, correct branch-end Host B toe seeding and faster staged solver tracing after host regeneration. Version 10.2A8A7B3 adds a tangent-exact cubic connector fallback and detailed read-only solver tracing when the exact biarc family cannot produce a local route after host regeneration. Version 10.2A8A7B2 repairs the remaining curved-host crossover rejection by replacing the over-strict endpoint-chord test with sampled local-route validation and an unequal-distance biarc family search. It retains loop rejection, exact end tangency, minimum-radius validation and transactional failure before any document geometry is created. Version 10.2A8A7B1 repairs crossover connector selection after host-curve regeneration by rejecting non-local looping biarcs and adaptively refining the neighbouring-host toe search before any document geometry is created. Version 10.2A8A7B assigns ordinary REA S1/S1J chairs and C-switch P, PLR block-slide and PLR block-heel supports, preserves key direction as an explicit configurable requirement where no policy is stored, and records read-only model-scale timber-support recommendations from confirmed chair footprints without generating chair solids or altering production geometry. Version 10.2A8A7A1 repairs live chair-analysis display height, binds inherited protected support to the applicable route and rail role, physically qualifies analytical footprint findings, and groups repeated advisory output without generating chair solids or changing production geometry. Version 10.2A8A7A adds a read-only stable chair-position and assignment framework, lightweight diagnostics, cache signatures and chair-aware production preflight without generating chair solids or altering production geometry. Version 10.2A8A6C2 repairs the selected-production export workflow, adds scrolling to both tabs of the unified turnout and crossover manager, and safely projects turnout engraving records to planar XY export copies without changing their FreeCAD display objects. Version 10.2A8A6C1 repairs managed-crossover production export by projecting crossover rail and construction-mark display geometry to safe planar XY engraving records and by validating only records which the selected export formats will actually write. Version 10.2A8A6C adds transactional crossover editing and reversible host-template integration of the final automatically resolved timber arrangement. Version 10.2A8A6B4A1 refines crossover timbering terminology and adds complete operator tooltips without changing resolver geometry. Version 10.2A8A6B4 adds a one-click hybrid automatic crossover timber resolver. It rebuilds the complete A8A6B2A2 shared-timber envelope in memory, applies the A8A6B3 interlacing and minimum controlled-shove solver only where long timbers cannot safely resolve the arrangement, validates the final effective timbering as one deterministic result, and retains unsafe positions explicitly rather than forcing geometry. Shared envelope timbers are assessed against every supported road normal instead of being reported as ordinary single-road sleepers. The B4 result remains a preview until A8A6C integrates it reversibly with the host templates; chair generation and fit validation remain staged for A8A7. Version 10.2A8A6A6 completes the reversible turnout/crossover lifecycle. A managed crossover can be converted transactionally back into a standalone turnout. Crossovers created from an existing turnout automatically restore that original Host A turnout and stable identity; independently created crossovers allow either constituent turnout to be retained. New turnout-to-crossover conversions also store the complete source-turnout configuration snapshot so future reversal restores all optional timber and datum outputs exactly.

Version 10.2A8A6A adds a managed natural REA C10 crossover geometry module and retains the A8A5 ability to integrate a validated REA C10 turnout into derived host-template production geometry and adds independent reference-copy extraction without modifying the original generated railway objects. It preserves the complete A8A4 source-driven turnout timbering and all established turnout rail geometry. It uses the published C-switch individual timber centres, evenly fits closure timbers within the available interlead, preserves the fixed REA crossing-chair spacings around the wing and vee rails, and provides correctly widening timber outlines, optional centre lines, timber identities, optional length labels and separate construction datums. The timber rectangles inherit the selected host alignment through the same proven station-normal mapping as the rail geometry, so their position and orientation remain coherent through straight, constant-radius and Euler-transition regions. Existing Version 10.2A8A1-A8A3 turnouts can be upgraded transactionally through Edit selected turnout and Apply turnout changes without altering their placement. The replacement geometry is fully built and validated in memory before one FreeCAD transaction updates the existing turnout identity and production records. It retains the complete A8A3 switch, closure, common-crossing, vee, wing-rail and check-rail geometry and the proven Version 10.2A7 configuration and named-preset system. Presets store reusable configuration snapshots only, can be transported inside configuration JSON, and are written to the user preset library only after an explicit save. It retains the complete
Version 10.2A2 production schedule and material report, together with the proven Version 10.0B3
curve, easement, straight, platform, formation-board, sectioning, assembly and production-export
geometry. This stage retains the established read-only production preflight system, adds a focused integrated-crossover readiness check, and retains repaired selected-item
production export, including persistent reconstruction of sloped platform-edge display wires as safe XY engraving records and deterministic filenames for the distinct track-centreline and platform-edge engraving outputs, and recognises intentional one-dimensional centreline and platform-edge engraving as valid linear output rather than noisy degenerate-span diagnostics, for FreeCAD object selections, highlighted production records, individual sections, complete tracks, platforms,
formation boards, routes and whole template sets. It filters the persistent production-record
catalogue, presents a complete file and overwrite preview, runs scope-aware preflight checks, then
writes every requested DXF, SVG, STL, STEP and CSV manifest into a hidden staging directory before
committing the complete file set. Any exporter, manifest or final-file failure rolls back the
operation and restores overwritten files. Legacy sets remain readable through the cautious Version
10.2A1 metadata scan. No railway geometry, numbering, sectioning, assembly, formation-board or
established exporter calculation is changed.

Connected straights continue to inherit the generated curve endpoints, headings, track
centres, template widths and output selections rather than recalculating or altering any
curve geometry. Independent straights retain their own datum, rotation, travel direction,
parallel side, spacing, width and thickness. Straight platforms remain deliberately
outside this revision so the established curved-platform manager is not destabilised.
A pre-transaction validation still requires every connected route to contain exactly one
straight alignment for every generated curve track.
The corrected Version 9.13 Platform Manager initialisation and every existing curve
output pathway remain intact. Accepted dialogue values remain remembered per document,
with a last-used fallback for new or renamed documents.

The formation board is deliberately simple and robust: one continuous swept outline
is calculated from the furthest occupied transverse limits of the selected track-template
strips and platforms along the route. Abrupt platform-end changes are broadened into
controlled longitudinal transitions, the ends are closed perpendicular to the route,
and the resulting single face is extruded downwards by the entered sheet thickness.
The base board uses no face-to-face Boolean fusions, holes or joints unless those
separate optional post-processing features are explicitly selected.

Each added track can use standard independent Euler geometry or the dedicated
platform-widening geometry. Every track has:

  * its own Euler entry and exit easements
  * its own concentric constant-radius section
  * independent entry, curve and exit centre spacing
  * automatic easement solving to match the requested straight spacings, or
    manual entry and exit easement lengths
  * no reverse curvature: curvature remains zero or follows the selected turn
    direction throughout the complete alignment
  * optional platform widening transitions with exact straight and curve spacing
  * an individual template width and output controls

The main curve defines the common circular centre and total turn angle. Added
tracks use the selected curve spacing to calculate their constant radius:

  Outside radius = main radius + curve spacing
  Inside radius  = main radius - curve spacing

Positive turn angles curve left; negative turn angles curve right. Run the macro
again to edit the stored settings.
"""

import bisect
import csv
import copy
import datetime
import json
import hashlib
import math
import os
import re
import shutil
import subprocess
import sys
import tempfile
import time
import uuid
import xml.etree.ElementTree as ET

import FreeCAD as App
import Part

try:
    import FreeCADGui as Gui
except ImportError:
    Gui = None

try:
    from PySide import QtCore, QtGui, QtWidgets
except ImportError:
    from PySide import QtCore, QtGui
    QtWidgets = QtGui


GROUP_NAME = "ModelRailwayCurve"
TEMPLATE_NAME = "RailwayCurveTemplate"
CENTRELINE_PREFIX = "RailwayTrackCentreline_"
PLATFORM_EDGE_PREFIX = "RailwayPlatformEdge_"
PLATFORM_BODY_NAME = "RailwayPlatform"
SETTINGS_NAME = "RailwayCurveSettings"
FORMATION_OUTLINE_NAME = "RailwayFormationBoardPerimeter"
FORMATION_BODY_NAME = "RailwayFormationBoard"
FORMATION_SECTION_PREFIX = "RailwayFormationSection_"
TEMPLATE_SECTION_PREFIX = "RailwayTrackTemplateSection_"
PLATFORM_SECTION_PREFIX = "RailwayPlatformSection_"
REGISTRATION_PREFIX = "RailwayRegistrationFeature_"
ALIGNMENT_HOLE_PREFIX = "RailwayAlignmentHoles_"
TRACK_ENGRAVING_NAME = "RailwayTrackCentrelineEngraving"
PLATFORM_ENGRAVING_NAME = "RailwayPlatformEdgeEngraving"
SECTION_ENGRAVING_PREFIX = "RailwaySectionNumberEngraving_"
TRACK_TEMPLATE_JOINT_PREFIX = "RailwayTrackTemplateJoint_"
TRACK_TEMPLATE_HOLE_PREFIX = "RailwayTrackTemplateFixingHoles_"
FORMATION_MATCHING_HOLES_NAME = "RailwayFormationMatchingFixingHoles"
PLATFORM_PLAN_OUTLINE_EXPORT_NAME = "RailwayPlatformPlanOutlineExport"
PRODUCTION_EXPORT_SETTINGS_PROPERTY = "ProductionExportConfigurationJSON"
PRODUCTION_RECORD_INDEX_PROPERTY = "ProductionRecordIndexJSON"
PRODUCTION_RECORD_ID_PROPERTY = "ProductionRecordID"
PRODUCTION_RECORD_IDS_PROPERTY = "ProductionRecordIDsJSON"
PRODUCTION_RECORD_SCHEMA_VERSION = 2
ASSEMBLY_LABEL_SETTINGS_PROPERTY = "AssemblyLabelConfigurationJSON"
ASSEMBLY_LABEL_SCHEMA_VERSION = 1
ASSEMBLY_LABEL_ROLE = "AssemblyLabel"
ASSEMBLY_LABEL_SUBTYPE = "AssemblyLabel"
ASSEMBLY_LABEL_SELECTION_KEY = "assembly_labels"
ASSEMBLY_LABEL_FORMAT_AUTOMATIC = "Automatic compact"
ASSEMBLY_LABEL_FORMAT_CUSTOM = "Custom token format"
ASSEMBLY_LABEL_PLACE_AUTO = "Automatic - underside preferred"
ASSEMBLY_LABEL_PLACE_UNDERSIDE_ENTRY = "Underside near first end"
ASSEMBLY_LABEL_PLACE_UNDERSIDE_EXIT = "Underside near second end"
ASSEMBLY_LABEL_PLACE_TOP_ENTRY = "Top near first end"
ASSEMBLY_LABEL_PLACE_TOP_EXIT = "Top near second end"
ASSEMBLY_LABEL_PLACEMENTS = [
    ASSEMBLY_LABEL_PLACE_AUTO,
    ASSEMBLY_LABEL_PLACE_UNDERSIDE_ENTRY,
    ASSEMBLY_LABEL_PLACE_UNDERSIDE_EXIT,
    ASSEMBLY_LABEL_PLACE_TOP_ENTRY,
    ASSEMBLY_LABEL_PLACE_TOP_EXIT,
]
ASSEMBLY_LABEL_DERIVED_PROPERTY = "AssemblyLabelDerived"
ASSEMBLY_LABEL_TARGET_PROPERTY = "AssemblyLabelTargetKey"
PRODUCTION_SCHEDULE_SCHEMA_VERSION = 1
PRODUCTION_SCHEDULE_NAME = "RailwayProductionSchedule"
PRODUCTION_SCHEDULE_ROLE = "ProductionSchedule"
MATERIAL_REPORT_SETTINGS_PROPERTY = "MaterialReportConfigurationJSON"
MATERIAL_REPORT_PARAMETER_KEY = "LastMaterialReportConfigurationJSON"
MATERIAL_REPORT_SCHEMA_VERSION = 1
MATERIAL_REPORT_NAME = "RailwayMaterialLengthReport"
MATERIAL_REPORT_ROLE = "MaterialLengthReport"
PRODUCTION_PREFLIGHT_SCHEMA_VERSION = 1
PRODUCTION_PREFLIGHT_SEVERITY_INFORMATION = "Information"
PRODUCTION_PREFLIGHT_SEVERITY_WARNING = "Warning"
PRODUCTION_PREFLIGHT_SEVERITY_ERROR = "Error"
SELECTED_EXPORT_SCOPE_OBJECTS = "Selected FreeCAD objects"
SELECTED_EXPORT_SCOPE_SECTION = "One section"
SELECTED_EXPORT_SCOPE_TRACK = "One complete track"
SELECTED_EXPORT_SCOPE_PLATFORM = "One platform"
SELECTED_EXPORT_SCOPE_FORMATION = "One formation board"
SELECTED_EXPORT_SCOPE_ROUTE = "One route"
SELECTED_EXPORT_SCOPE_TEMPLATE_SET = "One template set"
SELECTED_EXPORT_SCOPES = [
    SELECTED_EXPORT_SCOPE_OBJECTS,
    SELECTED_EXPORT_SCOPE_SECTION,
    SELECTED_EXPORT_SCOPE_TRACK,
    SELECTED_EXPORT_SCOPE_PLATFORM,
    SELECTED_EXPORT_SCOPE_FORMATION,
    SELECTED_EXPORT_SCOPE_ROUTE,
    SELECTED_EXPORT_SCOPE_TEMPLATE_SET,
]
SELECTED_EXPORT_RECORD_FIELDS = [
    "Source object", "Route", "Track", "Platform", "Section",
    "Travel order", "Object type", "Export subtype", "Category",
    "Compatible formats", "Production-record ID",
]
SELECTED_EXPORT_PLAN_FIELDS = [
    "Filename", "Format", "Output type", "Records", "File action", "Full path",
]
PRODUCTION_PREFLIGHT_FIELDS = [
    "Severity",
    "Issue code",
    "Message",
    "Blocks export",
    "Template-set ID",
    "Route name",
    "Route ID",
    "Track number",
    "Track name",
    "Platform number",
    "Platform name",
    "Section number",
    "Travel-order number",
    "Export format",
    "Proposed path",
    "Source object",
    "Production-record ID",
]
MEASUREMENT_EXACT = "Exact"
MEASUREMENT_BOUNDING_BOX = "Bounding-box estimate"
MEASUREMENT_SHEET_ESTIMATE = "Approximate sheet-use estimate"
MEASUREMENT_CONFIGURED = "Configured input"
EXPORT_CATEGORY_CUTTING = "CuttingProfile"
EXPORT_CATEGORY_HOLES = "InternalHoleProfile"
EXPORT_CATEGORY_JOINTS = "JointProfile"
EXPORT_CATEGORY_ENGRAVING = "Engraving"
EXPORT_CATEGORY_SOLID = "Solid"
EXPORT_FORMAT_DXF = "dxf"
EXPORT_FORMAT_SVG = "svg"
EXPORT_FORMAT_STL = "stl"
EXPORT_FORMAT_STEP = "step"
EXPORT_FORMAT_LABELS = {
    EXPORT_FORMAT_DXF: "DXF",
    EXPORT_FORMAT_SVG: "SVG",
    EXPORT_FORMAT_STL: "STL",
    EXPORT_FORMAT_STEP: "STEP",
}
EXPORT_CATEGORY_COMBINED_NAMES = {
    EXPORT_CATEGORY_CUTTING: "Combined_Cutting_Profiles",
    EXPORT_CATEGORY_HOLES: "Combined_Internal_Holes",
    EXPORT_CATEGORY_JOINTS: "Combined_Joint_Profiles",
    EXPORT_CATEGORY_ENGRAVING: "Combined_Engraving",
    EXPORT_CATEGORY_SOLID: "Combined_Solid_Assembly",
}
EXPORT_SUBTYPE_FILENAMES = {
    "TrackTemplateCompound": "Track_Template_Compound",
    "TrackTemplateTurnout": "Turnout_Template",
    "TrackTemplateTurnoutIntegrated": "Integrated_Turnout_Template",
    "TrackTemplateTurnoutIntegratedSection": "Integrated_Turnout_Section",
    "TrackTemplateCrossoverIntegrated": "Integrated_Crossover_Template",
    "CrossoverResolvedTimberGeometry": "Resolved_Crossover_Timbering",
    "TurnoutRailGeometry": "Turnout_Rail_Geometry",
    "TurnoutTimberGeometry": "Turnout_Timber_Outlines",
    "TurnoutTimberCentres": "Turnout_Timber_Centres",
    "TurnoutTimberLabels": "Turnout_Timber_Labels",
    "TurnoutConstructionMarks": "Turnout_Construction_Marks",
    "TrackTemplateSection": "Template",
    "TrackTemplateFixingHole": "Template_Fixing_Holes",
    "TrackTemplateJoint": "Track_Template_Joint",
    "TrackCentreline": "Centreline",
    "PlatformBody": "Platform",
    "PlatformSection": "Platform",
    "PlatformSectionOutline": "Platform_Section_Outline",
    "PlatformPlanOutline": "Platform_Plan_Outline",
    "PlatformEdge": "Platform_Edges",
    "FormationPerimeter": "Formation_Board_Perimeter",
    "FormationBody": "Formation_Board",
    "FormationSectionPerimeter": "Formation_Board_Perimeter",
    "FormationSectionBody": "Formation_Board",
    "RegistrationHole": "Registration_Holes",
    "FormationMatchingFixingHole": "Formation_Board_Matching_Fixing_Holes",
    "RegistrationJoint": "Registration_Joint",
    "SectionNumberEngraving": "Section_Number_Engraving",
    "OtherEngraving": "Engraving_Geometry",
    "AssemblyLabel": "Assembly_Label",
}
EXPORT_MANIFEST_FIELDS = [
    "Macro version",
    "Export date and time",
    "Template-set identifier",
    "Generated object name",
    "Generated object role",
    "Track number",
    "Platform number",
    "Platform name",
    "Section number",
    "Travel-order number",
    "Export format",
    "Export filename",
    "Full export path",
    "Section length",
    "Template thickness",
    "Platform thickness",
    "Formation-board thickness",
    "Joint type",
    "Fixing-hole diameter",
    "Export status",
    "Error message",
]


PRODUCTION_SCHEDULE_FIELDS = [
    "Template-set ID",
    "Route name",
    "Route ID",
    "Track number",
    "Track name",
    "Object type",
    "Generated role",
    "Platform number",
    "Platform name",
    "Section number",
    "Travel-order number",
    "Overall length (mm)",
    "Overall width (mm)",
    "Overall height or thickness (mm)",
    "Measurement classification",
    "Export subtype",
    "Supported export formats",
    "Configured export formats",
    "Expected export filenames",
    "Export status",
    "Diagnostic status",
    "Diagnostic details",
    "Source object",
    "Production-record ID",
]

MATERIAL_REPORT_FIELDS = [
    "Template-set ID",
    "Report section",
    "Metric",
    "Route name",
    "Route ID",
    "Track number",
    "Track name",
    "Platform number",
    "Platform name",
    "Value",
    "Unit",
    "Measurement classification",
    "Calculation method",
    "Part count",
    "Source-record count",
    "Source production-record IDs",
    "Notes",
]
GENERATOR_ID = "ModelRailwayCurveTemplate.IndependentEasements"
OUTPUT_REPLACE = "Replace all existing generated templates"
OUTPUT_CREATE_NEW = "Create a new template set"
LEGACY_CENTRELINE_NAMES = (
    "RailwayCurveCentreline",
    "RailwayParallelCurveCentreline",
)

DEFAULT_TRANSITION_LENGTH = 600.0
DEFAULT_RADIUS = 600.0
DEFAULT_TURN_ANGLE = 90.0
DEFAULT_MAIN_TEMPLATE_WIDTH = 32.0
DEFAULT_PARALLEL_TRACKS = [
    {
        "name": "Track 2",
        "side": "Outside",
        "alignment_mode": "Euler - match spacings",
        "start_spacing": 50.0,
        "curve_spacing": 55.0,
        "finish_spacing": 50.0,
        "entry_transition_length": 600.0,
        "exit_transition_length": 600.0,
        "width": 32.0,
        "create_template": True,
        "show_centreline": True,
    }
]

TEMPLATE_THICKNESS = 1.0
SAMPLE_SPACING = 3.0
CENTRELINE_LIFT = 0.02
MAX_PARALLEL_TRACKS = 20
MACRO_VERSION_NUMBER = "10.2A8A7B15"
MACRO_VERSION = "{} CHAIR PERFORMANCE AND REPRESENTATION".format(MACRO_VERSION_NUMBER)
CROSSOVER_OPERATOR_VERSION_NUMBER = "10.2"


CROSSOVER_TIMBERING_UI_TEXT = {
    "group_title": "Crossover timbering: analysis and automatic resolution",
    "apply_automatic": "Resolve crossover timbering automatically",
    "remove_automatic": "Remove automatic timbering result",
    "automatic_details": "Show automatic resolution details",
    "show_automatic": "Show final resolved timbering",
    "build_shared": "Build shared long-timber envelope",
    "remove_shared": "Remove shared long-timber envelope",
    "shared_details": "Show shared-envelope details",
    "shared_settings": "Shared-envelope settings…",
    "show_shared": "Show shared long-timber result",
    "resolve_remaining": "Resolve remaining timber conflicts",
    "remove_adjustment": "Remove interlacing and timber movement",
    "adjustment_details": "Show interlacing and movement details",
    "adjustment_settings": "Interlacing and movement settings…",
    "show_adjusted": "Show adjusted timbering",
    "integration_group_title": "Crossover editing and host integration",
    "edit_crossover": "Edit selected crossover",
    "cancel_edit": "Cancel crossover editing",
    "integrate_hosts": "Integrate with host templates",
    "remove_integration": "Remove host integration",
    "integration_details": "Show host-integration details",
}

CROSSOVER_TIMBERING_TOOLTIPS = {
    "status": "Shows the current analysis, shared-envelope, interlacing and automatic-resolution status for the selected crossover.",
    "analyse": "Checks the current effective timber arrangement for intersections, inadequate spacing, skew and unsupported protected positions. This does not alter timber, rail or host-track geometry.",
    "show_conflicts": "Shows or hides lightweight markers at timber conflicts found by the latest current analysis. This changes display only.",
    "show_supports": "Shows or hides protected switch, crossing, check-rail, wing-rail and rail-joint support markers. This changes display only.",
    "analysis_settings": "Adjusts model-scale analysis tolerances. It does not move or resize timbers; rerun the analysis after changing a value.",
    "analysis_details": "Opens the complete readable report for the latest current timber analysis.",
    "copy_analysis": "Copies the latest readable timber-analysis report to the clipboard.",
    "clear_analysis": "Removes temporary conflict and protected-support markers. Cached analysis results and production geometry remain unchanged.",
    "apply_automatic": "Builds the shared long-timber envelope, then applies controlled interlacing or the smallest permitted longitudinal movement where required. The result remains preview geometry until host-track integration.",
    "remove_automatic": "Removes the final automatic timbering preview and restores the preceding shared, adjusted or inherited display where available. Rails and host tracks are unchanged.",
    "automatic_details": "Shows how the automatic resolver combined long timbers, accepted interlacing and controlled timber movement, including any unresolved positions.",
    "show_automatic": "Shows or hides the final automatically resolved timbering preview. This changes display only.",
    "build_shared": "Extends compatible inherited timbers and creates connector timbers through the crossover until both routes can return safely to their configured plain-track sleeper width. It does not shove or interlace timbers.",
    "remove_shared": "Removes the shared long-timber preview and restores the inherited turnout timber references. Rails and host tracks are unchanged.",
    "shared_details": "Shows the shared-envelope limits, long-timber counts, plain-track return checks and rejected candidates.",
    "shared_settings": "Adjusts long-timber eligibility, clearance, envelope allowance and plain-track return settings.",
    "show_shared": "Shows or hides the shared long-timber result. This changes display only.",
    "resolve_remaining": "Attempts safe interlacing and the smallest permitted longitudinal timber movement at positions not resolved by shared long timbers. Shared long timbers remain fixed.",
    "remove_adjustment": "Removes controlled interlacing and timber movements, restoring the shared long-timber envelope. Rails and host tracks are unchanged.",
    "adjustment_details": "Shows accepted interlacing, timber movements, protected-support checks and any unresolved positions.",
    "adjustment_settings": "Adjusts permitted timber movement, search increment, spacing and protected-support limits.",
    "show_adjusted": "Shows or hides the interlaced and longitudinally adjusted timbering preview. This changes display only.",
    "edit_crossover": "Loads the selected crossover into the geometry controls while preserving its stable identity. If host integration is active, the original host production records are restored inside the same edit transaction. Applying changes invalidates earlier timber-resolution results.",
    "cancel_edit": "Leaves the selected crossover unchanged and returns the geometry controls to create mode.",
    "integrate_hosts": "Replaces the affected host-template production records with one reversible crossover assembly using the current final resolved timbering. Chair validation remains outstanding.",
    "remove_integration": "Restores the original host-template production records and the separate crossover preview without changing the crossover geometry. Removing or converting the whole crossover also performs this restoration automatically.",
    "integration_details": "Shows the affected host tracks, section checks, production-record replacements and current integration signature.",
}


# Stage 8A turnout-manager constants. The prototype switch data is the REA
# C-size semi-curved flexible switch data published in Templot/OpenTemplot:
# 110 inch planing at 1:40, 329 inch lead to heel and 11,520 inch switch
# radius. Geometry is calculated in model millimetres and then mapped through
# the selected generated host centreline by station and local normal.
TURNOUT_SCHEMA_VERSION = 1
TURNOUT_CATALOGUE_PROPERTY = "TurnoutConfigurationsJSON"
TURNOUT_CONFIGURATION_PROPERTY = "TurnoutConfigurationJSON"
TURNOUT_ID_PROPERTY = "TurnoutID"
TURNOUT_HOST_PROPERTY = "TurnoutHostObject"
TURNOUT_GROUP_ROLE = "TurnoutGroup"
TURNOUT_SETTINGS_ROLE = "TurnoutSettings"
TURNOUT_TEMPLATE_ROLE = "TurnoutTemplate"
TURNOUT_OUTLINE_ROLE = "TurnoutPlanOutline"
TURNOUT_RAIL_ROLE = "TurnoutRailGeometry"
TURNOUT_TIMBER_ROLE = "TurnoutTimberGeometry"
TURNOUT_TIMBER_CENTRE_ROLE = "TurnoutTimberCentres"
TURNOUT_TIMBER_LABEL_ROLE = "TurnoutTimberLabels"
TURNOUT_DATUM_ROLE = "TurnoutConstructionMarks"
TURNOUT_INTEGRATION_GROUP_ROLE = "TurnoutHostIntegrationGroup"
TURNOUT_INTEGRATION_SETTINGS_ROLE = "TurnoutHostIntegrationSettings"
TURNOUT_INTEGRATED_DISPLAY_ROLE = "TurnoutIntegratedHostDisplay"
TURNOUT_INTEGRATED_TEMPLATE_ROLE = "TurnoutIntegratedHostTemplate"
TURNOUT_INTEGRATED_OUTLINE_ROLE = "TurnoutIntegratedHostOutline"
TURNOUT_REFERENCE_GROUP_ROLE = "TurnoutReferenceCopyGroup"
TURNOUT_REFERENCE_OBJECT_ROLE = "TurnoutReferenceCopy"
TURNOUT_INTEGRATION_PROPERTY = "TurnoutHostIntegrationJSON"
TURNOUT_REFERENCE_SOURCE_PROPERTY = "ReferenceSourceTurnoutID"
TURNOUT_REFERENCE_ID_PROPERTY = "TurnoutReferenceCopyID"
TURNOUT_INTEGRATION_SCHEMA_VERSION = 1
TURNOUT_INTEGRATION_CLEARANCE = 0.15
TURNOUT_INTEGRATION_Z_CLEARANCE = 0.20
TURNOUT_INTEGRATION_BRANCH_CLIP_WIDTH = 500.0
TURNOUT_SUBTYPE_TEMPLATE = "TrackTemplateTurnout"
TURNOUT_SUBTYPE_RAIL = "TurnoutRailGeometry"
TURNOUT_SUBTYPE_TIMBER = "TurnoutTimberGeometry"
TURNOUT_SUBTYPE_TIMBER_CENTRE = "TurnoutTimberCentres"
TURNOUT_SUBTYPE_TIMBER_LABEL = "TurnoutTimberLabels"
TURNOUT_SUBTYPE_DATUM = "TurnoutConstructionMarks"
TURNOUT_SELECTION_TEMPLATE_2D = "track_template_compound_2d"
TURNOUT_SELECTION_TEMPLATE_3D = "track_template_compound_3d"
TURNOUT_SELECTION_ENGRAVING = "other_engraving"
TURNOUT_SIZE_C10 = "REA C10 natural"
TURNOUT_HAND_LEFT = "Left-hand"
TURNOUT_HAND_RIGHT = "Right-hand"
TURNOUT_ORIENTATION_FACING = "Facing in host travel direction"
TURNOUT_ORIENTATION_TRAILING = "Trailing against host travel direction"
TURNOUT_SOURCE_NOTE = (
    "REA C switch and regular 1:10 common-crossing geometry cross-checked "
    "against the Templot5 math_unit.pas calculation model"
)
TURNOUT_RAIL_GEOMETRY_REVISION = 2
TURNOUT_TIMBER_GEOMETRY_REVISION = 2
TURNOUT_TIMBER_SOURCE_NOTE = (
    "REA C-switch and regular-crossing timber positions cross-checked against "
    "Templot5 switch_select.pas and math_unit.pas"
)
TURNOUT_TIMBER_WIDTH_INCHES = 12.0
TURNOUT_SLEEPER_WIDTH_INCHES = 10.0
TURNOUT_TIMBER_LENGTH_INCREMENT_INCHES = 6.0
TURNOUT_TIMBER_LABEL_HEIGHT = 1.40
TURNOUT_TIMBER_LABEL_CLEARANCE = 0.40
TURNOUT_RAIL_SAMPLE_SPACING = 1.0
TURNOUT_RAIL_GEOMETRY_CONTENT = (
    "stock rails",
    "switch and closure rails",
    "normal-radius knuckle bends",
    "main-side and turnout-side wing rails",
    "point and splice rails forming the crossing vee",
    "main-side and turnout-side check rails",
)
TURNOUT_DEFAULT_GAUGE = 16.5
TURNOUT_DEFAULT_FLANGEWAY = 1.0
TURNOUT_DEFAULT_SCALE = 76.2
TURNOUT_SAMPLE_SPACING = 2.0
TURNOUT_OVERLAP_TOLERANCE = 0.10
TURNOUT_MIN_GAUGE = 10.0
TURNOUT_MAX_GAUGE = 25.0
TURNOUT_MIN_FLANGEWAY = 0.25
TURNOUT_MAX_FLANGEWAY = 3.0
FORMATION_OUTLINE_ONLY = "2D cutting outline"
FORMATION_SOLID_ONLY = "3D solid board"
FORMATION_BOTH = "2D outline and 3D solid"
REGISTRATION_PLAIN = "Plain joints"
REGISTRATION_HOLES = "Alignment holes"
REGISTRATION_PINS = "Pins and sockets"
REGISTRATION_TONGUE = "Tongue-and-groove joints"
TEMPLATE_JOINT_PLAIN = "Plain joints"
TEMPLATE_JOINT_PINS = "Pins and sockets"
TEMPLATE_JOINT_TONGUE = "Tongue-and-socket joints"
TEMPLATE_HOLE_PROFILE_LIFT = TEMPLATE_THICKNESS + 0.06
FORMATION_OUTLINE_LIFT = 0.01
ENGRAVING_LIFT = 0.04
SECTION_MASK_MARGIN = 100.0
MAX_SECTION_COUNT = 999
MODE_MATCH_SPACINGS = "Euler - match spacings"
MODE_USE_LENGTHS = "Euler - use lengths"
MODE_PLATFORM = "Platform widening"
PLATFORM_BETWEEN = "Between two tracks"
PLATFORM_OUTSIDE = "Outside one track"
PLATFORM_LEFT = "Left of travel"
PLATFORM_RIGHT = "Right of travel"
PLATFORM_END_SQUARE = "Square"
PLATFORM_END_TAPERED = "Tapered"
PLATFORM_END_TAPERED_LABEL = "Tapered ramp to trackbed"
PLATFORM_CONSTANT = "Constant curve only"
PLATFORM_ENTRY = "Entry transition and constant curve"
PLATFORM_EXIT = "Constant curve and exit transition"
PLATFORM_CORE = "Both transitions and constant curve"
PLATFORM_EDGES_ONLY = "Edges only (2D)"
PLATFORM_FACE = "2D platform face"
PLATFORM_SOLID = "3D platform solid"
PLATFORM_2D_LIFT = TEMPLATE_THICKNESS + 0.05
PLATFORM_MIN_NOSE_WIDTH = 0.10
PLATFORM_MIN_RAMP_HEIGHT = 0.01
PLATFORM_LOFT_PROFILE_SPACING = 9.0
MAX_PLATFORM_NAME_LENGTH = 80
MAX_PLATFORMS = 20
PLATFORM_DEFAULTS_SCHEMA_VERSION = 3
OUTSIDE_PLATFORM_PRESET_VERSION = 2
PLATFORM_CONFIGS_PROPERTY = "PlatformConfigurationsJSON"
STRAIGHT_CONFIGS_PROPERTY = "StraightTrackConfigurationsJSON"
STRAIGHT_TRACK_GROUP_NAME = "Straight_Tracks"
STRAIGHT_TEMPLATE_GROUP_NAME = "Straight_Track_Templates"
STRAIGHT_TEMPLATE_PREFIX = "RailwayStraightTrackTemplate_"
STRAIGHT_CENTRELINE_PREFIX = "RailwayStraightTrackCentreline_"
STRAIGHT_FORMATION_GROUP_NAME = "Straight_Formation"
STRAIGHT_TEMPLATE_SECTION_PREFIX = "RailwayStraightTrackTemplateSection_"
STRAIGHT_TEMPLATE_JOINT_PREFIX = "RailwayStraightTrackTemplateJoint_"
STRAIGHT_TEMPLATE_HOLE_PREFIX = "RailwayStraightTrackTemplateFixingHoles_"
STRAIGHT_FORMATION_OUTLINE_PREFIX = "RailwayStraightFormationBoardPerimeter_"
STRAIGHT_FORMATION_BODY_PREFIX = "RailwayStraightFormationBoard_"
STRAIGHT_FORMATION_SECTION_PREFIX = "RailwayStraightFormationSection_"
STRAIGHT_FORMATION_MATCHING_HOLES_PREFIX = "RailwayStraightFormationMatchingFixingHoles_"
STRAIGHT_REGISTRATION_PREFIX = "RailwayStraightRegistrationFeature_"
STRAIGHT_ALIGNMENT_HOLE_PREFIX = "RailwayStraightAlignmentHoles_"
STRAIGHT_SECTION_ENGRAVING_PREFIX = "RailwayStraightSectionNumberEngraving_"
STRAIGHT_CONNECTION_INDEPENDENT = "Independent datum"
STRAIGHT_CONNECTION_CURVE_ENTRANCE = "Curve entrance"
STRAIGHT_CONNECTION_CURVE_EXIT = "Curve exit"
STRAIGHT_DIRECTION_FORWARD = "Forward"
STRAIGHT_DIRECTION_REVERSE = "Reverse"
STRAIGHT_PARALLEL_LEFT = "Left of travel"
STRAIGHT_PARALLEL_RIGHT = "Right of travel"
MAX_STRAIGHT_ROUTES = 20
LAST_INPUTS_PARAMETER_PATH = "User parameter:BaseApp/Preferences/Macros/ModelRailwayCurveTemplate"
LAST_INPUTS_PARAMETER_KEY = "LastAcceptedInputConfigurationJSON"
LAST_INPUTS_DOCUMENT_MAP_KEY = "LastAcceptedInputConfigurationsByDocumentJSON"
LAST_INPUTS_SCHEMA_VERSION = 3
MAX_REMEMBERED_INPUT_DOCUMENTS = 20
CONFIGURATION_SCHEMA_VERSION = 1
CONFIGURATION_MAX_FILE_SIZE = 5 * 1024 * 1024
CONFIGURATION_MAX_PRESETS = 100
PRESET_LIBRARY_SCHEMA_VERSION = 1
PRESET_RECORD_SCHEMA_VERSION = 1
PRESET_LIBRARY_PARAMETER_KEY = "NamedPresetLibraryJSON"
PRESET_MAX_NAME_LENGTH = 80
PRESET_MAX_DESCRIPTION_LENGTH = 500
PRESET_TIMESTAMP_FALLBACK = "1970-01-01T00:00:00Z"
CONFIGURATION_SEVERITY_INFORMATION = "Information"
CONFIGURATION_SEVERITY_WARNING = "Warning"
CONFIGURATION_SEVERITY_ERROR = "Error"
CONFIGURATION_REQUIRED_SECTIONS = (
    "curve",
    "tracks",
    "platforms",
    "straight_routes",
    "formation_board",
    "sectioning",
    "registration",
    "template_joints",
    "assembly_labels",
    "production_export",
    "material_report",
    "production_utilities",
)
_PENDING_IMPORTED_CONFIGURATION = None
DEFAULT_OUTSIDE_PLATFORM_WIDTH = 100.0
DEFAULT_OUTSIDE_PLATFORM_COVERAGE = PLATFORM_CORE
DEFAULT_OUTSIDE_PLATFORM_ENTRY_END_STYLE = PLATFORM_END_TAPERED
GEOMETRY_TOLERANCE = 1.0e-8
PLATFORM_PROJECTION_TOLERANCE = 0.01
SVG_MINIMUM_VIEWBOX_SPAN = 1.0

CENTRELINE_COLOURS = [
    (0.85, 0.15, 0.15),
    (0.15, 0.30, 0.85),
    (0.15, 0.65, 0.25),
    (0.80, 0.45, 0.10),
    (0.60, 0.20, 0.70),
    (0.10, 0.65, 0.70),
]


def clone_track_config(config, main_transition=DEFAULT_TRANSITION_LENGTH):
    mode = str(config.get("alignment_mode", MODE_MATCH_SPACINGS))
    legacy_modes = {
        "Match spacings": MODE_MATCH_SPACINGS,
        "Use easement lengths": MODE_USE_LENGTHS,
    }
    mode = legacy_modes.get(mode, mode)
    if mode not in (MODE_MATCH_SPACINGS, MODE_USE_LENGTHS, MODE_PLATFORM):
        mode = MODE_MATCH_SPACINGS

    # Version 4 migration: preserve its requested straight and curve spacings.
    # Independent easement lengths are then solved when the macro runs.
    entry_length = float(
        config.get(
            "entry_transition_length",
            config.get("widening_length", main_transition),
        )
    )
    exit_length = float(
        config.get(
            "exit_transition_length",
            config.get("widening_length", main_transition),
        )
    )

    return {
        "name": str(config.get("name", "Parallel track")),
        "side": "Inside" if str(config.get("side", "Outside")) == "Inside" else "Outside",
        "alignment_mode": mode,
        "start_spacing": float(config.get("start_spacing", 50.0)),
        "curve_spacing": float(config.get("curve_spacing", 55.0)),
        "finish_spacing": float(config.get("finish_spacing", 50.0)),
        "entry_transition_length": max(0.0, entry_length),
        "exit_transition_length": max(0.0, exit_length),
        "width": float(config.get("width", DEFAULT_MAIN_TEMPLATE_WIDTH)),
        "create_template": bool(config.get("create_template", True)),
        "show_centreline": bool(config.get("show_centreline", True)),
    }


def default_track_config(index, main_transition=DEFAULT_TRANSITION_LENGTH):
    return {
        "name": "Track {}".format(index + 2),
        "side": "Outside",
        "alignment_mode": MODE_MATCH_SPACINGS,
        "start_spacing": 50.0 + (index * 50.0),
        "curve_spacing": 55.0 + (index * 55.0),
        "finish_spacing": 50.0 + (index * 50.0),
        "entry_transition_length": float(main_transition),
        "exit_transition_length": float(main_transition),
        "width": DEFAULT_MAIN_TEMPLATE_WIDTH,
        "create_template": True,
        "show_centreline": True,
    }


def new_straight_manager_id():
    return uuid.uuid4().hex


def default_straight_config(index=0):
    return {
        "manager_id": new_straight_manager_id(),
        "enabled": True,
        "name": "Straight {}".format(int(index) + 1),
        "connection_mode": STRAIGHT_CONNECTION_INDEPENDENT,
        "length": 600.0,
        "direction": STRAIGHT_DIRECTION_FORWARD,
        "track_count": 1,
        "track_spacing": 50.0,
        "parallel_side": STRAIGHT_PARALLEL_LEFT,
        "template_width": DEFAULT_MAIN_TEMPLATE_WIDTH,
        "template_thickness": TEMPLATE_THICKNESS,
        "start_x": 0.0,
        "start_y": 0.0,
        "rotation_degrees": 0.0,
        "create_template": True,
        "show_centreline": True,
    }


def clone_straight_config(config, index=0):
    defaults = default_straight_config(index)
    source = config if isinstance(config, dict) else {}

    connection_mode = str(
        source.get("connection_mode", defaults["connection_mode"])
    )
    if connection_mode not in (
        STRAIGHT_CONNECTION_INDEPENDENT,
        STRAIGHT_CONNECTION_CURVE_ENTRANCE,
        STRAIGHT_CONNECTION_CURVE_EXIT,
    ):
        connection_mode = defaults["connection_mode"]

    direction = str(source.get("direction", defaults["direction"]))
    if direction not in (STRAIGHT_DIRECTION_FORWARD, STRAIGHT_DIRECTION_REVERSE):
        direction = defaults["direction"]

    parallel_side = str(
        source.get("parallel_side", defaults["parallel_side"])
    )
    if parallel_side not in (STRAIGHT_PARALLEL_LEFT, STRAIGHT_PARALLEL_RIGHT):
        parallel_side = defaults["parallel_side"]

    try:
        track_count = int(source.get("track_count", defaults["track_count"]))
    except (TypeError, ValueError):
        track_count = defaults["track_count"]

    manager_id = str(source.get("manager_id", "") or "").strip()
    return {
        "manager_id": manager_id or new_straight_manager_id(),
        "enabled": bool(source.get("enabled", defaults["enabled"])),
        "name": str(source.get("name", defaults["name"])).strip()
        or defaults["name"],
        "connection_mode": connection_mode,
        "length": max(0.001, float(source.get("length", defaults["length"]))),
        "direction": direction,
        "track_count": min(max(1, track_count), MAX_PARALLEL_TRACKS + 1),
        "track_spacing": max(
            0.001,
            float(source.get("track_spacing", defaults["track_spacing"])),
        ),
        "parallel_side": parallel_side,
        "template_width": max(
            0.001,
            float(source.get("template_width", defaults["template_width"])),
        ),
        "template_thickness": max(
            0.001,
            float(
                source.get(
                    "template_thickness", defaults["template_thickness"]
                )
            ),
        ),
        "start_x": float(source.get("start_x", defaults["start_x"])),
        "start_y": float(source.get("start_y", defaults["start_y"])),
        "rotation_degrees": float(
            source.get("rotation_degrees", defaults["rotation_degrees"])
        ),
        "create_template": bool(
            source.get("create_template", defaults["create_template"])
        ),
        "show_centreline": bool(
            source.get("show_centreline", defaults["show_centreline"])
        ),
    }


def clone_straight_configs(configs):
    source = configs if isinstance(configs, list) else []
    return [
        clone_straight_config(item, index)
        for index, item in enumerate(source[:MAX_STRAIGHT_ROUTES])
        if isinstance(item, dict)
    ]


def straight_manager_selection_index(configs, selected_index=0):
    source = configs if isinstance(configs, list) else []
    if not source:
        return -1
    try:
        fallback_index = int(selected_index)
    except (TypeError, ValueError):
        fallback_index = 0
    return min(max(0, fallback_index), len(source) - 1)


def new_platform_manager_id():
    return uuid.uuid4().hex


def platform_manager_selection_index(configs, selected_id="", selected_index=0):
    source = configs if isinstance(configs, list) else []
    requested_id = str(selected_id or "").strip()
    if requested_id:
        for index, config in enumerate(source):
            if not isinstance(config, dict):
                continue
            if str(config.get("manager_id", "")).strip() == requested_id:
                return index
    if not source:
        return 0
    try:
        fallback_index = int(selected_index)
    except (TypeError, ValueError):
        fallback_index = 0
    return min(max(0, fallback_index), len(source) - 1)


def default_material_report_config():
    return {
        "sheet_width": 1220.0,
        "sheet_length": 610.0,
        "usable_edge_margin": 10.0,
        "kerf_allowance": 0.0,
        "material_thickness": 0.0,
        "allow_rotation": True,
        "part_spacing": 5.0,
    }


def clone_material_report_config(config):
    defaults = default_material_report_config()
    source = config if isinstance(config, dict) else {}
    try:
        sheet_width = float(source.get("sheet_width", defaults["sheet_width"]))
        sheet_length = float(source.get("sheet_length", defaults["sheet_length"]))
        margin = float(source.get("usable_edge_margin", defaults["usable_edge_margin"]))
        kerf = float(source.get("kerf_allowance", defaults["kerf_allowance"]))
        thickness = float(source.get("material_thickness", defaults["material_thickness"]))
        spacing = float(source.get("part_spacing", defaults["part_spacing"]))
    except (TypeError, ValueError):
        return dict(defaults)
    return {
        "sheet_width": max(1.0, sheet_width),
        "sheet_length": max(1.0, sheet_length),
        "usable_edge_margin": max(0.0, margin),
        "kerf_allowance": max(0.0, kerf),
        "material_thickness": max(0.0, thickness),
        "allow_rotation": bool(source.get("allow_rotation", defaults["allow_rotation"])),
        "part_spacing": max(0.0, spacing),
    }


def validate_material_report_config(config):
    normalised = clone_material_report_config(config)
    width = normalised["sheet_width"]
    length = normalised["sheet_length"]
    margin = normalised["usable_edge_margin"]
    if width <= 0.0 or length <= 0.0:
        raise ValueError("Sheet width and length must both be greater than zero.")
    if 2.0 * margin >= min(width, length):
        raise ValueError(
            "The usable edge margin leaves no usable sheet area. Reduce the margin or increase the sheet size."
        )
    return normalised


def read_last_material_report_config():
    try:
        group = App.ParamGet(LAST_INPUTS_PARAMETER_PATH)
        stored = str(group.GetString(MATERIAL_REPORT_PARAMETER_KEY, "") or "")
        if stored:
            decoded = json.loads(stored)
            if isinstance(decoded, dict):
                return validate_material_report_config(decoded)
    except Exception:
        pass
    return default_material_report_config()


def remember_last_material_report_config(config):
    normalised = validate_material_report_config(config)
    try:
        group = App.ParamGet(LAST_INPUTS_PARAMETER_PATH)
        group.SetString(
            MATERIAL_REPORT_PARAMETER_KEY,
            json.dumps(normalised, sort_keys=True),
        )
    except Exception:
        pass
    return normalised


def default_platform_config():
    return {
        "manager_id": new_platform_manager_id(),
        "defaults_version": PLATFORM_DEFAULTS_SCHEMA_VERSION,
        "outside_platform_preset_version": OUTSIDE_PLATFORM_PRESET_VERSION,
        "enabled": False,
        "name": "Platform 1",
        "arrangement": PLATFORM_BETWEEN,
        "track_a_index": 0,
        "track_b_index": 1,
        "outside_side": PLATFORM_LEFT,
        "clearance_a": 25.0,
        "clearance_b": 25.0,
        "coverage": DEFAULT_OUTSIDE_PLATFORM_COVERAGE,
        "platform_length": 500.0,
        "centre_offset": 0.0,
        # Retained in stored JSON so Version 7.2 and earlier can reopen a
        # Version 7.4 template at the same longitudinal position.
        "start_inset": 0.0,
        "finish_inset": 0.0,
        "entry_end_style": DEFAULT_OUTSIDE_PLATFORM_ENTRY_END_STYLE,
        "exit_end_style": PLATFORM_END_TAPERED,
        "match_end_profiles": True,
        "entry_taper_length": 100.0,
        "exit_taper_length": 100.0,
        # Legacy Version 7.2/7.3 keys remain stored for backwards compatibility.
        # Version 7.4 derives them from the selected tapered end profiles.
        "vertical_end_ramps": True,
        "entry_ramp_length": 100.0,
        "exit_ramp_length": 100.0,
        "ramp_end_height": TEMPLATE_THICKNESS,
        "platform_width": DEFAULT_OUTSIDE_PLATFORM_WIDTH,
        "required_clearance": 20.0,
        "check_clearance": True,
        "create_edges": True,
        "show_edges": True,
        "body_output": PLATFORM_SOLID,
        "platform_height": 15.0,
        "show_body": True,
        "export_stl": False,
        "stl_directory": "",
    }


def default_formation_config():
    return {
        "enabled": False,
        "include_track_templates": True,
        "include_platform": True,
        "outer_margin": 10.0,
        "minimum_neck_width": 20.0,
        "fill_enclosed_gaps": True,
        "smooth_outline": False,
        "smoothing_tolerance": 0.25,
        "output_type": FORMATION_BOTH,
        "board_thickness": 12.0,
        "show_outline": True,
        "show_solid": True,
        "create_track_engraving": True,
        "create_platform_engraving": True,
    }


def clone_formation_config(config):
    defaults = default_formation_config()
    source = config if isinstance(config, dict) else {}
    output_type = str(source.get("output_type", defaults["output_type"]))
    if output_type not in (FORMATION_OUTLINE_ONLY, FORMATION_SOLID_ONLY, FORMATION_BOTH):
        output_type = defaults["output_type"]
    return {
        "enabled": bool(source.get("enabled", defaults["enabled"])),
        "include_track_templates": bool(source.get("include_track_templates", defaults["include_track_templates"])),
        "include_platform": bool(source.get("include_platform", defaults["include_platform"])),
        "outer_margin": max(0.0, float(source.get("outer_margin", defaults["outer_margin"]))),
        "minimum_neck_width": max(0.1, float(source.get("minimum_neck_width", defaults["minimum_neck_width"]))),
        "fill_enclosed_gaps": bool(source.get("fill_enclosed_gaps", defaults["fill_enclosed_gaps"])),
        "smooth_outline": bool(source.get("smooth_outline", defaults["smooth_outline"])),
        "smoothing_tolerance": max(0.001, float(source.get("smoothing_tolerance", defaults["smoothing_tolerance"]))),
        "output_type": output_type,
        "board_thickness": max(0.1, float(source.get("board_thickness", defaults["board_thickness"]))),
        "show_outline": bool(source.get("show_outline", defaults["show_outline"])),
        "show_solid": bool(source.get("show_solid", defaults["show_solid"])),
        "create_track_engraving": bool(source.get("create_track_engraving", defaults["create_track_engraving"])),
        "create_platform_engraving": bool(source.get("create_platform_engraving", defaults["create_platform_engraving"])),
    }


def default_section_config():
    return {
        "enabled": False,
        "maximum_section_length": 0.0,
        "balance_lengths": True,
        "minimum_section_length": 100.0,
        "section_track_templates": True,
        "section_platform": True,
        "section_formation": True,
        "preserve_unsplit": True,
        "number_in_travel_order": True,
    }


def clone_section_config(config):
    defaults = default_section_config()
    source = config if isinstance(config, dict) else {}
    return {
        "enabled": bool(source.get("enabled", defaults["enabled"])),
        "maximum_section_length": max(0.0, float(source.get("maximum_section_length", defaults["maximum_section_length"]))),
        "balance_lengths": bool(source.get("balance_lengths", defaults["balance_lengths"])),
        "minimum_section_length": max(0.0, float(source.get("minimum_section_length", defaults["minimum_section_length"]))),
        "section_track_templates": bool(source.get("section_track_templates", defaults["section_track_templates"])),
        "section_platform": bool(source.get("section_platform", defaults["section_platform"])),
        "section_formation": bool(source.get("section_formation", defaults["section_formation"])),
        "preserve_unsplit": bool(source.get("preserve_unsplit", defaults["preserve_unsplit"])),
        "number_in_travel_order": bool(source.get("number_in_travel_order", defaults["number_in_travel_order"])),
    }


def default_registration_config():
    return {
        "joint_type": REGISTRATION_PLAIN,
        "joint_depth": 12.0,
        "joint_width": 16.0,
        "fit_clearance": 0.20,
        "alignment_hole_diameter": 4.0,
        "alignment_hole_offset": 15.0,
    }


def clone_registration_config(config):
    defaults = default_registration_config()
    source = config if isinstance(config, dict) else {}
    joint_type = str(source.get("joint_type", defaults["joint_type"]))
    if joint_type not in (REGISTRATION_PLAIN, REGISTRATION_HOLES, REGISTRATION_PINS, REGISTRATION_TONGUE):
        joint_type = defaults["joint_type"]
    return {
        "joint_type": joint_type,
        "joint_depth": max(0.1, float(source.get("joint_depth", defaults["joint_depth"]))),
        "joint_width": max(0.1, float(source.get("joint_width", defaults["joint_width"]))),
        "fit_clearance": max(0.0, float(source.get("fit_clearance", defaults["fit_clearance"]))),
        "alignment_hole_diameter": max(0.1, float(source.get("alignment_hole_diameter", defaults["alignment_hole_diameter"]))),
        "alignment_hole_offset": max(0.1, float(source.get("alignment_hole_offset", defaults["alignment_hole_offset"]))),
    }


def default_template_assembly_config():
    return {
        "enabled": False,
        "joint_type": TEMPLATE_JOINT_TONGUE,
        "joint_depth": 8.0,
        "joint_width": 10.0,
        "fit_clearance": 0.20,
        "fixing_holes_enabled": True,
        "holes_per_section": 2,
        "hole_diameter": 2.0,
        "minimum_end_clearance": 25.0,
        "matching_formation_holes": False,
        "show_hole_geometry": True,
    }


def clone_template_assembly_config(config):
    defaults = default_template_assembly_config()
    source = config if isinstance(config, dict) else {}
    joint_type = str(source.get("joint_type", defaults["joint_type"]))
    if joint_type not in (TEMPLATE_JOINT_PLAIN, TEMPLATE_JOINT_PINS, TEMPLATE_JOINT_TONGUE):
        joint_type = defaults["joint_type"]
    try:
        holes_per_section = int(source.get("holes_per_section", defaults["holes_per_section"]))
    except Exception:
        holes_per_section = defaults["holes_per_section"]
    return {
        "enabled": bool(source.get("enabled", defaults["enabled"])),
        "joint_type": joint_type,
        "joint_depth": max(0.5, float(source.get("joint_depth", defaults["joint_depth"]))),
        "joint_width": max(0.5, float(source.get("joint_width", defaults["joint_width"]))),
        "fit_clearance": max(0.0, float(source.get("fit_clearance", defaults["fit_clearance"]))),
        "fixing_holes_enabled": bool(source.get("fixing_holes_enabled", defaults["fixing_holes_enabled"])),
        "holes_per_section": max(1, min(20, holes_per_section)),
        "hole_diameter": max(0.2, float(source.get("hole_diameter", defaults["hole_diameter"]))),
        "minimum_end_clearance": max(0.0, float(source.get("minimum_end_clearance", defaults["minimum_end_clearance"]))),
        "matching_formation_holes": bool(source.get("matching_formation_holes", defaults["matching_formation_holes"])),
        "show_hole_geometry": bool(source.get("show_hole_geometry", defaults["show_hole_geometry"])),
    }



def default_assembly_label_config():
    return {
        "schema_version": ASSEMBLY_LABEL_SCHEMA_VERSION,
        "enabled": False,
        "label_format": ASSEMBLY_LABEL_FORMAT_AUTOMATIC,
        "custom_format": "{SET} / {IDENTITY} / {SECTION}",
        "text_height": 3.0,
        "stroke_width": 0.30,
        "engraving_depth": 0.20,
        "edge_margin": 2.0,
        "preferred_placement": ASSEMBLY_LABEL_PLACE_AUTO,
        "include_template_set_id": True,
        "include_track_number": True,
        "include_track_name": False,
        "include_section_number": True,
        "include_travel_order_number": False,
        "include_platform_identity": True,
        "include_formation_identity": True,
    }


def clone_assembly_label_config(config):
    defaults = default_assembly_label_config()
    source = config if isinstance(config, dict) else {}
    label_format = str(source.get("label_format", defaults["label_format"]))
    if label_format not in (ASSEMBLY_LABEL_FORMAT_AUTOMATIC, ASSEMBLY_LABEL_FORMAT_CUSTOM):
        label_format = defaults["label_format"]
    preferred = str(source.get("preferred_placement", defaults["preferred_placement"]))
    if preferred not in ASSEMBLY_LABEL_PLACEMENTS:
        preferred = defaults["preferred_placement"]
    custom_format = str(source.get("custom_format", defaults["custom_format"]) or "").strip()
    if not custom_format:
        custom_format = defaults["custom_format"]
    if len(custom_format) > 120:
        custom_format = custom_format[:120]
    text_height = max(1.0, min(20.0, float(source.get("text_height", defaults["text_height"]))))
    stroke_width = max(0.08, min(2.0, float(source.get("stroke_width", defaults["stroke_width"]))))
    # The bitmap rows are one seventh of the text height apart. Keeping the
    # cutter width within one row cell ensures every engraved stroke remains
    # inside the placement footprint and prevents neighbouring rows merging.
    stroke_width = min(stroke_width, text_height / 7.0)
    engraving_depth = max(0.05, min(5.0, float(source.get("engraving_depth", defaults["engraving_depth"]))))
    edge_margin = max(0.0, min(50.0, float(source.get("edge_margin", defaults["edge_margin"]))))
    return {
        "schema_version": ASSEMBLY_LABEL_SCHEMA_VERSION,
        "enabled": bool(source.get("enabled", defaults["enabled"])),
        "label_format": label_format,
        "custom_format": custom_format,
        "text_height": text_height,
        "stroke_width": stroke_width,
        "engraving_depth": engraving_depth,
        "edge_margin": edge_margin,
        "preferred_placement": preferred,
        "include_template_set_id": bool(source.get("include_template_set_id", defaults["include_template_set_id"])),
        "include_track_number": bool(source.get("include_track_number", defaults["include_track_number"])),
        "include_track_name": bool(source.get("include_track_name", defaults["include_track_name"])),
        "include_section_number": bool(source.get("include_section_number", defaults["include_section_number"])),
        "include_travel_order_number": bool(source.get("include_travel_order_number", defaults["include_travel_order_number"])),
        "include_platform_identity": bool(source.get("include_platform_identity", defaults["include_platform_identity"])),
        "include_formation_identity": bool(source.get("include_formation_identity", defaults["include_formation_identity"])),
    }


def validate_assembly_label_config(config):
    normalised = clone_assembly_label_config(config)
    if normalised["label_format"] == ASSEMBLY_LABEL_FORMAT_CUSTOM:
        allowed = {
            "SET", "IDENTITY", "TRACK", "TRACK_NAME", "SECTION", "TRAVEL",
            "PLATFORM", "FORMATION", "ROUTE",
        }
        tokens = set(re.findall(r"\{([A-Za-z_]+)\}", normalised["custom_format"]))
        unsupported = sorted(token for token in tokens if token.upper() not in allowed)
        if unsupported:
            raise ValueError(
                "Unsupported assembly-label token(s): {}. Allowed tokens are {}.".format(
                    ", ".join(unsupported), ", ".join(sorted(allowed))
                )
            )
        if "{" in re.sub(r"\{[A-Za-z_]+\}", "", normalised["custom_format"]) or "}" in re.sub(r"\{[A-Za-z_]+\}", "", normalised["custom_format"]):
            raise ValueError("The custom assembly-label format contains an incomplete token.")
    return normalised



def default_production_export_config():
    return {
        "enabled": False,
        "output_directory": "",
        "include_set_identifier": True,
        "include_object_role": True,
        "include_track_number": True,
        "include_section_number": True,
        "export_each_section": True,
        "create_combined_files": True,
        "overwrite_existing": False,
        "create_manifest": True,
        "open_output_directory": False,
        "current_template_set_only": True,
        "formats": {
            EXPORT_FORMAT_DXF: True,
            EXPORT_FORMAT_SVG: True,
            EXPORT_FORMAT_STL: True,
            EXPORT_FORMAT_STEP: True,
        },
        "selections": {
            "track_template_compound_2d": True,
            "track_template_sections_2d": True,
            "track_template_fixing_holes": True,
            "track_template_joints": True,
            "platform_plan_outline": True,
            "platform_sections_2d": True,
            "formation_perimeter": True,
            "formation_sections_2d": True,
            "registration_holes": True,
            "formation_matching_holes": True,
            "registration_joints": True,
            "track_centrelines": True,
            "platform_edges": True,
            "section_numbers": True,
            "other_engraving": False,
            "assembly_labels": True,
            "track_template_compound_3d": True,
            "track_template_sections_3d": True,
            "platform_body": True,
            "platform_sections_3d": True,
            "formation_body": True,
            "formation_sections_3d": True,
        },
    }


def clone_production_export_config(config):
    defaults = default_production_export_config()
    source = config if isinstance(config, dict) else {}
    source_formats = source.get("formats", {})
    if not isinstance(source_formats, dict):
        source_formats = {}
    source_selections = source.get("selections", {})
    if not isinstance(source_selections, dict):
        source_selections = {}
    return {
        "enabled": bool(source.get("enabled", defaults["enabled"])),
        "output_directory": str(
            source.get("output_directory", defaults["output_directory"])
        ).strip(),
        # The set identifier and current-set restriction are deliberately retained
        # as required safeguards even if an older or hand-edited JSON value says
        # otherwise.
        "include_set_identifier": True,
        "include_object_role": bool(
            source.get("include_object_role", defaults["include_object_role"])
        ),
        "include_track_number": bool(
            source.get("include_track_number", defaults["include_track_number"])
        ),
        "include_section_number": bool(
            source.get("include_section_number", defaults["include_section_number"])
        ),
        "export_each_section": bool(
            source.get("export_each_section", defaults["export_each_section"])
        ),
        "create_combined_files": bool(
            source.get("create_combined_files", defaults["create_combined_files"])
        ),
        "overwrite_existing": bool(
            source.get("overwrite_existing", defaults["overwrite_existing"])
        ),
        "create_manifest": bool(
            source.get("create_manifest", defaults["create_manifest"])
        ),
        "open_output_directory": bool(
            source.get("open_output_directory", defaults["open_output_directory"])
        ),
        "current_template_set_only": True,
        "formats": {
            key: bool(source_formats.get(key, defaults["formats"][key]))
            for key in (
                EXPORT_FORMAT_DXF,
                EXPORT_FORMAT_SVG,
                EXPORT_FORMAT_STL,
                EXPORT_FORMAT_STEP,
            )
        },
        "selections": {
            key: bool(source_selections.get(key, default_value))
            for key, default_value in defaults["selections"].items()
        },
    }

def clone_platform_config(config):
    defaults = default_platform_config()
    source = config if isinstance(config, dict) else {}

    arrangement = str(source.get("arrangement", defaults["arrangement"]))
    if arrangement not in (PLATFORM_BETWEEN, PLATFORM_OUTSIDE):
        arrangement = defaults["arrangement"]

    outside_side = str(source.get("outside_side", defaults["outside_side"]))
    if outside_side not in (PLATFORM_LEFT, PLATFORM_RIGHT):
        outside_side = defaults["outside_side"]

    coverage = str(source.get("coverage", defaults["coverage"]))
    try:
        outside_platform_preset_version = int(
            source.get("outside_platform_preset_version", 0)
        )
    except (TypeError, ValueError):
        outside_platform_preset_version = 0
    if coverage not in (
        PLATFORM_CONSTANT,
        PLATFORM_ENTRY,
        PLATFORM_EXIT,
        PLATFORM_CORE,
    ):
        coverage = defaults["coverage"]
    # Version 9.0-9.12 could save a partly initialised Platform Manager editor
    # over the selected row while the dialogue was opening. The exact characteristic
    # corruption was Outside one track with Constant curve only and Square. Use a
    # dedicated revision marker, but repair only that exact pair so deliberate
    # alternative coverage/end-style combinations remain untouched.
    migrate_outside_defaults = bool(
        arrangement == PLATFORM_OUTSIDE
        and outside_platform_preset_version < OUTSIDE_PLATFORM_PRESET_VERSION
    )

    body_output = str(source.get("body_output", defaults["body_output"]))
    if body_output not in (PLATFORM_EDGES_ONLY, PLATFORM_FACE, PLATFORM_SOLID):
        body_output = defaults["body_output"]

    def normalise_end_style(value, fallback):
        value = str(value)
        if value == PLATFORM_END_TAPERED_LABEL:
            return PLATFORM_END_TAPERED
        if value not in (PLATFORM_END_SQUARE, PLATFORM_END_TAPERED):
            return fallback
        return value

    entry_end_style = normalise_end_style(
        source.get("entry_end_style", defaults["entry_end_style"]),
        defaults["entry_end_style"],
    )
    if (
        migrate_outside_defaults
        and coverage == PLATFORM_CONSTANT
        and entry_end_style == PLATFORM_END_SQUARE
    ):
        coverage = DEFAULT_OUTSIDE_PLATFORM_COVERAGE
        entry_end_style = DEFAULT_OUTSIDE_PLATFORM_ENTRY_END_STYLE
    exit_end_style = normalise_end_style(
        source.get("exit_end_style", defaults["exit_end_style"]),
        defaults["exit_end_style"],
    )

    entry_taper_length = max(
        0.0,
        float(source.get("entry_taper_length", defaults["entry_taper_length"])),
    )
    exit_taper_length = max(
        0.0,
        float(source.get("exit_taper_length", defaults["exit_taper_length"])),
    )
    # Version 7.4 defaults older saved platform definitions to matched ends.
    # This removes the accidental 50/30 mm mismatch visible in Version 7.3 while
    # still allowing independent profiles when the user unticks the new control.
    if "match_end_profiles" in source:
        match_end_profiles = bool(source.get("match_end_profiles"))
    else:
        # Older files with the same end style at both ends are treated as an
        # intended matched pair. Mixed square/tapered ends remain independent.
        match_end_profiles = entry_end_style == exit_end_style
    if match_end_profiles:
        exit_end_style = entry_end_style
        exit_taper_length = entry_taper_length

    legacy_start_inset = max(
        0.0,
        float(source.get("start_inset", defaults["start_inset"])),
    )
    legacy_finish_inset = max(
        0.0,
        float(source.get("finish_inset", defaults["finish_inset"])),
    )
    platform_length = max(
        0.0,
        float(source.get("platform_length", defaults["platform_length"])),
    )
    centre_offset = float(
        source.get(
            "centre_offset",
            0.5 * (legacy_start_inset - legacy_finish_inset),
        )
    )

    entry_is_ramp = (
        body_output == PLATFORM_SOLID
        and entry_end_style == PLATFORM_END_TAPERED
    )
    exit_is_ramp = (
        body_output == PLATFORM_SOLID
        and exit_end_style == PLATFORM_END_TAPERED
    )

    manager_id = str(source.get("manager_id", "")).strip()
    if not manager_id:
        manager_id = new_platform_manager_id()

    return {
        "manager_id": manager_id,
        "defaults_version": PLATFORM_DEFAULTS_SCHEMA_VERSION,
        "outside_platform_preset_version": OUTSIDE_PLATFORM_PRESET_VERSION,
        "enabled": bool(source.get("enabled", defaults["enabled"])),
        "name": (
            str(source.get("name", defaults["name"])).strip()
            or defaults["name"]
        )[:MAX_PLATFORM_NAME_LENGTH],
        "arrangement": arrangement,
        "track_a_index": max(0, int(source.get("track_a_index", defaults["track_a_index"]))),
        "track_b_index": max(0, int(source.get("track_b_index", defaults["track_b_index"]))),
        "outside_side": outside_side,
        "clearance_a": max(0.0, float(source.get("clearance_a", defaults["clearance_a"]))),
        "clearance_b": max(0.0, float(source.get("clearance_b", defaults["clearance_b"]))),
        "coverage": coverage,
        "platform_length": platform_length,
        "centre_offset": centre_offset,
        "start_inset": legacy_start_inset,
        "finish_inset": legacy_finish_inset,
        "entry_end_style": entry_end_style,
        "exit_end_style": exit_end_style,
        "match_end_profiles": match_end_profiles,
        "entry_taper_length": entry_taper_length,
        "exit_taper_length": exit_taper_length,
        "vertical_end_ramps": bool(entry_is_ramp or exit_is_ramp),
        "entry_ramp_length": entry_taper_length if entry_is_ramp else 0.0,
        "exit_ramp_length": exit_taper_length if exit_is_ramp else 0.0,
        "ramp_end_height": TEMPLATE_THICKNESS,
        "platform_width": max(0.0, float(source.get("platform_width", defaults["platform_width"]))),
        "required_clearance": max(0.0, float(source.get("required_clearance", defaults["required_clearance"]))),
        "check_clearance": bool(source.get("check_clearance", defaults["check_clearance"])),
        "create_edges": bool(source.get("create_edges", defaults["create_edges"])),
        "show_edges": bool(source.get("show_edges", defaults["show_edges"])),
        "body_output": body_output,
        "platform_height": max(0.0, float(source.get("platform_height", defaults["platform_height"]))),
        "show_body": bool(source.get("show_body", defaults["show_body"])),
        # Version 9 removes the legacy platform-only STL exporter. These keys are
        # retained only so older settings can be mirrored without reviving it.
        "export_stl": False,
        "stl_directory": "",
    }


def clone_platform_configs(configs):
    source = configs if isinstance(configs, list) else []
    result = [
        clone_platform_config(item)
        for item in source[:MAX_PLATFORMS]
        if isinstance(item, dict)
    ]
    return result or [default_platform_config()]


def _document_input_cache_key(doc):
    if doc is None:
        return ""
    try:
        filename = str(getattr(doc, "FileName", "") or "").strip()
    except Exception:
        filename = ""
    if filename:
        try:
            filename = os.path.normcase(os.path.abspath(filename))
        except Exception:
            pass
        return "file:{}".format(filename)
    try:
        name = str(getattr(doc, "Name", "") or "").strip()
    except Exception:
        name = ""
    return "document:{}".format(name) if name else ""


def _normalise_last_input_payload(payload, doc=None):
    if not isinstance(payload, dict):
        return None
    try:
        schema_version = int(payload.get("schema_version", 0))
    except (TypeError, ValueError):
        return None
    # Version 9.6 accepts the Version 9.3 single-payload schema and the new
    # per-document schema. Document selection is handled by the reader before
    # normalisation so a saved/renamed document can still use the last-used
    # fallback rather than losing every dialogue value.
    if schema_version not in (1, 2, LAST_INPUTS_SCHEMA_VERSION):
        return None
    try:
        transition = max(0.0, float(payload["transition"]))
        radius = max(0.001, float(payload["radius"]))
        angle = float(payload["angle"])
        main_width = max(0.001, float(payload["main_width"]))
    except (KeyError, TypeError, ValueError):
        return None
    output_mode = str(payload.get("output_mode", OUTPUT_REPLACE))
    if output_mode not in (OUTPUT_REPLACE, OUTPUT_CREATE_NEW):
        output_mode = OUTPUT_REPLACE
    raw_track_configs = payload.get("track_configs")
    if isinstance(raw_track_configs, list):
        track_configs = [
            clone_track_config(item, transition)
            for item in raw_track_configs[:MAX_PARALLEL_TRACKS]
            if isinstance(item, dict)
        ]
    else:
        track_configs = [
            clone_track_config(item, transition) for item in DEFAULT_PARALLEL_TRACKS
        ]
    try:
        selected_platform_index = max(
            0,
            int(payload.get("selected_platform_index", 0) or 0),
        )
    except (TypeError, ValueError):
        selected_platform_index = 0
    try:
        selected_straight_index = int(
            payload.get("selected_straight_index", 0) or 0
        )
    except (TypeError, ValueError):
        selected_straight_index = 0
    return {
        "transition": transition,
        "radius": radius,
        "angle": angle,
        "main_width": main_width,
        "track_configs": track_configs,
        "straight_configs": clone_straight_configs(
            payload.get("straight_configs", [])
        ),
        "selected_straight_index": selected_straight_index,
        "platform_configs": clone_platform_configs(payload.get("platform_configs", [])),
        "selected_platform_id": str(
            payload.get("selected_platform_id", "") or ""
        ).strip(),
        "selected_platform_index": selected_platform_index,
        "formation_config": clone_formation_config(payload.get("formation_config", {})),
        "section_config": clone_section_config(payload.get("section_config", {})),
        "registration_config": clone_registration_config(payload.get("registration_config", {})),
        "template_assembly_config": clone_template_assembly_config(payload.get("template_assembly_config", {})),
        "production_export_config": clone_production_export_config(payload.get("production_export_config", {})),
        "output_mode": output_mode,
    }


def read_last_dialog_inputs(doc):
    try:
        parameter_group = App.ParamGet(LAST_INPUTS_PARAMETER_PATH)
    except Exception:
        return None

    document_key = _document_input_cache_key(doc)
    if document_key:
        try:
            stored_map = str(
                parameter_group.GetString(LAST_INPUTS_DOCUMENT_MAP_KEY, "") or ""
            )
            decoded_map = json.loads(stored_map) if stored_map else {}
            if isinstance(decoded_map, dict):
                exact_payload = decoded_map.get(document_key)
                exact = _normalise_last_input_payload(exact_payload, doc)
                if exact is not None:
                    return exact
        except Exception:
            pass

    # The global last-used payload is an intentional fallback. It covers new
    # documents, documents saved under a new filename after a failed run, and
    # users who create a fresh FreeCAD document for each small revision.
    try:
        stored = str(
            parameter_group.GetString(LAST_INPUTS_PARAMETER_KEY, "") or ""
        )
        if stored:
            return _normalise_last_input_payload(json.loads(stored), doc)
    except Exception:
        pass
    return None


def remember_last_dialog_inputs(
    doc,
    transition,
    radius,
    angle,
    main_width,
    track_configs,
    straight_configs,
    selected_straight_index,
    platform_configs,
    selected_platform_id,
    selected_platform_index,
    formation_config,
    section_config,
    registration_config,
    template_assembly_config,
    production_export_config,
    output_mode,
):
    payload = {
        "schema_version": LAST_INPUTS_SCHEMA_VERSION,
        "document_key": _document_input_cache_key(doc),
        "saved_at": datetime.datetime.now().isoformat(timespec="seconds"),
        "transition": float(transition),
        "radius": float(radius),
        "angle": float(angle),
        "main_width": float(main_width),
        "track_configs": [
            clone_track_config(item, transition) for item in track_configs
        ],
        "straight_configs": clone_straight_configs(straight_configs),
        "selected_straight_index": max(-1, int(selected_straight_index)),
        "platform_configs": clone_platform_configs(platform_configs),
        "selected_platform_id": str(selected_platform_id or "").strip(),
        "selected_platform_index": max(0, int(selected_platform_index)),
        "formation_config": clone_formation_config(formation_config),
        "section_config": clone_section_config(section_config),
        "registration_config": clone_registration_config(registration_config),
        "template_assembly_config": clone_template_assembly_config(template_assembly_config),
        "production_export_config": clone_production_export_config(production_export_config),
        "output_mode": (
            output_mode
            if output_mode in (OUTPUT_REPLACE, OUTPUT_CREATE_NEW)
            else OUTPUT_REPLACE
        ),
    }
    try:
        parameter_group = App.ParamGet(LAST_INPUTS_PARAMETER_PATH)
        serialised_payload = json.dumps(payload, sort_keys=True)
        parameter_group.SetString(
            LAST_INPUTS_PARAMETER_KEY,
            serialised_payload,
        )

        document_key = _document_input_cache_key(doc)
        if document_key:
            try:
                stored_map = str(
                    parameter_group.GetString(
                        LAST_INPUTS_DOCUMENT_MAP_KEY, ""
                    ) or ""
                )
                decoded_map = json.loads(stored_map) if stored_map else {}
                if not isinstance(decoded_map, dict):
                    decoded_map = {}
                decoded_map[document_key] = payload
                if len(decoded_map) > MAX_REMEMBERED_INPUT_DOCUMENTS:
                    ordered_keys = sorted(
                        decoded_map,
                        key=lambda key: str(
                            decoded_map[key].get("saved_at", "")
                            if isinstance(decoded_map[key], dict)
                            else ""
                        ),
                    )
                    for stale_key in ordered_keys[
                        :len(decoded_map) - MAX_REMEMBERED_INPUT_DOCUMENTS
                    ]:
                        decoded_map.pop(stale_key, None)
                parameter_group.SetString(
                    LAST_INPUTS_DOCUMENT_MAP_KEY,
                    json.dumps(decoded_map, sort_keys=True),
                )
            except Exception:
                # The global last-used payload has already been stored, so a
                # damaged per-document map must not discard the user's inputs.
                pass
        return True
    except Exception:
        return False


# ---------------------------------------------------------------------------
# Version 10.2A6 configuration import and export
# ---------------------------------------------------------------------------


def _configuration_json_copy(value):
    return json.loads(json.dumps(value, ensure_ascii=False, sort_keys=True))


def _configuration_display_value(value, maximum=160):
    try:
        text = json.dumps(value, ensure_ascii=False, sort_keys=True)
    except Exception:
        text = repr(value)
    if len(text) > maximum:
        return text[: maximum - 3] + "..."
    return text


def _configuration_diagnostic(
    severity,
    field_path,
    supplied_value,
    expected,
    message,
    migration_action="",
    default_applied=False,
):
    severity = str(severity)
    return {
        "severity": severity,
        "field_path": str(field_path or "$"),
        "supplied_value": _configuration_json_copy(supplied_value),
        "expected": str(expected or ""),
        "message": str(message or ""),
        "migration_action": str(migration_action or ""),
        "default_applied": bool(default_applied),
        "blocks_import": severity == CONFIGURATION_SEVERITY_ERROR,
    }


def _configuration_add_diagnostic(
    diagnostics,
    severity,
    field_path,
    supplied_value,
    expected,
    message,
    migration_action="",
    default_applied=False,
):
    diagnostics.append(
        _configuration_diagnostic(
            severity,
            field_path,
            supplied_value,
            expected,
            message,
            migration_action,
            default_applied,
        )
    )


def _configuration_is_number(value):
    return (
        isinstance(value, (int, float))
        and not isinstance(value, bool)
        and math.isfinite(float(value))
    )


def _configuration_string_looks_executable(value):
    text = str(value or "")
    patterns = (
        r"\b(?:eval|exec|compile|__import__)\s*\(",
        r"(?:^|[;\n])\s*(?:lambda\b|import\s+|from\s+[A-Za-z_][A-Za-z0-9_\.]*\s+import\b)",
        r"\b(?:os\.system|subprocess\.|pickle\.loads|marshal\.loads)\b",
    )
    return any(re.search(pattern, text, flags=re.IGNORECASE) for pattern in patterns)


def _configuration_scan_plain_data(value, path, diagnostics):
    if isinstance(value, dict):
        for key, child in value.items():
            if not isinstance(key, str):
                _configuration_add_diagnostic(
                    diagnostics,
                    CONFIGURATION_SEVERITY_ERROR,
                    path,
                    key,
                    "JSON object keys must be strings",
                    "A non-string object key is not supported.",
                )
                continue
            _configuration_scan_plain_data(
                child,
                "{}.{}".format(path, key) if path != "$" else "$.{}".format(key),
                diagnostics,
            )
    elif isinstance(value, list):
        for index, child in enumerate(value):
            _configuration_scan_plain_data(
                child, "{}[{}]".format(path, index), diagnostics
            )
    elif isinstance(value, str):
        if "\x00" in value or any(ord(char) < 9 for char in value):
            _configuration_add_diagnostic(
                diagnostics,
                CONFIGURATION_SEVERITY_ERROR,
                path,
                value,
                "Plain text without NUL or control characters",
                "Unsafe control characters are not supported.",
            )
        elif _configuration_string_looks_executable(value):
            _configuration_add_diagnostic(
                diagnostics,
                CONFIGURATION_SEVERITY_ERROR,
                path,
                value,
                "Plain non-executable configuration text",
                "Expression-like or executable content is not accepted.",
            )
    elif value is not None and not isinstance(value, (bool, int, float)):
        _configuration_add_diagnostic(
            diagnostics,
            CONFIGURATION_SEVERITY_ERROR,
            path,
            repr(value),
            "JSON null, boolean, number, string, array or object",
            "Unsupported data type.",
        )


def _configuration_alias_section(source, aliases, canonical, diagnostics):
    if canonical in source:
        return source.get(canonical)
    for alias in aliases:
        if alias in source:
            _configuration_add_diagnostic(
                diagnostics,
                CONFIGURATION_SEVERITY_INFORMATION,
                "$.configuration.{}".format(canonical),
                source.get(alias),
                "Current field name '{}'".format(canonical),
                "Recognised older field name was migrated.",
                "{} -> {}".format(alias, canonical),
            )
            return source.get(alias)
    return None


def _legacy_last_inputs_to_configuration(payload, diagnostics):
    try:
        curve = {
            "transition": payload["transition"],
            "radius": payload["radius"],
            "angle": payload["angle"],
            "main_width": payload["main_width"],
        }
    except KeyError as error:
        _configuration_add_diagnostic(
            diagnostics,
            CONFIGURATION_SEVERITY_ERROR,
            "$",
            payload,
            "Recognised legacy last-input payload",
            "Legacy payload is missing required field {}.".format(error),
        )
        return None
    migrated = {
        "schema_version": CONFIGURATION_SCHEMA_VERSION,
        "macro_version": str(payload.get("macro_version") or "Legacy saved settings"),
        "configuration": {
            "curve": curve,
            "tracks": payload.get("track_configs", []),
            "platforms": payload.get("platform_configs", [default_platform_config()]),
            "straight_routes": payload.get("straight_configs", []),
            "formation_board": payload.get("formation_config", default_formation_config()),
            "sectioning": payload.get("section_config", default_section_config()),
            "registration": payload.get("registration_config", default_registration_config()),
            "template_joints": payload.get("template_assembly_config", default_template_assembly_config()),
            "assembly_labels": payload.get("assembly_label_config", default_assembly_label_config()),
            "production_export": payload.get("production_export_config", default_production_export_config()),
            "material_report": payload.get("material_report_config", default_material_report_config()),
            "production_utilities": {
                "output_mode": payload.get("output_mode", OUTPUT_REPLACE),
            },
        },
        "presets": payload.get("presets", []),
    }
    _configuration_add_diagnostic(
        diagnostics,
        CONFIGURATION_SEVERITY_INFORMATION,
        "$",
        payload.get("schema_version", "absent"),
        "Configuration schema {}".format(CONFIGURATION_SCHEMA_VERSION),
        "Recognised Version 10.0/10.2 saved-dialog payload was migrated.",
        "Legacy saved inputs -> configuration schema 1",
    )
    return migrated


def migrate_configuration_payload(payload):
    diagnostics = []
    if not isinstance(payload, dict):
        _configuration_add_diagnostic(
            diagnostics,
            CONFIGURATION_SEVERITY_ERROR,
            "$",
            payload,
            "JSON object",
            "The configuration root must be a JSON object.",
        )
        return None, diagnostics

    _configuration_scan_plain_data(payload, "$", diagnostics)
    if any(item["blocks_import"] for item in diagnostics):
        return None, diagnostics

    if (
        "configuration" not in payload
        and all(key in payload for key in ("transition", "radius", "angle", "main_width"))
    ):
        return _legacy_last_inputs_to_configuration(payload, diagnostics), diagnostics

    raw_schema = payload.get("schema_version")
    if not isinstance(raw_schema, int) or isinstance(raw_schema, bool):
        _configuration_add_diagnostic(
            diagnostics,
            CONFIGURATION_SEVERITY_ERROR,
            "$.schema_version",
            raw_schema,
            "Integer schema version",
            "A supported schema version is required.",
        )
        return None, diagnostics
    if raw_schema > CONFIGURATION_SCHEMA_VERSION:
        _configuration_add_diagnostic(
            diagnostics,
            CONFIGURATION_SEVERITY_ERROR,
            "$.schema_version",
            raw_schema,
            "Schema version <= {}".format(CONFIGURATION_SCHEMA_VERSION),
            "This configuration was created by an unsupported future schema.",
        )
        return None, diagnostics
    if raw_schema < 0:
        _configuration_add_diagnostic(
            diagnostics,
            CONFIGURATION_SEVERITY_ERROR,
            "$.schema_version",
            raw_schema,
            "Schema version 0 or {}".format(CONFIGURATION_SCHEMA_VERSION),
            "Negative schema versions are not supported.",
        )
        return None, diagnostics
    if raw_schema == CONFIGURATION_SCHEMA_VERSION:
        return _configuration_json_copy(payload), diagnostics

    # Schema 0 was the controlled development schema used before Stage 6 was
    # finalised. It is deliberately migrated in one place rather than through
    # scattered compatibility aliases in the validators.
    source_configuration = payload.get("configuration")
    if not isinstance(source_configuration, dict):
        _configuration_add_diagnostic(
            diagnostics,
            CONFIGURATION_SEVERITY_ERROR,
            "$.configuration",
            source_configuration,
            "JSON object",
            "Schema 0 requires a configuration object.",
        )
        return None, diagnostics
    migrated_configuration = {
        "curve": _configuration_alias_section(
            source_configuration, ("main_curve",), "curve", diagnostics
        ),
        "tracks": _configuration_alias_section(
            source_configuration, ("parallel_tracks", "track_configs"), "tracks", diagnostics
        ),
        "platforms": _configuration_alias_section(
            source_configuration, ("platform_configs",), "platforms", diagnostics
        ),
        "straight_routes": _configuration_alias_section(
            source_configuration, ("straight_tracks", "straight_configs"), "straight_routes", diagnostics
        ),
        "formation_board": _configuration_alias_section(
            source_configuration, ("formation", "formation_config"), "formation_board", diagnostics
        ),
        "sectioning": _configuration_alias_section(
            source_configuration, ("sections", "section_config"), "sectioning", diagnostics
        ),
        "registration": _configuration_alias_section(
            source_configuration, ("registration_holes", "registration_config"), "registration", diagnostics
        ),
        "template_joints": _configuration_alias_section(
            source_configuration, ("template_assembly", "template_assembly_config"), "template_joints", diagnostics
        ),
        "assembly_labels": _configuration_alias_section(
            source_configuration, ("labels", "assembly_label_config"), "assembly_labels", diagnostics
        ),
        "production_export": _configuration_alias_section(
            source_configuration, ("export", "production_export_config"), "production_export", diagnostics
        ),
        "material_report": _configuration_alias_section(
            source_configuration, ("materials", "material_report_config"), "material_report", diagnostics
        ),
        "production_utilities": _configuration_alias_section(
            source_configuration, ("utilities",), "production_utilities", diagnostics
        ),
    }
    schema_zero_defaults = {
        "tracks": [],
        "platforms": [default_platform_config()],
        "straight_routes": [],
        "formation_board": default_formation_config(),
        "sectioning": default_section_config(),
        "registration": default_registration_config(),
        "template_joints": default_template_assembly_config(),
        "assembly_labels": default_assembly_label_config(),
        "production_export": default_production_export_config(),
        "material_report": default_material_report_config(),
        "production_utilities": {"output_mode": OUTPUT_REPLACE},
    }
    for section_name, default_value in schema_zero_defaults.items():
        if migrated_configuration.get(section_name) is None:
            migrated_configuration[section_name] = default_value
            _configuration_add_diagnostic(
                diagnostics,
                CONFIGURATION_SEVERITY_INFORMATION,
                "$.configuration.{}".format(section_name),
                None,
                "Current schema section",
                "Schema 0 did not contain this later optional section; the current default was applied.",
                "Default applied during schema 0 migration",
                True,
            )
    migrated = {
        "schema_version": CONFIGURATION_SCHEMA_VERSION,
        "macro_version": str(payload.get("macro_version") or "10.2 development schema"),
        "configuration": migrated_configuration,
        "presets": payload.get("presets", []),
    }
    _configuration_add_diagnostic(
        diagnostics,
        CONFIGURATION_SEVERITY_INFORMATION,
        "$.schema_version",
        raw_schema,
        "Schema version {}".format(CONFIGURATION_SCHEMA_VERSION),
        "Recognised schema 0 was migrated deterministically.",
        "Schema 0 -> schema 1",
    )
    return migrated, diagnostics


def _configuration_unknown_fields(source, allowed, path, diagnostics):
    if not isinstance(source, dict):
        return
    for key in sorted(set(source) - set(allowed)):
        _configuration_add_diagnostic(
            diagnostics,
            CONFIGURATION_SEVERITY_WARNING,
            "{}.{}".format(path, key),
            source.get(key),
            "Known optional field",
            "Unknown optional field was ignored safely.",
            "Ignored",
        )


def _configuration_field(
    source,
    key,
    default,
    path,
    diagnostics,
    kind,
    minimum=None,
    maximum=None,
    choices=None,
    maximum_length=None,
    allow_empty=True,
    fixed_value=None,
):
    field_path = "{}.{}".format(path, key)
    if key not in source:
        _configuration_add_diagnostic(
            diagnostics,
            CONFIGURATION_SEVERITY_INFORMATION,
            field_path,
            None,
            kind,
            "Optional field was absent and received its current default.",
            "Default applied",
            True,
        )
        return _configuration_json_copy(default)
    value = source.get(key)
    valid = True
    expected = kind
    if kind == "boolean":
        valid = isinstance(value, bool)
    elif kind == "integer":
        valid = isinstance(value, int) and not isinstance(value, bool)
        if valid and minimum is not None:
            valid = value >= minimum
        if valid and maximum is not None:
            valid = value <= maximum
        expected = "integer{}".format(
            " from {} to {}".format(minimum, maximum)
            if minimum is not None and maximum is not None
            else ""
        )
    elif kind == "number":
        valid = _configuration_is_number(value)
        if valid and minimum is not None:
            valid = float(value) >= minimum
        if valid and maximum is not None:
            valid = float(value) <= maximum
        expected = "finite number{}".format(
            " from {} to {}".format(minimum, maximum)
            if minimum is not None and maximum is not None
            else ""
        )
    elif kind == "string":
        valid = isinstance(value, str)
        if valid and not allow_empty:
            valid = bool(value.strip())
        if valid and maximum_length is not None:
            valid = len(value) <= maximum_length
        expected = "string{}".format(
            " of at most {} characters".format(maximum_length)
            if maximum_length is not None
            else ""
        )
    elif kind == "path":
        valid = isinstance(value, str) and "\x00" not in value and "\n" not in value and "\r" not in value
        if valid and maximum_length is not None:
            valid = len(value) <= maximum_length
        expected = "plain filesystem path"
    elif kind == "enumeration":
        valid = isinstance(value, str) and value in tuple(choices or ())
        expected = "one of: {}".format(", ".join(str(item) for item in choices or ()))
    else:
        valid = False
    if valid and fixed_value is not None:
        valid = value == fixed_value
        expected = "fixed value {}".format(_configuration_display_value(fixed_value))
    if not valid:
        _configuration_add_diagnostic(
            diagnostics,
            CONFIGURATION_SEVERITY_ERROR,
            field_path,
            value,
            expected,
            "Invalid field value.",
        )
        return _configuration_json_copy(default)
    if kind == "number":
        return float(value)
    if kind == "string" or kind == "path":
        return str(value).strip() if kind == "path" else str(value)
    return value


def _validate_known_dictionary(source, defaults, specs, path, diagnostics):
    if not isinstance(source, dict):
        _configuration_add_diagnostic(
            diagnostics,
            CONFIGURATION_SEVERITY_ERROR,
            path,
            source,
            "JSON object",
            "This configuration section must be a JSON object.",
        )
        source = {}
    _configuration_unknown_fields(source, specs.keys(), path, diagnostics)
    result = {}
    for key, specification in specs.items():
        options = dict(specification)
        kind = options.pop("kind")
        result[key] = _configuration_field(
            source,
            key,
            defaults.get(key),
            path,
            diagnostics,
            kind,
            **options
        )
    return result


def _curve_configuration_specs():
    return {
        "transition": {"kind": "number", "minimum": 0.0, "maximum": 100000.0},
        "radius": {"kind": "number", "minimum": 1.0, "maximum": 100000.0},
        "angle": {"kind": "number", "minimum": -360.0, "maximum": 360.0},
        "main_width": {"kind": "number", "minimum": 0.1, "maximum": 1000.0},
    }


def _track_configuration_specs():
    return {
        "name": {"kind": "string", "maximum_length": 80, "allow_empty": False},
        "side": {"kind": "enumeration", "choices": ("Inside", "Outside")},
        "alignment_mode": {"kind": "enumeration", "choices": (MODE_MATCH_SPACINGS, MODE_USE_LENGTHS, MODE_PLATFORM)},
        "start_spacing": {"kind": "number", "minimum": 0.0, "maximum": 100000.0},
        "curve_spacing": {"kind": "number", "minimum": 0.0, "maximum": 100000.0},
        "finish_spacing": {"kind": "number", "minimum": 0.0, "maximum": 100000.0},
        "entry_transition_length": {"kind": "number", "minimum": 0.0, "maximum": 100000.0},
        "exit_transition_length": {"kind": "number", "minimum": 0.0, "maximum": 100000.0},
        "width": {"kind": "number", "minimum": 0.1, "maximum": 1000.0},
        "create_template": {"kind": "boolean"},
        "show_centreline": {"kind": "boolean"},
    }


def _straight_configuration_specs():
    return {
        "manager_id": {"kind": "string", "maximum_length": 128, "allow_empty": False},
        "enabled": {"kind": "boolean"},
        "name": {"kind": "string", "maximum_length": 80, "allow_empty": False},
        "connection_mode": {"kind": "enumeration", "choices": (STRAIGHT_CONNECTION_INDEPENDENT, STRAIGHT_CONNECTION_CURVE_ENTRANCE, STRAIGHT_CONNECTION_CURVE_EXIT)},
        "length": {"kind": "number", "minimum": 0.001, "maximum": 1000000.0},
        "direction": {"kind": "enumeration", "choices": (STRAIGHT_DIRECTION_FORWARD, STRAIGHT_DIRECTION_REVERSE)},
        "track_count": {"kind": "integer", "minimum": 1, "maximum": MAX_PARALLEL_TRACKS + 1},
        "track_spacing": {"kind": "number", "minimum": 0.001, "maximum": 100000.0},
        "parallel_side": {"kind": "enumeration", "choices": (STRAIGHT_PARALLEL_LEFT, STRAIGHT_PARALLEL_RIGHT)},
        "template_width": {"kind": "number", "minimum": 0.001, "maximum": 10000.0},
        "template_thickness": {"kind": "number", "minimum": 0.001, "maximum": 1000.0},
        "start_x": {"kind": "number", "minimum": -1000000.0, "maximum": 1000000.0},
        "start_y": {"kind": "number", "minimum": -1000000.0, "maximum": 1000000.0},
        "rotation_degrees": {"kind": "number", "minimum": -360.0, "maximum": 360.0},
        "create_template": {"kind": "boolean"},
        "show_centreline": {"kind": "boolean"},
    }


def _platform_configuration_specs():
    return {
        "manager_id": {"kind": "string", "maximum_length": 128, "allow_empty": False},
        "defaults_version": {"kind": "integer", "minimum": 1, "maximum": PLATFORM_DEFAULTS_SCHEMA_VERSION},
        "outside_platform_preset_version": {"kind": "integer", "minimum": 1, "maximum": OUTSIDE_PLATFORM_PRESET_VERSION},
        "enabled": {"kind": "boolean"},
        "name": {"kind": "string", "maximum_length": MAX_PLATFORM_NAME_LENGTH, "allow_empty": False},
        "arrangement": {"kind": "enumeration", "choices": (PLATFORM_BETWEEN, PLATFORM_OUTSIDE)},
        "track_a_index": {"kind": "integer", "minimum": 0, "maximum": MAX_PARALLEL_TRACKS},
        "track_b_index": {"kind": "integer", "minimum": 0, "maximum": MAX_PARALLEL_TRACKS},
        "outside_side": {"kind": "enumeration", "choices": (PLATFORM_LEFT, PLATFORM_RIGHT)},
        "clearance_a": {"kind": "number", "minimum": 0.001, "maximum": 10000.0},
        "clearance_b": {"kind": "number", "minimum": 0.001, "maximum": 10000.0},
        "coverage": {"kind": "enumeration", "choices": (PLATFORM_CONSTANT, PLATFORM_ENTRY, PLATFORM_EXIT, PLATFORM_CORE)},
        "platform_length": {"kind": "number", "minimum": 0.001, "maximum": 100000.0},
        "centre_offset": {"kind": "number", "minimum": -100000.0, "maximum": 100000.0},
        "start_inset": {"kind": "number", "minimum": 0.0, "maximum": 100000.0},
        "finish_inset": {"kind": "number", "minimum": 0.0, "maximum": 100000.0},
        "entry_end_style": {"kind": "enumeration", "choices": (PLATFORM_END_SQUARE, PLATFORM_END_TAPERED)},
        "exit_end_style": {"kind": "enumeration", "choices": (PLATFORM_END_SQUARE, PLATFORM_END_TAPERED)},
        "match_end_profiles": {"kind": "boolean"},
        "entry_taper_length": {"kind": "number", "minimum": 0.0, "maximum": 100000.0},
        "exit_taper_length": {"kind": "number", "minimum": 0.0, "maximum": 100000.0},
        "vertical_end_ramps": {"kind": "boolean"},
        "entry_ramp_length": {"kind": "number", "minimum": 0.0, "maximum": 100000.0},
        "exit_ramp_length": {"kind": "number", "minimum": 0.0, "maximum": 100000.0},
        "ramp_end_height": {"kind": "number", "minimum": 0.0, "maximum": 1000.0},
        "platform_width": {"kind": "number", "minimum": 0.0, "maximum": 10000.0},
        "required_clearance": {"kind": "number", "minimum": 0.0, "maximum": 10000.0},
        "check_clearance": {"kind": "boolean"},
        "create_edges": {"kind": "boolean"},
        "show_edges": {"kind": "boolean"},
        "body_output": {"kind": "enumeration", "choices": (PLATFORM_EDGES_ONLY, PLATFORM_FACE, PLATFORM_SOLID)},
        "platform_height": {"kind": "number", "minimum": 0.0, "maximum": 1000.0},
        "show_body": {"kind": "boolean"},
        "export_stl": {"kind": "boolean", "fixed_value": False},
        "stl_directory": {"kind": "path", "maximum_length": 4096},
    }


def _formation_configuration_specs():
    return {
        "enabled": {"kind": "boolean"},
        "include_track_templates": {"kind": "boolean"},
        "include_platform": {"kind": "boolean"},
        "outer_margin": {"kind": "number", "minimum": 0.0, "maximum": 10000.0},
        "minimum_neck_width": {"kind": "number", "minimum": 0.1, "maximum": 10000.0},
        "fill_enclosed_gaps": {"kind": "boolean"},
        "smooth_outline": {"kind": "boolean"},
        "smoothing_tolerance": {"kind": "number", "minimum": 0.001, "maximum": 1000.0},
        "output_type": {"kind": "enumeration", "choices": (FORMATION_OUTLINE_ONLY, FORMATION_SOLID_ONLY, FORMATION_BOTH)},
        "board_thickness": {"kind": "number", "minimum": 0.1, "maximum": 1000.0},
        "show_outline": {"kind": "boolean"},
        "show_solid": {"kind": "boolean"},
        "create_track_engraving": {"kind": "boolean"},
        "create_platform_engraving": {"kind": "boolean"},
    }


def _section_configuration_specs():
    return {
        "enabled": {"kind": "boolean"},
        "maximum_section_length": {"kind": "number", "minimum": 0.0, "maximum": 1000000.0},
        "balance_lengths": {"kind": "boolean"},
        "minimum_section_length": {"kind": "number", "minimum": 0.0, "maximum": 1000000.0},
        "section_track_templates": {"kind": "boolean"},
        "section_platform": {"kind": "boolean"},
        "section_formation": {"kind": "boolean"},
        "preserve_unsplit": {"kind": "boolean"},
        "number_in_travel_order": {"kind": "boolean"},
    }


def _registration_configuration_specs():
    return {
        "joint_type": {"kind": "enumeration", "choices": (REGISTRATION_PLAIN, REGISTRATION_HOLES, REGISTRATION_PINS, REGISTRATION_TONGUE)},
        "joint_depth": {"kind": "number", "minimum": 0.1, "maximum": 10000.0},
        "joint_width": {"kind": "number", "minimum": 0.1, "maximum": 10000.0},
        "fit_clearance": {"kind": "number", "minimum": 0.0, "maximum": 100.0},
        "alignment_hole_diameter": {"kind": "number", "minimum": 0.1, "maximum": 1000.0},
        "alignment_hole_offset": {"kind": "number", "minimum": 0.1, "maximum": 10000.0},
    }


def _template_assembly_configuration_specs():
    return {
        "enabled": {"kind": "boolean"},
        "joint_type": {"kind": "enumeration", "choices": (TEMPLATE_JOINT_PLAIN, TEMPLATE_JOINT_PINS, TEMPLATE_JOINT_TONGUE)},
        "joint_depth": {"kind": "number", "minimum": 0.5, "maximum": 10000.0},
        "joint_width": {"kind": "number", "minimum": 0.5, "maximum": 10000.0},
        "fit_clearance": {"kind": "number", "minimum": 0.0, "maximum": 100.0},
        "fixing_holes_enabled": {"kind": "boolean"},
        "holes_per_section": {"kind": "integer", "minimum": 1, "maximum": 20},
        "hole_diameter": {"kind": "number", "minimum": 0.2, "maximum": 1000.0},
        "minimum_end_clearance": {"kind": "number", "minimum": 0.0, "maximum": 100000.0},
        "matching_formation_holes": {"kind": "boolean"},
        "show_hole_geometry": {"kind": "boolean"},
    }


def _assembly_label_configuration_specs():
    return {
        "schema_version": {"kind": "integer", "minimum": ASSEMBLY_LABEL_SCHEMA_VERSION, "maximum": ASSEMBLY_LABEL_SCHEMA_VERSION},
        "enabled": {"kind": "boolean"},
        "label_format": {"kind": "enumeration", "choices": (ASSEMBLY_LABEL_FORMAT_AUTOMATIC, ASSEMBLY_LABEL_FORMAT_CUSTOM)},
        "custom_format": {"kind": "string", "maximum_length": 120, "allow_empty": False},
        "text_height": {"kind": "number", "minimum": 1.0, "maximum": 20.0},
        "stroke_width": {"kind": "number", "minimum": 0.08, "maximum": 2.0},
        "engraving_depth": {"kind": "number", "minimum": 0.05, "maximum": 5.0},
        "edge_margin": {"kind": "number", "minimum": 0.0, "maximum": 50.0},
        "preferred_placement": {"kind": "enumeration", "choices": tuple(ASSEMBLY_LABEL_PLACEMENTS)},
        "include_template_set_id": {"kind": "boolean"},
        "include_track_number": {"kind": "boolean"},
        "include_track_name": {"kind": "boolean"},
        "include_section_number": {"kind": "boolean"},
        "include_travel_order_number": {"kind": "boolean"},
        "include_platform_identity": {"kind": "boolean"},
        "include_formation_identity": {"kind": "boolean"},
    }


def _production_export_configuration_specs():
    return {
        "enabled": {"kind": "boolean"},
        "output_directory": {"kind": "path", "maximum_length": 4096},
        "include_set_identifier": {"kind": "boolean", "fixed_value": True},
        "include_object_role": {"kind": "boolean"},
        "include_track_number": {"kind": "boolean"},
        "include_section_number": {"kind": "boolean"},
        "export_each_section": {"kind": "boolean"},
        "create_combined_files": {"kind": "boolean"},
        "overwrite_existing": {"kind": "boolean"},
        "create_manifest": {"kind": "boolean"},
        "open_output_directory": {"kind": "boolean"},
        "current_template_set_only": {"kind": "boolean", "fixed_value": True},
    }


def _material_report_configuration_specs():
    return {
        "sheet_width": {"kind": "number", "minimum": 1.0, "maximum": 100000.0},
        "sheet_length": {"kind": "number", "minimum": 1.0, "maximum": 100000.0},
        "usable_edge_margin": {"kind": "number", "minimum": 0.0, "maximum": 10000.0},
        "kerf_allowance": {"kind": "number", "minimum": 0.0, "maximum": 1000.0},
        "material_thickness": {"kind": "number", "minimum": 0.0, "maximum": 1000.0},
        "allow_rotation": {"kind": "boolean"},
        "part_spacing": {"kind": "number", "minimum": 0.0, "maximum": 10000.0},
    }


def _validate_boolean_map(source, defaults, path, diagnostics):
    if not isinstance(source, dict):
        _configuration_add_diagnostic(
            diagnostics,
            CONFIGURATION_SEVERITY_ERROR,
            path,
            source,
            "JSON object containing boolean fields",
            "This field must be a JSON object.",
        )
        source = {}
    _configuration_unknown_fields(source, defaults.keys(), path, diagnostics)
    result = {}
    for key, default in defaults.items():
        result[key] = _configuration_field(
            source, key, default, path, diagnostics, "boolean"
        )
    return result


def _validate_configuration_list(source, path, maximum, defaults_factory, specs_factory, clone_function, diagnostics, allow_empty=True):
    if not isinstance(source, list):
        _configuration_add_diagnostic(
            diagnostics,
            CONFIGURATION_SEVERITY_ERROR,
            path,
            source,
            "JSON array",
            "This configuration section must be a JSON array.",
        )
        return []
    if len(source) > maximum:
        _configuration_add_diagnostic(
            diagnostics,
            CONFIGURATION_SEVERITY_ERROR,
            path,
            len(source),
            "At most {} entries".format(maximum),
            "The configuration contains too many entries.",
        )
    if not allow_empty and not source:
        _configuration_add_diagnostic(
            diagnostics,
            CONFIGURATION_SEVERITY_ERROR,
            path,
            source,
            "At least one entry",
            "This configuration list cannot be empty.",
        )
    results = []
    for index, item in enumerate(source[:maximum]):
        defaults = defaults_factory(index)
        if "manager_id" in defaults and not str(defaults.get("manager_id") or "").strip():
            defaults["manager_id"] = "import-{:03d}".format(index + 1)
        if "manager_id" in defaults:
            defaults["manager_id"] = "{}-import-{:03d}".format(
                "platform" if "arrangement" in defaults else "straight",
                index + 1,
            )
        validated = _validate_known_dictionary(
            item,
            defaults,
            specs_factory(),
            "{}[{}]".format(path, index),
            diagnostics,
        )
        try:
            results.append(clone_function(validated, index))
        except TypeError:
            results.append(clone_function(validated))
        except Exception as error:
            _configuration_add_diagnostic(
                diagnostics,
                CONFIGURATION_SEVERITY_ERROR,
                "{}[{}]".format(path, index),
                item,
                "Internally consistent configuration entry",
                str(error),
            )
    return results


def _preset_utc_now():
    return datetime.datetime.utcnow().replace(microsecond=0).isoformat() + "Z"


def _preset_deterministic_id(name, configuration):
    seed = json.dumps(
        {
            "name": str(name or "").strip().casefold(),
            "configuration": configuration if isinstance(configuration, dict) else {},
        },
        ensure_ascii=False,
        sort_keys=True,
        separators=(",", ":"),
    )
    return uuid.uuid5(uuid.NAMESPACE_URL, "model-railway-preset:" + seed).hex


def _preset_timestamp_valid(value):
    return bool(
        isinstance(value, str)
        and re.match(r"^\d{4}-\d{2}-\d{2}T\d{2}:\d{2}:\d{2}Z$", value)
    )


def _mapped_preset_diagnostic(item, preset_path):
    mapped = dict(item)
    field_path = str(mapped.get("field_path", "$"))
    if field_path.startswith("$.configuration"):
        field_path = preset_path + field_path[1:]
    elif field_path == "$.macro_version":
        field_path = preset_path + ".source_macro_version"
    elif field_path == "$.presets":
        field_path = preset_path
    elif field_path.startswith("$.presets"):
        field_path = preset_path + field_path[len("$.presets"):]
    elif field_path == "$":
        field_path = preset_path
    mapped["field_path"] = field_path
    return mapped


def _validate_presets(source, diagnostics, source_macro_version="Unknown"):
    if source is None:
        _configuration_add_diagnostic(
            diagnostics,
            CONFIGURATION_SEVERITY_INFORMATION,
            "$.presets",
            None,
            "JSON array",
            "Optional presets array was absent and received an empty default.",
            "Default applied",
            True,
        )
        return []
    if not isinstance(source, list):
        _configuration_add_diagnostic(
            diagnostics,
            CONFIGURATION_SEVERITY_ERROR,
            "$.presets",
            source,
            "JSON array",
            "Presets must be transported as an array.",
        )
        return []
    if len(source) > CONFIGURATION_MAX_PRESETS:
        _configuration_add_diagnostic(
            diagnostics,
            CONFIGURATION_SEVERITY_ERROR,
            "$.presets",
            len(source),
            "At most {} preset records".format(CONFIGURATION_MAX_PRESETS),
            "The preset transport array is too large.",
        )

    result = []
    seen_ids = set()
    seen_names = set()
    for index, original in enumerate(source[:CONFIGURATION_MAX_PRESETS]):
        path = "$.presets[{}]".format(index)
        if not isinstance(original, dict):
            _configuration_add_diagnostic(
                diagnostics,
                CONFIGURATION_SEVERITY_ERROR,
                path,
                original,
                "JSON object",
                "Each transported preset must be a JSON object.",
            )
            continue

        item = _configuration_json_copy(original)
        if "configuration" not in item and isinstance(item.get("payload"), dict):
            payload = item.pop("payload")
            if isinstance(payload.get("configuration"), dict):
                item["configuration"] = payload["configuration"]
            else:
                item["configuration"] = payload
            _configuration_add_diagnostic(
                diagnostics,
                CONFIGURATION_SEVERITY_WARNING,
                path + ".configuration",
                "payload",
                "configuration object",
                "A legacy preset payload field was converted.",
                "payload -> configuration",
            )
        if "preset_schema_version" not in item and "schema_version" in item:
            item["preset_schema_version"] = item.pop("schema_version")
            _configuration_add_diagnostic(
                diagnostics,
                CONFIGURATION_SEVERITY_WARNING,
                path + ".preset_schema_version",
                original.get("schema_version"),
                "Preset schema version {}".format(PRESET_RECORD_SCHEMA_VERSION),
                "A legacy preset schema field was converted.",
                "schema_version -> preset_schema_version",
            )

        allowed = {
            "preset_schema_version", "preset_id", "name", "description",
            "created_utc", "modified_utc", "source_macro_version", "configuration",
        }
        _configuration_unknown_fields(item, allowed, path, diagnostics)

        schema = item.get("preset_schema_version", PRESET_RECORD_SCHEMA_VERSION)
        if schema != PRESET_RECORD_SCHEMA_VERSION:
            _configuration_add_diagnostic(
                diagnostics,
                CONFIGURATION_SEVERITY_ERROR,
                path + ".preset_schema_version",
                schema,
                "Preset schema version {}".format(PRESET_RECORD_SCHEMA_VERSION),
                "This named-preset schema is unsupported.",
            )

        raw_name = item.get("name")
        name = str(raw_name or "").strip() if isinstance(raw_name, str) else ""
        if not name or len(name) > PRESET_MAX_NAME_LENGTH:
            _configuration_add_diagnostic(
                diagnostics,
                CONFIGURATION_SEVERITY_ERROR,
                path + ".name",
                raw_name,
                "Non-empty string of at most {} characters".format(PRESET_MAX_NAME_LENGTH),
                "A preset requires a concise unique name.",
            )
        elif name != raw_name:
            _configuration_add_diagnostic(
                diagnostics,
                CONFIGURATION_SEVERITY_INFORMATION,
                path + ".name",
                raw_name,
                "Trimmed preset name",
                "Leading or trailing whitespace was removed.",
                "Whitespace trimmed",
            )

        raw_description = item.get("description", "")
        description = str(raw_description) if isinstance(raw_description, str) else ""
        if not isinstance(raw_description, str) or len(description) > PRESET_MAX_DESCRIPTION_LENGTH:
            _configuration_add_diagnostic(
                diagnostics,
                CONFIGURATION_SEVERITY_ERROR,
                path + ".description",
                raw_description,
                "String of at most {} characters".format(PRESET_MAX_DESCRIPTION_LENGTH),
                "The preset description is invalid.",
            )

        configuration = item.get("configuration")
        normalised_configuration = None
        if not isinstance(configuration, dict):
            _configuration_add_diagnostic(
                diagnostics,
                CONFIGURATION_SEVERITY_ERROR,
                path + ".configuration",
                configuration,
                "Complete configuration object",
                "A named preset must contain one complete reusable configuration snapshot.",
            )
        else:
            nested = validate_configuration_payload({
                "schema_version": CONFIGURATION_SCHEMA_VERSION,
                "macro_version": str(item.get("source_macro_version") or source_macro_version or "Unknown"),
                "configuration": configuration,
                "presets": [],
            })
            for nested_item in nested.get("diagnostics", []):
                diagnostics.append(_mapped_preset_diagnostic(nested_item, path))
            if nested.get("valid"):
                normalised_configuration = nested["payload"]["configuration"]

        supplied_id = item.get("preset_id")
        preset_id = str(supplied_id or "").strip() if isinstance(supplied_id, str) else ""
        if not preset_id:
            preset_id = _preset_deterministic_id(name, configuration)
            _configuration_add_diagnostic(
                diagnostics,
                CONFIGURATION_SEVERITY_INFORMATION,
                path + ".preset_id",
                supplied_id,
                "Stable preset identifier",
                "A stable identifier was generated for this recognised legacy preset.",
                "Deterministic identifier generated",
                True,
            )
        elif not re.match(r"^[A-Za-z0-9._-]{8,80}$", preset_id):
            _configuration_add_diagnostic(
                diagnostics,
                CONFIGURATION_SEVERITY_ERROR,
                path + ".preset_id",
                supplied_id,
                "8 to 80 letters, numbers, dots, underscores or hyphens",
                "The preset identifier is unsafe or malformed.",
            )

        source_version = item.get("source_macro_version", source_macro_version or "Unknown")
        if not isinstance(source_version, str) or not source_version.strip() or len(source_version) > 80:
            _configuration_add_diagnostic(
                diagnostics,
                CONFIGURATION_SEVERITY_ERROR,
                path + ".source_macro_version",
                source_version,
                "Non-empty string of at most 80 characters",
                "The preset source macro version is invalid.",
            )
            source_version = "Unknown"
        else:
            source_version = source_version.strip()

        created_missing = "created_utc" not in item
        modified_missing = "modified_utc" not in item
        created = item.get("created_utc", PRESET_TIMESTAMP_FALLBACK)
        modified = item.get("modified_utc", created)
        if created_missing:
            _configuration_add_diagnostic(
                diagnostics,
                CONFIGURATION_SEVERITY_INFORMATION,
                path + ".created_utc",
                None,
                "UTC timestamp YYYY-MM-DDTHH:MM:SSZ",
                "A deterministic legacy creation timestamp was applied.",
                "Default applied",
                True,
            )
        if modified_missing:
            _configuration_add_diagnostic(
                diagnostics,
                CONFIGURATION_SEVERITY_INFORMATION,
                path + ".modified_utc",
                None,
                "UTC timestamp YYYY-MM-DDTHH:MM:SSZ",
                "The legacy modification timestamp was set to the creation timestamp.",
                "Default applied",
                True,
            )
        if not _preset_timestamp_valid(created):
            _configuration_add_diagnostic(
                diagnostics,
                CONFIGURATION_SEVERITY_ERROR,
                path + ".created_utc",
                created,
                "UTC timestamp YYYY-MM-DDTHH:MM:SSZ",
                "The preset creation timestamp is invalid.",
            )
        if not _preset_timestamp_valid(modified):
            _configuration_add_diagnostic(
                diagnostics,
                CONFIGURATION_SEVERITY_ERROR,
                path + ".modified_utc",
                modified,
                "UTC timestamp YYYY-MM-DDTHH:MM:SSZ",
                "The preset modification timestamp is invalid.",
            )

        name_key = name.casefold()
        if preset_id and preset_id in seen_ids:
            _configuration_add_diagnostic(
                diagnostics,
                CONFIGURATION_SEVERITY_ERROR,
                path + ".preset_id",
                preset_id,
                "Unique preset identifier",
                "Two presets use the same identifier.",
            )
        if name_key and name_key in seen_names:
            _configuration_add_diagnostic(
                diagnostics,
                CONFIGURATION_SEVERITY_ERROR,
                path + ".name",
                name,
                "Unique preset name",
                "Preset names must be unique without regard to letter case.",
            )
        seen_ids.add(preset_id)
        seen_names.add(name_key)

        result.append({
            "preset_schema_version": PRESET_RECORD_SCHEMA_VERSION,
            "preset_id": preset_id,
            "name": name,
            "description": description,
            "created_utc": created,
            "modified_utc": modified,
            "source_macro_version": source_version,
            "configuration": (
                normalised_configuration
                if normalised_configuration is not None
                else _configuration_json_copy(configuration if isinstance(configuration, dict) else {})
            ),
        })
    return result


def validate_configuration_payload(payload):
    migrated, diagnostics = migrate_configuration_payload(payload)
    if migrated is None:
        return {
            "valid": False,
            "blocked": True,
            "payload": None,
            "diagnostics": diagnostics,
        }

    allowed_root = {"schema_version", "macro_version", "configuration", "presets"}
    _configuration_unknown_fields(migrated, allowed_root, "$", diagnostics)

    macro_version = migrated.get("macro_version")
    if not isinstance(macro_version, str) or not macro_version.strip():
        _configuration_add_diagnostic(
            diagnostics,
            CONFIGURATION_SEVERITY_ERROR,
            "$.macro_version",
            macro_version,
            "Non-empty string",
            "The source macro version is required for traceability.",
        )
        macro_version = "Unknown"
    configuration = migrated.get("configuration")
    if not isinstance(configuration, dict):
        _configuration_add_diagnostic(
            diagnostics,
            CONFIGURATION_SEVERITY_ERROR,
            "$.configuration",
            configuration,
            "JSON object",
            "The configuration field is required.",
        )
        configuration = {}
    _configuration_unknown_fields(
        configuration, CONFIGURATION_REQUIRED_SECTIONS, "$.configuration", diagnostics
    )
    for section in CONFIGURATION_REQUIRED_SECTIONS:
        if section not in configuration or configuration.get(section) is None:
            _configuration_add_diagnostic(
                diagnostics,
                CONFIGURATION_SEVERITY_ERROR,
                "$.configuration.{}".format(section),
                configuration.get(section),
                "Required configuration section",
                "The required configuration section is missing.",
            )

    curve_defaults = {
        "transition": DEFAULT_TRANSITION_LENGTH,
        "radius": DEFAULT_RADIUS,
        "angle": DEFAULT_TURN_ANGLE,
        "main_width": DEFAULT_MAIN_TEMPLATE_WIDTH,
    }
    curve = _validate_known_dictionary(
        configuration.get("curve", {}),
        curve_defaults,
        _curve_configuration_specs(),
        "$.configuration.curve",
        diagnostics,
    )
    if curve["radius"] <= 0.5 * curve["main_width"]:
        _configuration_add_diagnostic(
            diagnostics,
            CONFIGURATION_SEVERITY_ERROR,
            "$.configuration.curve.radius",
            curve["radius"],
            "Greater than half the main template width",
            "The main template strip would fold across the curve centre.",
        )

    tracks = _validate_configuration_list(
        configuration.get("tracks", []),
        "$.configuration.tracks",
        MAX_PARALLEL_TRACKS,
        lambda index: default_track_config(index, curve["transition"]),
        _track_configuration_specs,
        lambda item, index: clone_track_config(item, curve["transition"]),
        diagnostics,
        allow_empty=True,
    )
    total_curve_tracks = 1 + len(tracks)
    for index, track in enumerate(tracks):
        if track["side"] == "Inside" and track["curve_spacing"] >= curve["radius"]:
            _configuration_add_diagnostic(
                diagnostics,
                CONFIGURATION_SEVERITY_ERROR,
                "$.configuration.tracks[{}].curve_spacing".format(index),
                track["curve_spacing"],
                "Less than the main curve radius for an inside track",
                "The requested inside constant radius would be zero or negative.",
            )

    straight_routes = _validate_configuration_list(
        configuration.get("straight_routes", []),
        "$.configuration.straight_routes",
        MAX_STRAIGHT_ROUTES,
        default_straight_config,
        _straight_configuration_specs,
        clone_straight_config,
        diagnostics,
        allow_empty=True,
    )
    for index, route in enumerate(straight_routes):
        if route["connection_mode"] != STRAIGHT_CONNECTION_INDEPENDENT and route["track_count"] != total_curve_tracks:
            _configuration_add_diagnostic(
                diagnostics,
                CONFIGURATION_SEVERITY_ERROR,
                "$.configuration.straight_routes[{}].track_count".format(index),
                route["track_count"],
                "{} for a curve-connected route".format(total_curve_tracks),
                "Connected routes must inherit every generated curve track.",
            )

    platforms = _validate_configuration_list(
        configuration.get("platforms", []),
        "$.configuration.platforms",
        MAX_PLATFORMS,
        lambda index: default_platform_config(),
        _platform_configuration_specs,
        lambda item, index: clone_platform_config(item),
        diagnostics,
        allow_empty=False,
    )
    platform_names = set()
    for index, platform in enumerate(platforms):
        name_key = platform["name"].casefold()
        if name_key in platform_names:
            _configuration_add_diagnostic(
                diagnostics,
                CONFIGURATION_SEVERITY_ERROR,
                "$.configuration.platforms[{}].name".format(index),
                platform["name"],
                "Unique platform name",
                "Platform names must be unique.",
            )
        platform_names.add(name_key)
        for field in ("track_a_index", "track_b_index"):
            if platform["enabled"] and platform[field] >= total_curve_tracks:
                _configuration_add_diagnostic(
                    diagnostics,
                    CONFIGURATION_SEVERITY_ERROR,
                    "$.configuration.platforms[{}].{}".format(index, field),
                    platform[field],
                    "Track index from 0 to {}".format(total_curve_tracks - 1),
                    "The selected platform track does not exist in this configuration.",
                )
        if (
            platform["enabled"]
            and platform["arrangement"] == PLATFORM_BETWEEN
            and platform["track_a_index"] == platform["track_b_index"]
        ):
            _configuration_add_diagnostic(
                diagnostics,
                CONFIGURATION_SEVERITY_ERROR,
                "$.configuration.platforms[{}]".format(index),
                {"track_a_index": platform["track_a_index"], "track_b_index": platform["track_b_index"]},
                "Two different tracks for a between-track platform",
                "A between-track platform cannot use the same track on both sides.",
            )

    formation = _validate_known_dictionary(
        configuration.get("formation_board", {}),
        default_formation_config(),
        _formation_configuration_specs(),
        "$.configuration.formation_board",
        diagnostics,
    )
    formation = clone_formation_config(formation)

    sectioning = _validate_known_dictionary(
        configuration.get("sectioning", {}),
        default_section_config(),
        _section_configuration_specs(),
        "$.configuration.sectioning",
        diagnostics,
    )
    sectioning = clone_section_config(sectioning)
    if sectioning["enabled"] and sectioning["maximum_section_length"] <= 0.0:
        _configuration_add_diagnostic(
            diagnostics,
            CONFIGURATION_SEVERITY_ERROR,
            "$.configuration.sectioning.maximum_section_length",
            sectioning["maximum_section_length"],
            "Greater than zero when sectioning is enabled",
            "Enabled sectioning requires a maximum section length.",
        )
    if (
        sectioning["enabled"]
        and sectioning["minimum_section_length"] > sectioning["maximum_section_length"]
        and sectioning["maximum_section_length"] > 0.0
    ):
        _configuration_add_diagnostic(
            diagnostics,
            CONFIGURATION_SEVERITY_ERROR,
            "$.configuration.sectioning.minimum_section_length",
            sectioning["minimum_section_length"],
            "No greater than maximum_section_length",
            "The minimum section length exceeds the maximum section length.",
        )

    registration = _validate_known_dictionary(
        configuration.get("registration", {}),
        default_registration_config(),
        _registration_configuration_specs(),
        "$.configuration.registration",
        diagnostics,
    )
    registration = clone_registration_config(registration)

    template_joints = _validate_known_dictionary(
        configuration.get("template_joints", {}),
        default_template_assembly_config(),
        _template_assembly_configuration_specs(),
        "$.configuration.template_joints",
        diagnostics,
    )
    template_joints = clone_template_assembly_config(template_joints)

    assembly_labels = _validate_known_dictionary(
        configuration.get("assembly_labels", {}),
        default_assembly_label_config(),
        _assembly_label_configuration_specs(),
        "$.configuration.assembly_labels",
        diagnostics,
    )
    if assembly_labels["stroke_width"] > assembly_labels["text_height"] / 7.0:
        _configuration_add_diagnostic(
            diagnostics,
            CONFIGURATION_SEVERITY_ERROR,
            "$.configuration.assembly_labels.stroke_width",
            assembly_labels["stroke_width"],
            "No greater than text_height / 7",
            "The engraving stroke is too wide for the internal lettering cell size.",
        )
    if not any(item["blocks_import"] and item["field_path"].startswith("$.configuration.assembly_labels") for item in diagnostics):
        try:
            assembly_labels = validate_assembly_label_config(assembly_labels)
        except Exception as error:
            _configuration_add_diagnostic(
                diagnostics,
                CONFIGURATION_SEVERITY_ERROR,
                "$.configuration.assembly_labels",
                assembly_labels,
                "Valid assembly-label configuration",
                str(error),
            )

    production_source = configuration.get("production_export", {})
    production_defaults = default_production_export_config()
    production_specs = _production_export_configuration_specs()
    production_base_source = (
        {key: value for key, value in production_source.items() if key not in ("formats", "selections")}
        if isinstance(production_source, dict)
        else production_source
    )
    production_export = _validate_known_dictionary(
        production_base_source,
        production_defaults,
        production_specs,
        "$.configuration.production_export",
        diagnostics,
    )
    if isinstance(production_source, dict):
        _configuration_unknown_fields(
            production_source,
            set(production_specs) | {"formats", "selections"},
            "$.configuration.production_export",
            diagnostics,
        )
    if not isinstance(production_source, dict):
        production_source = {}
    production_export["formats"] = _validate_boolean_map(
        production_source.get("formats", {}),
        production_defaults["formats"],
        "$.configuration.production_export.formats",
        diagnostics,
    )
    production_export["selections"] = _validate_boolean_map(
        production_source.get("selections", {}),
        production_defaults["selections"],
        "$.configuration.production_export.selections",
        diagnostics,
    )
    production_export = clone_production_export_config(production_export)
    if production_export["enabled"] and not production_export["output_directory"]:
        _configuration_add_diagnostic(
            diagnostics,
            CONFIGURATION_SEVERITY_ERROR,
            "$.configuration.production_export.output_directory",
            production_export["output_directory"],
            "Non-empty directory when production export is enabled",
            "Production export cannot be enabled without an output directory.",
        )

    material_report = _validate_known_dictionary(
        configuration.get("material_report", {}),
        default_material_report_config(),
        _material_report_configuration_specs(),
        "$.configuration.material_report",
        diagnostics,
    )
    if not any(item["blocks_import"] and item["field_path"].startswith("$.configuration.material_report") for item in diagnostics):
        try:
            material_report = validate_material_report_config(material_report)
        except Exception as error:
            _configuration_add_diagnostic(
                diagnostics,
                CONFIGURATION_SEVERITY_ERROR,
                "$.configuration.material_report",
                material_report,
                "Valid material and sheet settings",
                str(error),
            )

    utilities_defaults = {"output_mode": OUTPUT_REPLACE}
    production_utilities = _validate_known_dictionary(
        configuration.get("production_utilities", {}),
        utilities_defaults,
        {
            "output_mode": {
                "kind": "enumeration",
                "choices": (OUTPUT_REPLACE, OUTPUT_CREATE_NEW),
            }
        },
        "$.configuration.production_utilities",
        diagnostics,
    )

    presets = _validate_presets(migrated.get("presets"), diagnostics, macro_version)
    normalised = {
        "schema_version": CONFIGURATION_SCHEMA_VERSION,
        "macro_version": str(macro_version),
        "configuration": {
            "curve": curve,
            "tracks": tracks,
            "platforms": platforms,
            "straight_routes": straight_routes,
            "formation_board": formation,
            "sectioning": sectioning,
            "registration": registration,
            "template_joints": template_joints,
            "assembly_labels": assembly_labels,
            "production_export": production_export,
            "material_report": material_report,
            "production_utilities": production_utilities,
        },
        "presets": presets,
    }
    blocked = any(item["blocks_import"] for item in diagnostics)
    return {
        "valid": not blocked,
        "blocked": blocked,
        "payload": None if blocked else normalised,
        "diagnostics": diagnostics,
    }


def normalise_configuration_payload(payload):
    result = validate_configuration_payload(payload)
    if result["blocked"]:
        messages = [
            "{}: {}".format(item["field_path"], item["message"])
            for item in result["diagnostics"]
            if item["blocks_import"]
        ]
        raise ValueError("Configuration validation failed:\n{}".format("\n".join(messages)))
    return result["payload"]


def configuration_diagnostics(payload):
    return validate_configuration_payload(payload)["diagnostics"]


def build_complete_configuration_payload(
    transition,
    radius,
    angle,
    main_width,
    track_configs,
    straight_configs,
    platform_configs,
    formation_config,
    section_config,
    registration_config,
    template_assembly_config,
    assembly_label_config,
    production_export_config,
    material_report_config,
    output_mode,
    presets=None,
):
    payload = {
        "schema_version": CONFIGURATION_SCHEMA_VERSION,
        "macro_version": MACRO_VERSION_NUMBER,
        "configuration": {
            "curve": {
                "transition": float(transition),
                "radius": float(radius),
                "angle": float(angle),
                "main_width": float(main_width),
            },
            "tracks": [
                clone_track_config(item, transition) for item in track_configs
            ],
            "platforms": clone_platform_configs(platform_configs),
            "straight_routes": clone_straight_configs(straight_configs),
            "formation_board": clone_formation_config(formation_config),
            "sectioning": clone_section_config(section_config),
            "registration": clone_registration_config(registration_config),
            "template_joints": clone_template_assembly_config(template_assembly_config),
            "assembly_labels": validate_assembly_label_config(assembly_label_config),
            "production_export": clone_production_export_config(production_export_config),
            "material_report": validate_material_report_config(material_report_config),
            "production_utilities": {
                "output_mode": (
                    output_mode
                    if output_mode in (OUTPUT_REPLACE, OUTPUT_CREATE_NEW)
                    else OUTPUT_REPLACE
                )
            },
        },
        "presets": _configuration_json_copy(presets or []),
    }
    return normalise_configuration_payload(payload)


def _configuration_flatten(value, path="$", result=None):
    result = result if result is not None else {}
    if isinstance(value, dict):
        if not value:
            result[path] = {}
        for key in sorted(value):
            child_path = "{}.{}".format(path, key) if path != "$" else "$.{}".format(key)
            _configuration_flatten(value[key], child_path, result)
    elif isinstance(value, list):
        if not value:
            result[path] = []
        for index, child in enumerate(value):
            _configuration_flatten(child, "{}[{}]".format(path, index), result)
    else:
        result[path] = value
    return result


def configuration_change_summary(current_payload, imported_payload):
    current = normalise_configuration_payload(current_payload)
    imported = normalise_configuration_payload(imported_payload)
    current_flat = _configuration_flatten(current.get("configuration", {}), "$.configuration")
    imported_flat = _configuration_flatten(imported.get("configuration", {}), "$.configuration")
    changes = []
    for path in sorted(set(current_flat) | set(imported_flat)):
        before = current_flat.get(path, "<absent>")
        after = imported_flat.get(path, "<absent>")
        if before != after:
            changes.append({
                "field_path": path,
                "current_value": _configuration_json_copy(before),
                "imported_value": _configuration_json_copy(after),
            })
    return changes


def configuration_summary(payload):
    normalised = normalise_configuration_payload(payload)
    config = normalised["configuration"]
    curve = config["curve"]
    enabled_platforms = sum(1 for item in config["platforms"] if item.get("enabled"))
    enabled_straights = sum(1 for item in config["straight_routes"] if item.get("enabled"))
    enabled_labels = bool(config["assembly_labels"].get("enabled"))
    enabled_export = bool(config["production_export"].get("enabled"))
    lines = [
        "Schema version: {}".format(normalised["schema_version"]),
        "Source macro version: {}".format(normalised["macro_version"]),
        "Curve: transition {:.3f} mm; radius {:.3f} mm; angle {:.3f} deg; width {:.3f} mm".format(
            curve["transition"], curve["radius"], curve["angle"], curve["main_width"]
        ),
        "Curve tracks: {} total ({} additional)".format(1 + len(config["tracks"]), len(config["tracks"])),
        "Straight routes: {} defined; {} enabled".format(len(config["straight_routes"]), enabled_straights),
        "Platforms: {} defined; {} enabled".format(len(config["platforms"]), enabled_platforms),
        "Formation board: {}".format("enabled" if config["formation_board"].get("enabled") else "disabled"),
        "Sectioning: {}".format("enabled" if config["sectioning"].get("enabled") else "disabled"),
        "Template joints and holes: {}".format("enabled" if config["template_joints"].get("enabled") else "disabled"),
        "Assembly labels: {}".format("enabled" if enabled_labels else "disabled"),
        "Production export: {}".format("enabled" if enabled_export else "disabled"),
        "Output behaviour: {}".format(config["production_utilities"]["output_mode"]),
        "Transported presets: {}".format(len(normalised.get("presets", []))),
    ]
    return "\n".join(lines)


def export_configuration_json_atomic(path, payload, overwrite=False):
    normalised = normalise_configuration_payload(payload)
    target = os.path.abspath(os.path.expanduser(str(path or "").strip()))
    if not target.lower().endswith(".json"):
        target += ".json"
    directory = os.path.dirname(target)
    if not os.path.isdir(directory):
        raise ValueError("The selected configuration directory does not exist: {}".format(directory))
    if os.path.exists(target) and not overwrite:
        raise FileExistsError("The configuration file already exists: {}".format(target))
    serialised = json.dumps(
        normalised,
        ensure_ascii=False,
        indent=2,
        sort_keys=True,
        allow_nan=False,
    ) + "\n"
    temporary_path = None
    try:
        with tempfile.NamedTemporaryFile(
            mode="w",
            encoding="utf-8",
            newline="\n",
            prefix=".railway_configuration_",
            suffix=".tmp",
            dir=directory,
            delete=False,
        ) as handle:
            temporary_path = handle.name
            handle.write(serialised)
            handle.flush()
            os.fsync(handle.fileno())
        os.replace(temporary_path, target)
        temporary_path = None
        try:
            directory_fd = os.open(directory, os.O_RDONLY)
            try:
                os.fsync(directory_fd)
            finally:
                os.close(directory_fd)
        except Exception:
            pass
        return target
    finally:
        if temporary_path and os.path.exists(temporary_path):
            try:
                os.remove(temporary_path)
            except Exception:
                pass


def import_configuration_json(path):
    source_path = os.path.abspath(os.path.expanduser(str(path or "").strip()))
    diagnostics = []
    if not source_path.lower().endswith(".json"):
        _configuration_add_diagnostic(
            diagnostics,
            CONFIGURATION_SEVERITY_ERROR,
            "$",
            source_path,
            "File with .json extension",
            "Configuration import accepts JSON files only.",
        )
        return {"valid": False, "blocked": True, "payload": None, "diagnostics": diagnostics, "path": source_path}
    if not os.path.isfile(source_path):
        _configuration_add_diagnostic(
            diagnostics,
            CONFIGURATION_SEVERITY_ERROR,
            "$",
            source_path,
            "Existing JSON file",
            "The selected configuration file does not exist.",
        )
        return {"valid": False, "blocked": True, "payload": None, "diagnostics": diagnostics, "path": source_path}
    try:
        file_size = os.path.getsize(source_path)
    except OSError as error:
        _configuration_add_diagnostic(
            diagnostics,
            CONFIGURATION_SEVERITY_ERROR,
            "$",
            source_path,
            "Readable JSON file",
            str(error),
        )
        return {"valid": False, "blocked": True, "payload": None, "diagnostics": diagnostics, "path": source_path}
    if file_size > CONFIGURATION_MAX_FILE_SIZE:
        _configuration_add_diagnostic(
            diagnostics,
            CONFIGURATION_SEVERITY_ERROR,
            "$",
            file_size,
            "File no larger than {} bytes".format(CONFIGURATION_MAX_FILE_SIZE),
            "The configuration file is unexpectedly large.",
        )
        return {"valid": False, "blocked": True, "payload": None, "diagnostics": diagnostics, "path": source_path}
    try:
        with open(source_path, "r", encoding="utf-8-sig") as handle:
            decoded = json.load(handle)
    except json.JSONDecodeError as error:
        _configuration_add_diagnostic(
            diagnostics,
            CONFIGURATION_SEVERITY_ERROR,
            "$",
            "line {}, column {}".format(error.lineno, error.colno),
            "Valid JSON",
            "Invalid JSON: {}".format(error.msg),
        )
        return {"valid": False, "blocked": True, "payload": None, "diagnostics": diagnostics, "path": source_path}
    except Exception as error:
        _configuration_add_diagnostic(
            diagnostics,
            CONFIGURATION_SEVERITY_ERROR,
            "$",
            source_path,
            "Readable JSON file",
            str(error),
        )
        return {"valid": False, "blocked": True, "payload": None, "diagnostics": diagnostics, "path": source_path}
    result = validate_configuration_payload(decoded)
    result["path"] = source_path
    return result



def validate_named_preset_collection(presets):
    diagnostics = []
    normalised = _validate_presets(presets, diagnostics, MACRO_VERSION_NUMBER)
    blocked = any(item.get("blocks_import") for item in diagnostics)
    return {
        "valid": not blocked,
        "blocked": blocked,
        "presets": None if blocked else normalised,
        "diagnostics": diagnostics,
    }


def normalise_named_preset_collection(presets):
    result = validate_named_preset_collection(presets)
    if result["blocked"]:
        messages = [
            "{}: {}".format(item.get("field_path"), item.get("message"))
            for item in result["diagnostics"]
            if item.get("blocks_import")
        ]
        raise ValueError("Named preset validation failed:\n{}".format("\n".join(messages)))
    return result["presets"]


def build_named_preset(name, description, payload, preset_id=None, created_utc=None):
    normalised_payload = normalise_configuration_payload(payload)
    now = _preset_utc_now()
    record = {
        "preset_schema_version": PRESET_RECORD_SCHEMA_VERSION,
        "preset_id": str(preset_id or uuid.uuid4().hex),
        "name": str(name or "").strip(),
        "description": str(description or ""),
        "created_utc": str(created_utc or now),
        "modified_utc": now,
        "source_macro_version": MACRO_VERSION_NUMBER,
        "configuration": _configuration_json_copy(normalised_payload["configuration"]),
    }
    return normalise_named_preset_collection([record])[0]


def preset_configuration_payload(preset, presets=None):
    validated = normalise_named_preset_collection([preset])[0]
    return normalise_configuration_payload({
        "schema_version": CONFIGURATION_SCHEMA_VERSION,
        "macro_version": validated["source_macro_version"],
        "configuration": _configuration_json_copy(validated["configuration"]),
        "presets": _configuration_json_copy(presets or []),
    })


def _unique_preset_name(name, occupied_names):
    base = str(name or "Preset").strip() or "Preset"
    occupied = {str(item).casefold() for item in occupied_names}
    if base.casefold() not in occupied:
        return base[:PRESET_MAX_NAME_LENGTH]
    counter = 2
    while True:
        suffix = " ({})".format(counter)
        candidate = base[: max(1, PRESET_MAX_NAME_LENGTH - len(suffix))] + suffix
        if candidate.casefold() not in occupied:
            return candidate
        counter += 1


def merge_named_preset_collections(existing, incoming):
    merged = normalise_named_preset_collection(existing or [])
    additions = normalise_named_preset_collection(incoming or [])
    report = {"added": 0, "renamed": 0, "skipped_identical": 0, "identifier_replaced": 0}
    ids = {item["preset_id"] for item in merged}
    names = {item["name"].casefold() for item in merged}
    for original in additions:
        item = _configuration_json_copy(original)
        identical = next(
            (
                current for current in merged
                if current["name"].casefold() == item["name"].casefold()
                and current["configuration"] == item["configuration"]
                and current.get("description", "") == item.get("description", "")
            ),
            None,
        )
        if identical is not None:
            report["skipped_identical"] += 1
            continue
        if item["preset_id"] in ids:
            item["preset_id"] = uuid.uuid4().hex
            item["created_utc"] = _preset_utc_now()
            item["modified_utc"] = item["created_utc"]
            report["identifier_replaced"] += 1
        if item["name"].casefold() in names:
            item["name"] = _unique_preset_name(item["name"] + " imported", names)
            item["modified_utc"] = _preset_utc_now()
            report["renamed"] += 1
        merged.append(item)
        ids.add(item["preset_id"])
        names.add(item["name"].casefold())
        report["added"] += 1
    return normalise_named_preset_collection(merged), report


def load_named_preset_library():
    diagnostics = []
    try:
        group = App.ParamGet(LAST_INPUTS_PARAMETER_PATH)
        stored = str(group.GetString(PRESET_LIBRARY_PARAMETER_KEY, "") or "")
    except Exception as error:
        return {"valid": False, "presets": [], "diagnostics": [], "message": str(error)}
    if not stored:
        return {"valid": True, "presets": [], "diagnostics": [], "message": "No saved preset library."}
    try:
        decoded = json.loads(stored)
    except Exception as error:
        return {"valid": False, "presets": [], "diagnostics": [], "message": "The saved preset library is not valid JSON: {}".format(error)}
    if isinstance(decoded, list):
        presets_source = decoded
        diagnostics.append(_configuration_diagnostic(
            CONFIGURATION_SEVERITY_INFORMATION,
            "$.library_schema_version",
            None,
            "Preset library schema {}".format(PRESET_LIBRARY_SCHEMA_VERSION),
            "A legacy preset array was migrated in memory.",
            "Legacy array -> library object",
        ))
    elif isinstance(decoded, dict):
        schema = decoded.get("library_schema_version")
        if schema != PRESET_LIBRARY_SCHEMA_VERSION:
            return {
                "valid": False,
                "presets": [],
                "diagnostics": diagnostics,
                "message": "Unsupported preset library schema: {}".format(schema),
            }
        presets_source = decoded.get("presets", [])
    else:
        return {"valid": False, "presets": [], "diagnostics": diagnostics, "message": "The saved preset library root is invalid."}
    result = validate_named_preset_collection(presets_source)
    diagnostics.extend(result["diagnostics"])
    if result["blocked"]:
        return {"valid": False, "presets": [], "diagnostics": diagnostics, "message": "The saved preset library failed validation."}
    return {"valid": True, "presets": result["presets"], "diagnostics": diagnostics, "message": "Loaded {} saved preset(s).".format(len(result["presets"]))}


def read_named_preset_library():
    result = load_named_preset_library()
    return _configuration_json_copy(result["presets"] if result.get("valid") else [])


def write_named_preset_library(presets):
    normalised = normalise_named_preset_collection(presets)
    payload = {
        "library_schema_version": PRESET_LIBRARY_SCHEMA_VERSION,
        "macro_version": MACRO_VERSION_NUMBER,
        "presets": normalised,
    }
    serialised = json.dumps(payload, ensure_ascii=False, sort_keys=True, allow_nan=False)
    if len(serialised.encode("utf-8")) > CONFIGURATION_MAX_FILE_SIZE:
        raise ValueError("The preset library exceeds the safe configuration size limit.")
    group = App.ParamGet(LAST_INPUTS_PARAMETER_PATH)
    previous = str(group.GetString(PRESET_LIBRARY_PARAMETER_KEY, "") or "")
    try:
        group.SetString(PRESET_LIBRARY_PARAMETER_KEY, serialised)
        verified = str(group.GetString(PRESET_LIBRARY_PARAMETER_KEY, "") or "")
        if verified != serialised:
            raise IOError("FreeCAD did not verify the complete preset-library write.")
    except Exception:
        try:
            group.SetString(PRESET_LIBRARY_PARAMETER_KEY, previous)
        except Exception:
            pass
        raise
    return _configuration_json_copy(normalised)

def store_pending_imported_configuration(payload):
    global _PENDING_IMPORTED_CONFIGURATION
    _PENDING_IMPORTED_CONFIGURATION = normalise_configuration_payload(payload)
    return _configuration_json_copy(_PENDING_IMPORTED_CONFIGURATION)


def pending_imported_configuration():
    if _PENDING_IMPORTED_CONFIGURATION is None:
        return None
    return _configuration_json_copy(_PENDING_IMPORTED_CONFIGURATION)


def apply_configuration_to_dialog(dialog, payload):
    if dialog is None or not hasattr(dialog, "apply_configuration_payload"):
        return store_pending_imported_configuration(payload)
    dialog.apply_configuration_payload(payload)
    return normalise_configuration_payload(payload)


class CurveInputDialog(QtWidgets.QDialog):
    STRAIGHT_COLUMNS = {
        "enabled": 0,
        "name": 1,
        "connection": 2,
        "length": 3,
        "direction": 4,
        "track_count": 5,
        "spacing": 6,
        "side": 7,
        "width": 8,
        "thickness": 9,
        "start_x": 10,
        "start_y": 11,
        "rotation": 12,
        "template": 13,
        "centreline": 14,
    }

    COLUMNS = {
        "name": 0,
        "side": 1,
        "mode": 2,
        "start": 3,
        "curve": 4,
        "finish": 5,
        "entry_transition": 6,
        "exit_transition": 7,
        "width": 8,
        "template": 9,
        "centreline": 10,
    }

    def __init__(
        self,
        transition,
        radius,
        angle,
        main_width,
        track_configs,
        straight_configs,
        selected_straight_index,
        platform_configs,
        selected_platform_id,
        selected_platform_index,
        formation_config,
        section_config,
        registration_config,
        template_assembly_config,
        assembly_label_config,
        production_export_config,
        material_report_config,
        exporter_capabilities,
        generated_set_count,
        parent=None,
    ):
        super(CurveInputDialog, self).__init__(parent)
        self.setWindowTitle("Model Railway Curve Template - {}".format(MACRO_VERSION))
        self.resize(1660, 1060)
        self.setMinimumSize(1320, 820)
        self._assembly_label_config = validate_assembly_label_config(
            assembly_label_config
        )
        self._material_report_config = validate_material_report_config(
            material_report_config
        )
        self._preset_library_load_result = load_named_preset_library()
        self._configuration_presets = _configuration_json_copy(
            self._preset_library_load_result.get("presets", [])
            if self._preset_library_load_result.get("valid")
            else []
        )
        self._last_preset_merge_report = None

        layout = QtWidgets.QVBoxLayout(self)

        banner = QtWidgets.QLabel(
            "MULTI-TRACK CONTROL PANEL - VERSION {}".format(MACRO_VERSION)
        )
        banner_font = banner.font()
        banner_font.setBold(True)
        banner_font.setPointSize(max(11, banner_font.pointSize() + 2))
        banner.setFont(banner_font)
        layout.addWidget(banner)

        note = QtWidgets.QLabel(
            "Every added track has its own concentric constant-radius section. "
            "Euler modes retain the previous independent-easement behaviour. "
            "Platform widening uses a continuous same-direction curvature profile "
            "to hold exact entry, curve and exit spacing without a reverse curve. "
            "The entered platform transition lengths are honoured exactly. Hover "
            "over any field label, table heading or entry control for help. Choose "
            "whether to replace existing generated sets or create a new one. "
            "Version 7.4 positions a platform from its centre and total length, "
            "then can taper either end in plan and slope a 3D platform down towards "
            "trackbed level. Version 8.2 adds validated DXF, SVG, STL, STEP and manifest "
            "output. Version 9.6 keeps outside-platform defaults persistent, shows key "
            "platform construction choices in the manager table, remembers accepted inputs "
            "per document with a last-used fallback, and creates the formation board from one "
            "continuous swept outline without face-to-face Boolean fusions. Version 10.0 adds "
            "a separate Straight Track Manager for independent straight routes and exact curve "
            "entrance or exit tangent extensions. Version 10.2A4 retains the stable production schedule, material report and read-only "
            "production preflight, then adds selected-item export by FreeCAD object, section, track, platform, formation board, route "
            "or template set with a complete file preview and staged all-or-nothing commitment. Version 10.2A6 adds validated, readable JSON configuration import and export without regenerating geometry. Version 10.2A7 adds a named-preset manager with explicit library saving, safe preset application and transported-preset merging. Version 10.2A8A6B1 adds read-only timber conflict analysis, and Version 10.2A8A6B2A2 extends controlled inherited-pair replacement into a complete connector timbering envelope which returns to each configured Main template width only after stable clearance. Version 10.2A8A6B3 adds a separate controlled interlacing and longitudinal-shoving stage for unresolved inherited A/B positions. Version 10.2A8A6B4 combines the envelope and movement stages into one deterministic automatic resolver. Resolved crossovers can now be edited and integrated reversibly with both host templates; chair validation remains staged for A8A7. Straight platforms remain staged for a later revision."
        )
        note.setWordWrap(True)
        layout.addWidget(note)

        scroll_area = QtWidgets.QScrollArea()
        scroll_area.setWidgetResizable(True)
        scroll_content = QtWidgets.QWidget()
        content_layout = QtWidgets.QVBoxLayout(scroll_content)
        scroll_area.setWidget(scroll_content)

        global_group = QtWidgets.QGroupBox("Main curve")
        global_form = QtWidgets.QFormLayout(global_group)

        self.transition_box = self._length_box(transition, 0.0, 100000.0, 10.0)
        self.radius_box = self._length_box(radius, 1.0, 100000.0, 10.0)
        self.angle_box = self._number_box(angle, -360.0, 360.0, " deg", 1.0)
        self.main_width_box = self._length_box(main_width, 0.1, 1000.0, 1.0)
        self.parallel_count_box = QtWidgets.QSpinBox()
        self.parallel_count_box.setRange(0, MAX_PARALLEL_TRACKS)
        self.parallel_count_box.setValue(len(track_configs))

        self.output_mode_box = QtWidgets.QComboBox()
        self.output_mode_box.addItems([OUTPUT_REPLACE, OUTPUT_CREATE_NEW])
        self.output_mode_box.setCurrentIndex(0)
        self.existing_sets_label = QtWidgets.QLabel(
            "{} generated template set{} found in this document".format(
                int(generated_set_count),
                "" if int(generated_set_count) == 1 else "s",
            )
        )

        self.transition_box.setToolTip("Length of both main-track Euler easements")
        self.radius_box.setToolTip("Main-track radius through the constant curve")
        self.angle_box.setToolTip("Total direction change: positive left, negative right")
        self.main_width_box.setToolTip("Printable strip width for the main track")
        self.parallel_count_box.setToolTip("Number of additional independent tracks")
        self.output_mode_box.setToolTip(
            "Replace performs a clean rebuild: all objects previously generated by "
            "this macro are removed only after the new geometry has passed validation. "
            "Create new preserves every existing set and adds a uniquely named set."
        )
        self.existing_sets_label.setToolTip(
            "Count of template sets recognised as having been generated by this macro, "
            "including compatible earlier versions."
        )

        global_form.addRow("Main transition length (each):", self.transition_box)
        global_form.addRow("Main constant radius:", self.radius_box)
        global_form.addRow("Total turn angle:", self.angle_box)
        global_form.addRow("Main template width:", self.main_width_box)
        global_form.addRow("Number of additional tracks:", self.parallel_count_box)
        global_form.addRow("Output behaviour:", self.output_mode_box)
        global_form.addRow("Existing generated sets:", self.existing_sets_label)

        main_field_tooltips = [
            (
                self.transition_box,
                "Length of each Euler easement on the main track. The macro uses "
                "one easement before and one after the constant-radius curve.",
            ),
            (
                self.radius_box,
                "Centreline radius of the main track through the constant-radius "
                "section. Added-track curve radii are calculated from this value "
                "and their selected curve spacing.",
            ),
            (
                self.angle_box,
                "Total change in direction for the complete alignment, including "
                "both easements and the constant-radius section. Positive values "
                "turn left; negative values turn right.",
            ),
            (
                self.main_width_box,
                "Width of the printable strip centred on the main track. A value "
                "of 32 mm represents an 8 ft prototype sleeper at OO scale.",
            ),
            (
                self.parallel_count_box,
                "Number of additional independently controlled tracks. Each row "
                "below represents one added track and can use different geometry.",
            ),
            (
                self.output_mode_box,
                "Replace all existing generated templates removes all template strips, "
                "centrelines and groups recognised as outputs from this macro, then "
                "creates one clean replacement. Create a new template set preserves "
                "all existing outputs and creates uniquely named new objects.",
            ),
        ]
        for field, tooltip in main_field_tooltips:
            field.setToolTip(tooltip)
            label = global_form.labelForField(field)
            if label is not None:
                label.setToolTip(tooltip)

        content_layout.addWidget(global_group)

        tracks_group = QtWidgets.QGroupBox("Independent parallel-track controls")
        tracks_layout = QtWidgets.QVBoxLayout(tracks_group)

        self.track_table = QtWidgets.QTableWidget()
        self.track_table.setColumnCount(11)
        self.track_table.setHorizontalHeaderLabels(
            [
                "Name",
                "Side",
                "Alignment mode",
                "Entry spacing",
                "Curve spacing",
                "Exit spacing",
                "Entry transition",
                "Exit transition",
                "Template width",
                "Strip",
                "Centreline",
            ]
        )
        table_header_tooltips = [
            "A descriptive name for this added track. It is also used to label "
            "the generated FreeCAD centreline object.",
            "Places the track on the inside or outside of the main curve. Outside "
            "increases the constant radius; Inside decreases it.",
            "Euler - match spacings solves standard Euler easement lengths. "
            "Euler - use lengths honours standard Euler lengths. Platform widening "
            "honours both the entered spacings and transition lengths using a "
            "same-direction compound-curvature transition.",
            "Perpendicular centre-to-centre spacing from the main track on the "
            "entry straight. Editable in Euler - match spacings and Platform widening.",
            "Exact radial centre-to-centre spacing through the concentric "
            "constant-radius section. This directly sets the added track radius.",
            "Perpendicular centre-to-centre spacing from the main track on the "
            "exit straight. Editable in Euler - match spacings and Platform widening.",
            "Entry transition length. Calculated in Euler - match spacings; "
            "entered directly in Euler - use lengths and Platform widening.",
            "Exit transition length. Calculated in Euler - match spacings; "
            "entered directly in Euler - use lengths and Platform widening.",
            "Width of the printable strip centred on this track. A value of 32 mm "
            "represents an 8 ft prototype sleeper at OO scale.",
            "Creates this track's solid printable template strip when ticked.",
            "Creates and displays this track's coloured centreline when ticked.",
        ]
        for column, tooltip in enumerate(table_header_tooltips):
            header_item = self.track_table.horizontalHeaderItem(column)
            if header_item is not None:
                header_item.setToolTip(tooltip)
        self.track_table.setAlternatingRowColors(True)
        try:
            self.track_table.setSelectionBehavior(QtWidgets.QAbstractItemView.SelectRows)
        except AttributeError:
            self.track_table.setSelectionBehavior(
                QtWidgets.QAbstractItemView.SelectionBehavior.SelectRows
            )
        self.track_table.setMinimumHeight(310)
        column_widths = [145, 85, 190, 120, 120, 120, 130, 130, 120, 60, 80]
        for column, width in enumerate(column_widths):
            self.track_table.setColumnWidth(column, width)
        try:
            self.track_table.horizontalHeader().setStretchLastSection(True)
        except Exception:
            pass
        tracks_layout.addWidget(self.track_table)

        row_buttons = QtWidgets.QHBoxLayout()
        self.add_track_button = QtWidgets.QPushButton("Add track")
        self.remove_track_button = QtWidgets.QPushButton("Remove last track")
        self.duplicate_track_button = QtWidgets.QPushButton("Duplicate selected track")
        row_buttons.addWidget(self.add_track_button)
        row_buttons.addWidget(self.remove_track_button)
        row_buttons.addWidget(self.duplicate_track_button)
        row_buttons.addStretch(1)
        tracks_layout.addLayout(row_buttons)

        help_note = QtWidgets.QLabel(
            "Use Platform widening where the curve spacing is deliberately much "
            "wider than the straight spacing, such as around an island platform. "
            "It keeps all curvature in the selected turn direction and holds the "
            "entered spacings and transition lengths exactly. Euler modes remain "
            "available for ordinary parallel tracks. The constant curve always stays "
            "truly concentric. Impossible combinations are rejected before any "
            "existing template is removed."
        )
        help_note.setWordWrap(True)
        tracks_layout.addWidget(help_note)
        content_layout.addWidget(tracks_group)

        self._initial_configs = [
            clone_track_config(item, transition) for item in track_configs
        ]
        self._set_parallel_count(len(self._initial_configs))

        self._straight_loading = True
        self._straight_configs = clone_straight_configs(straight_configs)
        self._straight_current_index = straight_manager_selection_index(
            self._straight_configs,
            selected_straight_index,
        )

        straight_group = QtWidgets.QGroupBox("Straight Track Manager")
        straight_layout = QtWidgets.QVBoxLayout(straight_group)

        self.straight_table = QtWidgets.QTableWidget()
        self.straight_table.setColumnCount(len(self.STRAIGHT_COLUMNS))
        self.straight_table.setHorizontalHeaderLabels(
            [
                "Enabled",
                "Route name",
                "Connection",
                "Length",
                "Travel direction",
                "Tracks",
                "Track spacing",
                "Parallel side",
                "Template width",
                "Template thickness",
                "Start X",
                "Start Y",
                "Rotation",
                "Create strip",
                "Show centreline",
            ]
        )
        straight_header_tooltips = [
            "Generate this straight route.",
            "Name used for the route and generated FreeCAD objects.",
            "Independent datum, or an exact tangent connection to the complete curve track family.",
            "Straight length measured along the direction of travel.",
            "Independent routes can follow or reverse the entered rotation. Connected routes inherit curve travel.",
            "Total number of tracks for an independent route. Connected routes inherit every curve track.",
            "Perpendicular centre-to-centre spacing between independent parallel tracks.",
            "Side on which additional independent tracks are placed relative to travel.",
            "Template width for independent tracks. Connected routes inherit each curve track width.",
            "Template thickness for independent tracks. Connected routes use the existing curve template thickness.",
            "Independent datum X coordinate for Track 1.",
            "Independent datum Y coordinate for Track 1.",
            "Independent route heading before the Forward or Reverse travel selection is applied.",
            "Create template strips for this route.",
            "Create centrelines for this route.",
        ]
        for column, tooltip in enumerate(straight_header_tooltips):
            header_item = self.straight_table.horizontalHeaderItem(column)
            if header_item is not None:
                header_item.setToolTip(tooltip)
        try:
            self.straight_table.setSelectionBehavior(
                QtWidgets.QAbstractItemView.SelectRows
            )
            self.straight_table.setSelectionMode(
                QtWidgets.QAbstractItemView.SingleSelection
            )
        except AttributeError:
            self.straight_table.setSelectionBehavior(
                QtWidgets.QAbstractItemView.SelectionBehavior.SelectRows
            )
            self.straight_table.setSelectionMode(
                QtWidgets.QAbstractItemView.SelectionMode.SingleSelection
            )
        self.straight_table.setAlternatingRowColors(True)
        self.straight_table.setMinimumHeight(280)
        try:
            self.straight_table.setHorizontalScrollMode(
                QtWidgets.QAbstractItemView.ScrollPerPixel
            )
        except AttributeError:
            self.straight_table.setHorizontalScrollMode(
                QtWidgets.QAbstractItemView.ScrollMode.ScrollPerPixel
            )
        straight_column_widths = [70, 175, 185, 110, 135, 75, 120, 145, 125, 135, 105, 105, 105, 90, 110]
        for column, width in enumerate(straight_column_widths):
            self.straight_table.setColumnWidth(column, width)
        straight_layout.addWidget(self.straight_table)

        straight_buttons = QtWidgets.QHBoxLayout()
        self.add_straight_button = QtWidgets.QPushButton("Add independent straight")
        self.add_connected_pair_button = QtWidgets.QPushButton(
            "Replace with curve entrance + exit pair"
        )
        self.remove_straight_button = QtWidgets.QPushButton("Remove selected straight")
        self.duplicate_straight_button = QtWidgets.QPushButton("Duplicate selected straight")
        self.add_connected_pair_button.setToolTip(
            "Replace all Straight Track Manager rows with two 600 mm routes: one joined exactly to every curve entrance tangent and one joined exactly to every curve exit tangent."
        )
        straight_buttons.addWidget(self.add_straight_button)
        straight_buttons.addWidget(self.add_connected_pair_button)
        straight_buttons.addWidget(self.remove_straight_button)
        straight_buttons.addWidget(self.duplicate_straight_button)
        straight_buttons.addStretch(1)
        straight_layout.addLayout(straight_buttons)

        straight_note = QtWidgets.QLabel(
            "Independent routes use Track 1 as the entered datum and place additional tracks at the entered spacing on the selected side. "
            "Use Replace with curve entrance + exit pair for the controlled connection test; it removes all independent straight rows and creates exactly two connected 600 mm routes. "
            "Curve entrance and Curve exit routes inherit every generated curve track, its exact tangent point, heading, centre, width and output selection. "
            "Fields that do not apply to a connected route are disabled. Version 10.2A4 retains Version 10.0B3 straight sectioning, export, joints, fixing holes, formation-board extensions, SVG repair and platform-edge projection unchanged. Section numbers follow travel order within each separate straight route."
        )
        straight_note.setWordWrap(True)
        straight_layout.addWidget(straight_note)
        content_layout.addWidget(straight_group)

        self.straight_table.setRowCount(len(self._straight_configs))
        for straight_row, straight_config in enumerate(self._straight_configs):
            self._populate_straight_row(straight_row, straight_config)
        if self._straight_current_index >= 0:
            self.straight_table.selectRow(self._straight_current_index)
        self._straight_loading = False
        self._update_all_straight_row_modes()

        self._platform_configs = clone_platform_configs(platform_configs)
        self._platform_current_index = platform_manager_selection_index(
            self._platform_configs,
            selected_platform_id,
            selected_platform_index,
        )
        # Keep the editor in loading mode throughout widget construction. The
        # initial track-choice population happens before _load_platform_editor();
        # allowing it to save at that point overwrites combo-box values that have
        # not yet been initialised from the selected platform.
        self._platform_loading = True
        self._platform_initial = clone_platform_config(
            self._platform_configs[self._platform_current_index]
        )

        platform_group = QtWidgets.QGroupBox("Platforms")
        platform_layout = QtWidgets.QVBoxLayout(platform_group)

        self.platform_table = QtWidgets.QTableWidget()
        self.platform_table.setColumnCount(9)
        self.platform_table.setHorizontalHeaderLabels(
            [
                "Enabled",
                "Platform",
                "Arrangement",
                "Adjacent / Up-side track",
                "Down-side track / outside side",
                "Coverage",
                "Entry end",
                "Body output",
                "Length",
            ]
        )
        platform_header_tooltips = [
            "Whether this platform definition will be generated.",
            "Platform name used in FreeCAD objects and production-export filenames.",
            "Outside one track or between two tracks.",
            "Adjacent track for an outside platform, or the Up-side platform-face track.",
            "Outside side for an outside platform, or the Down-side platform-face track.",
            "Longitudinal curve and transition coverage available to the platform.",
            "Plan and vertical profile used at the entry end.",
            "Edges only, a 2D face, or a full 3D platform solid.",
            "Total platform length measured along its reference track.",
        ]
        for column, tooltip in enumerate(platform_header_tooltips):
            header_item = self.platform_table.horizontalHeaderItem(column)
            if header_item is not None:
                header_item.setToolTip(tooltip)
        try:
            self.platform_table.setSelectionBehavior(
                QtWidgets.QAbstractItemView.SelectRows
            )
            self.platform_table.setSelectionMode(
                QtWidgets.QAbstractItemView.SingleSelection
            )
            self.platform_table.setEditTriggers(
                QtWidgets.QAbstractItemView.NoEditTriggers
            )
        except AttributeError:
            self.platform_table.setSelectionBehavior(
                QtWidgets.QAbstractItemView.SelectionBehavior.SelectRows
            )
            self.platform_table.setSelectionMode(
                QtWidgets.QAbstractItemView.SelectionMode.SingleSelection
            )
            self.platform_table.setEditTriggers(
                QtWidgets.QAbstractItemView.EditTrigger.NoEditTriggers
            )
        self.platform_table.setAlternatingRowColors(True)
        self.platform_table.setMinimumHeight(145)
        for column, width in enumerate(
            [72, 180, 160, 150, 180, 235, 180, 155, 110]
        ):
            self.platform_table.setColumnWidth(column, width)
        try:
            self.platform_table.horizontalHeader().setStretchLastSection(True)
        except Exception:
            pass
        platform_layout.addWidget(self.platform_table)

        platform_buttons = QtWidgets.QHBoxLayout()
        self.add_platform_button = QtWidgets.QPushButton("Add platform")
        self.duplicate_platform_button = QtWidgets.QPushButton("Duplicate selected")
        self.remove_platform_button = QtWidgets.QPushButton("Remove selected")
        self.move_platform_up_button = QtWidgets.QPushButton("Move up")
        self.move_platform_down_button = QtWidgets.QPushButton("Move down")
        for button in (
            self.add_platform_button,
            self.duplicate_platform_button,
            self.remove_platform_button,
            self.move_platform_up_button,
            self.move_platform_down_button,
        ):
            platform_buttons.addWidget(button)
        platform_buttons.addStretch(1)
        platform_layout.addLayout(platform_buttons)

        platform_editor_group = QtWidgets.QGroupBox("Selected platform settings")
        platform_editor_layout = QtWidgets.QGridLayout(platform_editor_group)

        self.platform_enabled_box = self._checkbox(self._platform_initial["enabled"])
        self.platform_name_box = QtWidgets.QLineEdit(self._platform_initial["name"])
        self.platform_name_box.setMaxLength(MAX_PLATFORM_NAME_LENGTH)

        self.platform_arrangement_box = QtWidgets.QComboBox()
        self.platform_arrangement_box.addItems([PLATFORM_BETWEEN, PLATFORM_OUTSIDE])
        self.platform_arrangement_box.setCurrentIndex(
            1 if self._platform_initial["arrangement"] == PLATFORM_OUTSIDE else 0
        )

        self.platform_track_a_box = QtWidgets.QComboBox()
        self.platform_track_b_box = QtWidgets.QComboBox()
        self.platform_outside_side_box = QtWidgets.QComboBox()
        self.platform_outside_side_box.addItems([PLATFORM_LEFT, PLATFORM_RIGHT])
        self.platform_outside_side_box.setCurrentIndex(
            1 if self._platform_initial["outside_side"] == PLATFORM_RIGHT else 0
        )

        self.platform_clearance_a_box = self._length_box(
            self._platform_initial["clearance_a"], 0.001, 10000.0, 1.0
        )
        self.platform_clearance_b_box = self._length_box(
            self._platform_initial["clearance_b"], 0.001, 10000.0, 1.0
        )
        self.platform_coverage_box = QtWidgets.QComboBox()
        self.platform_coverage_box.addItems(
            [PLATFORM_CONSTANT, PLATFORM_ENTRY, PLATFORM_EXIT, PLATFORM_CORE]
        )
        self.platform_length_box = self._length_box(
            self._platform_initial["platform_length"], 0.001, 100000.0, 10.0
        )
        self.platform_centre_offset_box = self._length_box(
            self._platform_initial["centre_offset"], -100000.0, 100000.0, 10.0
        )

        self.platform_entry_end_style_box = QtWidgets.QComboBox()
        self.platform_entry_end_style_box.addItems(
            [PLATFORM_END_SQUARE, PLATFORM_END_TAPERED_LABEL]
        )
        self.platform_exit_end_style_box = QtWidgets.QComboBox()
        self.platform_exit_end_style_box.addItems(
            [PLATFORM_END_SQUARE, PLATFORM_END_TAPERED_LABEL]
        )
        self.platform_entry_taper_length_box = self._length_box(
            self._platform_initial["entry_taper_length"], 0.0, 100000.0, 10.0
        )
        self.platform_exit_taper_length_box = self._length_box(
            self._platform_initial["exit_taper_length"], 0.0, 100000.0, 10.0
        )
        self.platform_match_end_profiles_box = self._checkbox(
            self._platform_initial["match_end_profiles"]
        )

        self.platform_width_box = self._length_box(
            self._platform_initial["platform_width"], 0.001, 10000.0, 1.0
        )
        self.platform_required_clearance_box = self._length_box(
            self._platform_initial["required_clearance"], 0.0, 10000.0, 1.0
        )
        self.platform_check_clearance_box = self._checkbox(
            self._platform_initial["check_clearance"]
        )
        self.platform_create_edges_box = self._checkbox(
            self._platform_initial["create_edges"]
        )
        self.platform_show_edges_box = self._checkbox(
            self._platform_initial["show_edges"]
        )
        self.platform_body_output_box = QtWidgets.QComboBox()
        self.platform_body_output_box.addItems(
            [PLATFORM_EDGES_ONLY, PLATFORM_FACE, PLATFORM_SOLID]
        )
        # New and reset platform definitions default to a true 3D body. Saved
        # platform choices still load unchanged through _load_platform_editor().
        self.platform_body_output_box.setCurrentIndex(2)
        self.platform_height_box = self._length_box(
            self._platform_initial["platform_height"], 0.001, 1000.0, 1.0
        )
        self.platform_show_body_box = self._checkbox(
            self._platform_initial["show_body"]
        )

        platform_fields = [
            ("Enable platform output:", self.platform_enabled_box,
             "Enables this platform definition. Track geometry is unchanged."),
            ("Platform name:", self.platform_name_box,
             "Unique name used for generated objects and production-export filenames."),
            ("Arrangement:", self.platform_arrangement_box,
             "Place an island platform between two selected tracks or outside one track."),
            ("Up-side track:", self.platform_track_a_box,
             "Up-side platform-face track for a between-track platform. This remains the longitudinal reference used by the proven geometry."),
            ("Down-side track:", self.platform_track_b_box,
             "Down-side platform-face track when the platform sits between two tracks."),
            ("Outside side:", self.platform_outside_side_box,
             "Side of the selected track relative to the direction of travel."),
            ("Up-side edge clearance:", self.platform_clearance_a_box,
             "Perpendicular distance from the Up-side track centreline to its platform edge."),
            ("Down-side edge clearance:", self.platform_clearance_b_box,
             "Perpendicular distance from the Down-side track centreline to its platform edge."),
            ("Platform coverage:", self.platform_coverage_box,
             "Select the curve and transition sections available to this platform."),
            ("Platform length:", self.platform_length_box,
             "Total length measured along Track A. Increasing it extends equally from the centre."),
            ("Centre offset:", self.platform_centre_offset_box,
             "Moves the platform centre from the middle of its selected coverage."),
            ("Match entry and exit ends:", self.platform_match_end_profiles_box,
             "Uses the entry end style and length at both ends."),
            ("Entry end style:", self.platform_entry_end_style_box,
             "Square keeps a full-width end. Tapered ramp narrows in plan and slopes a 3D body to trackbed level."),
            ("Exit end style:", self.platform_exit_end_style_box,
             "Available when matching is unticked."),
            ("Entry end length:", self.platform_entry_taper_length_box,
             "Length over which the entry end widens and, for a solid, rises."),
            ("Exit end length:", self.platform_exit_taper_length_box,
             "Available when matching is unticked."),
            ("Outside platform width:", self.platform_width_box,
             "Platform width measured away from the track-facing edge in Outside mode."),
            ("Required track clearance:", self.platform_required_clearance_box,
             "Centreline clearance envelope checked against selected and other tracks."),
            ("Check clearance envelope:", self.platform_check_clearance_box,
             "Checks the platform against track clearance envelopes before replacement."),
            ("Create edge objects:", self.platform_create_edges_box,
             "Creates separate platform-edge wire objects."),
            ("Show edge objects:", self.platform_show_edges_box,
             "Initial visibility of generated platform-edge wire objects."),
            ("Platform body output:", self.platform_body_output_box,
             "Choose edges only, a separate 2D face, or an extruded 3D solid."),
            ("Platform height:", self.platform_height_box,
             "Extrusion height for a 3D platform solid."),
            ("Show platform body:", self.platform_show_body_box,
             "Initial visibility of the generated 2D face or 3D solid."),
        ]
        for index, (label_text, field, tooltip) in enumerate(platform_fields):
            row = index // 2
            column = (index % 2) * 2
            label = QtWidgets.QLabel(label_text)
            label.setToolTip(tooltip)
            field.setToolTip(tooltip)
            if field is self.platform_track_a_box:
                self.platform_track_a_label = label
            elif field is self.platform_track_b_box:
                self.platform_track_b_label = label
            elif field is self.platform_clearance_a_box:
                self.platform_clearance_a_label = label
            elif field is self.platform_clearance_b_box:
                self.platform_clearance_b_label = label
            platform_editor_layout.addWidget(label, row, column)
            platform_editor_layout.addWidget(field, row, column + 1)
        platform_layout.addWidget(platform_editor_group)

        platform_note = QtWidgets.QLabel(
            "Add, duplicate, remove and reorder independent platform definitions. "
            "Selecting a row loads it into the editor above. Every enabled platform "
            "uses the proven Version 8 platform geometry independently; all enabled "
            "footprints can contribute to the formation board and all platform bodies "
            "can use the shared section boundaries. Platform files are exported only "
            "through Production export. Between-track platforms use Up-side and "
            "Down-side labels; outside platforms use Adjacent track and Outside side."
        )
        platform_note.setWordWrap(True)
        platform_layout.addWidget(platform_note)
        content_layout.addWidget(platform_group)

        self._formation_initial = clone_formation_config(formation_config)
        formation_group = QtWidgets.QGroupBox("Formation board")
        formation_layout = QtWidgets.QGridLayout(formation_group)
        self.formation_enabled_box = self._checkbox(self._formation_initial["enabled"])
        self.formation_include_tracks_box = self._checkbox(self._formation_initial["include_track_templates"])
        self.formation_include_platform_box = self._checkbox(self._formation_initial["include_platform"])
        self.formation_margin_box = self._length_box(self._formation_initial["outer_margin"], 0.0, 10000.0, 1.0)
        self.formation_neck_box = self._length_box(self._formation_initial["minimum_neck_width"], 0.1, 10000.0, 1.0)
        self.formation_fill_gaps_box = self._checkbox(self._formation_initial["fill_enclosed_gaps"])
        self.formation_smooth_box = self._checkbox(self._formation_initial["smooth_outline"])
        self.formation_smoothing_tolerance_box = self._length_box(self._formation_initial["smoothing_tolerance"], 0.001, 100.0, 0.05)
        self.formation_output_type_box = QtWidgets.QComboBox()
        self.formation_output_type_box.addItems([FORMATION_OUTLINE_ONLY, FORMATION_SOLID_ONLY, FORMATION_BOTH])
        self.formation_output_type_box.setCurrentIndex({FORMATION_OUTLINE_ONLY:0, FORMATION_SOLID_ONLY:1, FORMATION_BOTH:2}.get(self._formation_initial["output_type"],2))
        self.formation_thickness_box = self._length_box(self._formation_initial["board_thickness"], 0.1, 1000.0, 1.0)
        self.formation_show_outline_box = self._checkbox(self._formation_initial["show_outline"])
        self.formation_show_solid_box = self._checkbox(self._formation_initial["show_solid"])
        self.formation_track_engraving_box = self._checkbox(self._formation_initial["create_track_engraving"])
        self.formation_platform_engraving_box = self._checkbox(self._formation_initial["create_platform_engraving"])
        formation_fields = [
            ("Enable formation board:", self.formation_enabled_box, "Creates a continuous supporting footprint beneath the selected railway geometry."),
            ("Include track-template strips:", self.formation_include_tracks_box, "Includes every track whose printable Strip control is ticked."),
            ("Include platform footprint:", self.formation_include_platform_box, "Includes the calculated platform plan footprint when platform generation is enabled."),
            ("Outer margin:", self.formation_margin_box, "Extra material outside the selected track and platform footprints."),
            ("Minimum board width:", self.formation_neck_box, "Minimum transverse width of the simple supporting board."),
            ("Formation output type:", self.formation_output_type_box, "Creates a 2D cutting profile, a 3D plywood solid, or both."),
            ("Board material thickness:", self.formation_thickness_box, "Actual sheet thickness, for example 12 mm plywood. The board is extruded below track level."),
            ("Show formation outline:", self.formation_show_outline_box, "Initial visibility of the perimeter cutting profile."),
            ("Show formation solid:", self.formation_show_solid_box, "Initial visibility of the 3D formation-board solid."),
            ("Track-centreline engraving:", self.formation_track_engraving_box, "Creates a separate selectable compound of track centrelines for engraving."),
            ("Platform-edge engraving:", self.formation_platform_engraving_box, "Creates a separate selectable compound of platform edges for engraving."),
        ]
        for index, (label_text, field, tooltip) in enumerate(formation_fields):
            row = index // 2
            column = (index % 2) * 2
            label = QtWidgets.QLabel(label_text)
            label.setToolTip(tooltip)
            field.setToolTip(tooltip)
            formation_layout.addWidget(label, row, column)
            formation_layout.addWidget(field, row, column + 1)
        formation_note = QtWidgets.QLabel(
            "The formation board is one continuous closed swept footprint beneath the selected "
            "track templates and platforms. Version 9.6 samples the route, retains the furthest "
            "occupied limit on each side, broadens abrupt platform-end changes into controlled "
            "transitions, closes both ends perpendicular to the route, and extrudes one face. "
            "No overlapping track or platform faces are fused in the base-board calculation."
        )
        formation_note.setWordWrap(True)
        formation_layout.addWidget(formation_note, (len(formation_fields)+1)//2, 0, 1, 4)
        content_layout.addWidget(formation_group)

        self._section_initial = clone_section_config(section_config)
        section_group = QtWidgets.QGroupBox("Universal sectioning")
        section_layout = QtWidgets.QGridLayout(section_group)
        self.section_enabled_box = self._checkbox(self._section_initial["enabled"])
        self.section_max_length_box = self._length_box(self._section_initial["maximum_section_length"], 0.0, 100000.0, 10.0)
        self.section_balance_box = self._checkbox(self._section_initial["balance_lengths"])
        self.section_min_length_box = self._length_box(self._section_initial["minimum_section_length"], 0.0, 100000.0, 10.0)
        self.section_tracks_box = self._checkbox(self._section_initial["section_track_templates"])
        self.section_platform_box = self._checkbox(self._section_initial["section_platform"])
        self.section_formation_box = self._checkbox(self._section_initial["section_formation"])
        self.section_preserve_box = self._checkbox(self._section_initial["preserve_unsplit"])
        self.section_number_box = self._checkbox(self._section_initial["number_in_travel_order"])
        section_fields = [
            ("Enable sectioning:", self.section_enabled_box, "Creates export-ready pieces using shared cross-section positions."),
            ("Maximum section length:", self.section_max_length_box, "Freely editable maximum piece length. Zero keeps one complete object."),
            ("Balance section lengths:", self.section_balance_box, "Distributes the total length evenly so the final piece is not very short."),
            ("Minimum permitted length:", self.section_min_length_box, "Rejects an impractically short section arrangement."),
            ("Section track templates:", self.section_tracks_box, "Splits the printable track-template compound."),
            ("Section platform body:", self.section_platform_box, "Splits the generated 2D or 3D platform body."),
            ("Section formation board:", self.section_formation_box, "Splits the formation-board profile and solid using the same boundaries."),
            ("Preserve unsplit objects:", self.section_preserve_box, "Keeps the complete source objects as well as the section pieces."),
            ("Number in travel order:", self.section_number_box, "Creates Section 01, Section 02 and matching engraving geometry from entry to exit."),
        ]
        for index, (label_text, field, tooltip) in enumerate(section_fields):
            row = index // 2
            column = (index % 2) * 2
            label = QtWidgets.QLabel(label_text)
            label.setToolTip(tooltip)
            field.setToolTip(tooltip)
            section_layout.addWidget(label, row, column)
            section_layout.addWidget(field, row, column + 1)
        section_note = QtWidgets.QLabel(
            "Every selected layer uses the same boundaries measured along the main "
            "alignment. Each boundary is perpendicular to the local direction of "
            "travel, so formation, track and platform pieces remain aligned."
        )
        section_note.setWordWrap(True)
        section_layout.addWidget(section_note, (len(section_fields)+1)//2, 0, 1, 4)
        content_layout.addWidget(section_group)

        self._registration_initial = clone_registration_config(registration_config)
        registration_group = QtWidgets.QGroupBox("Formation-board registration features")
        registration_layout = QtWidgets.QGridLayout(registration_group)
        self.registration_type_box = QtWidgets.QComboBox()
        self.registration_type_box.addItems([REGISTRATION_PLAIN, REGISTRATION_HOLES, REGISTRATION_PINS, REGISTRATION_TONGUE])
        self.registration_type_box.setCurrentIndex({REGISTRATION_PLAIN:0, REGISTRATION_HOLES:1, REGISTRATION_PINS:2, REGISTRATION_TONGUE:3}.get(self._registration_initial["joint_type"],0))
        self.registration_depth_box = self._length_box(self._registration_initial["joint_depth"], 0.1, 1000.0, 1.0)
        self.registration_width_box = self._length_box(self._registration_initial["joint_width"], 0.1, 1000.0, 1.0)
        self.registration_clearance_box = self._length_box(self._registration_initial["fit_clearance"], 0.0, 10.0, 0.05)
        self.registration_hole_diameter_box = self._length_box(self._registration_initial["alignment_hole_diameter"], 0.1, 100.0, 0.5)
        self.registration_hole_offset_box = self._length_box(self._registration_initial["alignment_hole_offset"], 0.1, 1000.0, 1.0)
        registration_fields = [
            ("Joint type:", self.registration_type_box, "Plain, alignment-hole, pin-and-socket or tongue-and-groove formation-board joints."),
            ("Joint depth:", self.registration_depth_box, "Distance that a tongue or pin extends beyond the section boundary."),
            ("Joint width:", self.registration_width_box, "Width across the joint feature."),
            ("Fit clearance:", self.registration_clearance_box, "Extra size added to sockets and grooves for the chosen cutting process."),
            ("Alignment-hole diameter:", self.registration_hole_diameter_box, "Diameter of separate internal alignment-hole profiles."),
            ("Hole offset from joint:", self.registration_hole_offset_box, "Longitudinal distance from the split line to each alignment hole."),
        ]
        for index, (label_text, field, tooltip) in enumerate(registration_fields):
            row = index // 2
            column = (index % 2) * 2
            label = QtWidgets.QLabel(label_text)
            label.setToolTip(tooltip)
            field.setToolTip(tooltip)
            registration_layout.addWidget(label, row, column)
            registration_layout.addWidget(field, row, column + 1)
        registration_note = QtWidgets.QLabel(
            "Enable ‘Section formation board’ to use these joints. Registration modifies "
            "formation-board sections only; it remains separate from the track-template "
            "assembly features below."
        )
        registration_note.setWordWrap(True)
        registration_layout.addWidget(registration_note, (len(registration_fields)+1)//2, 0, 1, 4)
        content_layout.addWidget(registration_group)

        self._template_assembly_initial = clone_template_assembly_config(template_assembly_config)
        template_assembly_group = QtWidgets.QGroupBox("Track-template assembly and fixing")
        template_assembly_layout = QtWidgets.QGridLayout(template_assembly_group)
        self.template_assembly_enabled_box = self._checkbox(self._template_assembly_initial["enabled"])
        self.template_joint_type_box = QtWidgets.QComboBox()
        self.template_joint_type_box.addItems([
            TEMPLATE_JOINT_PLAIN,
            TEMPLATE_JOINT_PINS,
            TEMPLATE_JOINT_TONGUE,
        ])
        self.template_joint_type_box.setCurrentIndex({
            TEMPLATE_JOINT_PLAIN: 0,
            TEMPLATE_JOINT_PINS: 1,
            TEMPLATE_JOINT_TONGUE: 2,
        }.get(self._template_assembly_initial["joint_type"], 2))
        self.template_joint_depth_box = self._length_box(self._template_assembly_initial["joint_depth"], 0.5, 100.0, 0.5)
        self.template_joint_width_box = self._length_box(self._template_assembly_initial["joint_width"], 0.5, 100.0, 0.5)
        self.template_joint_clearance_box = self._length_box(self._template_assembly_initial["fit_clearance"], 0.0, 5.0, 0.05)
        self.template_fixing_holes_box = self._checkbox(self._template_assembly_initial["fixing_holes_enabled"])
        self.template_holes_per_section_box = QtWidgets.QSpinBox()
        self.template_holes_per_section_box.setRange(1, 20)
        self.template_holes_per_section_box.setValue(self._template_assembly_initial["holes_per_section"])
        self.template_hole_diameter_box = self._length_box(self._template_assembly_initial["hole_diameter"], 0.2, 20.0, 0.5)
        self.template_hole_end_clearance_box = self._length_box(self._template_assembly_initial["minimum_end_clearance"], 0.0, 1000.0, 5.0)
        self.template_matching_formation_holes_box = self._checkbox(self._template_assembly_initial["matching_formation_holes"])
        self.template_show_hole_geometry_box = self._checkbox(self._template_assembly_initial["show_hole_geometry"])
        template_assembly_fields = [
            ("Enable template assembly features:", self.template_assembly_enabled_box, "Adds physical joints and optional fixing holes to sectioned track templates."),
            ("Template joint type:", self.template_joint_type_box, "Plain cut edges, paired pins and sockets, or a centred tongue and socket at every track-strip joint."),
            ("Joint depth:", self.template_joint_depth_box, "Distance the template tongue or pin extends into the next section."),
            ("Joint width / pin diameter:", self.template_joint_width_box, "Width of a tongue, or diameter of each of the two rounded pins."),
            ("Fit clearance:", self.template_joint_clearance_box, "Extra material removed from sockets for the chosen printing or cutting process."),
            ("Centreline fixing holes:", self.template_fixing_holes_box, "Cuts fixing holes through every individual track strip on its exact centreline."),
            ("Holes per strip per section:", self.template_holes_per_section_box, "Number of centreline holes in each individual track strip and each section. Two is the recommended default."),
            ("Fixing-hole diameter:", self.template_hole_diameter_box, "Finished through-hole diameter in the track-template sections."),
            ("Minimum distance from section ends:", self.template_hole_end_clearance_box, "Minimum centre distance from each section end; joint clearance may increase this automatically."),
            ("Matching holes in formation board:", self.template_matching_formation_holes_box, "Cuts the same hole pattern through the formation board for positive pin registration."),
            ("Show hole-cutting geometry:", self.template_show_hole_geometry_box, "Shows separate selectable circular profiles for checking and later export."),
        ]
        for index, (label_text, field, tooltip) in enumerate(template_assembly_fields):
            row = index // 2
            column = (index % 2) * 2
            label = QtWidgets.QLabel(label_text)
            label.setToolTip(tooltip)
            field.setToolTip(tooltip)
            template_assembly_layout.addWidget(label, row, column)
            template_assembly_layout.addWidget(field, row, column + 1)
        template_assembly_note = QtWidgets.QLabel(
            "These controls apply only when sectioning and ‘Section track templates’ are enabled. "
            "Joints are generated independently on every selected track strip. Fixing holes sit on "
            "the exact track centreline; the default creates two holes per strip per section."
        )
        template_assembly_note.setWordWrap(True)
        template_assembly_layout.addWidget(template_assembly_note, (len(template_assembly_fields)+1)//2, 0, 1, 4)
        content_layout.addWidget(template_assembly_group)

        self._production_export_initial = clone_production_export_config(
            production_export_config
        )
        self._exporter_capabilities = exporter_capabilities or {}
        production_group = QtWidgets.QGroupBox("Production export")
        production_layout = QtWidgets.QVBoxLayout(production_group)

        production_basic = QtWidgets.QGridLayout()
        self.production_export_enabled_box = self._checkbox(
            self._production_export_initial["enabled"]
        )
        self.production_export_directory_box = QtWidgets.QLineEdit(
            self._production_export_initial["output_directory"]
        )
        self.production_export_browse_button = QtWidgets.QPushButton("Browse...")
        production_directory_widget = QtWidgets.QWidget()
        production_directory_layout = QtWidgets.QHBoxLayout(production_directory_widget)
        production_directory_layout.setContentsMargins(0, 0, 0, 0)
        production_directory_layout.addWidget(self.production_export_directory_box)
        production_directory_layout.addWidget(self.production_export_browse_button)

        self.production_include_set_box = self._checkbox(True)
        self.production_include_set_box.setEnabled(False)
        self.production_include_role_box = self._checkbox(
            self._production_export_initial["include_object_role"]
        )
        self.production_include_track_box = self._checkbox(
            self._production_export_initial["include_track_number"]
        )
        self.production_include_section_box = self._checkbox(
            self._production_export_initial["include_section_number"]
        )
        self.production_each_section_box = self._checkbox(
            self._production_export_initial["export_each_section"]
        )
        self.production_combined_box = self._checkbox(
            self._production_export_initial["create_combined_files"]
        )
        self.production_overwrite_box = self._checkbox(
            self._production_export_initial["overwrite_existing"]
        )
        self.production_manifest_box = self._checkbox(
            self._production_export_initial["create_manifest"]
        )
        self.production_open_directory_box = self._checkbox(
            self._production_export_initial["open_output_directory"]
        )
        self.production_current_set_box = self._checkbox(True)
        self.production_current_set_box.setEnabled(False)

        production_fields = [
            ("Enable production export:", self.production_export_enabled_box,
             "Exports only the recognised outputs created for the current template set after the FreeCAD transaction succeeds."),
            ("Output directory:", production_directory_widget,
             "Directory for production files. The macro creates it when its parent directory is writable."),
            ("Include template-set identifier:", self.production_include_set_box,
             "The unique SET identifier is mandatory so different template sets cannot silently collide."),
            ("Include object role:", self.production_include_role_box,
             "Uses consistent construction-role terminology in every filename."),
            ("Include track number:", self.production_include_track_box,
             "Adds zero-padded track numbers where the output belongs to one track."),
            ("Include section number:", self.production_include_section_box,
             "Adds zero-padded travel-order section numbers where available."),
            ("Export each section separately:", self.production_each_section_box,
             "Creates one file per selected track, platform or formation section."),
            ("Create combined files:", self.production_combined_box,
             "Creates separate combined files for cutting profiles, holes, joints, engraving and STEP solids. Categories are never mixed."),
            ("Overwrite existing files:", self.production_overwrite_box,
             "Allows atomic replacement of existing files. When unticked, an automatic Rev_02, Rev_03 and so on suffix is used."),
            ("Create CSV manifest:", self.production_manifest_box,
             "Records every successful, failed and skipped export in a LibreOffice-friendly CSV file."),
            ("Open output directory after export:", self.production_open_directory_box,
             "Opens the completed export directory using the desktop file manager where practical."),
            ("Current template set only:", self.production_current_set_box,
             "This safety restriction is always enabled; unrelated and older document objects are ignored."),
        ]
        for index, (label_text, field, tooltip) in enumerate(production_fields):
            row = index // 2
            column = (index % 2) * 2
            label = QtWidgets.QLabel(label_text)
            label.setToolTip(tooltip)
            field.setToolTip(tooltip)
            production_basic.addWidget(label, row, column)
            production_basic.addWidget(field, row, column + 1)
        production_layout.addLayout(production_basic)

        formats_group = QtWidgets.QGroupBox("Export formats available in this FreeCAD installation")
        formats_layout = QtWidgets.QHBoxLayout(formats_group)
        self.production_format_boxes = {}
        for format_key in (
            EXPORT_FORMAT_DXF,
            EXPORT_FORMAT_SVG,
            EXPORT_FORMAT_STL,
            EXPORT_FORMAT_STEP,
        ):
            capability = self._exporter_capabilities.get(format_key, {})
            available = bool(capability.get("available", False))
            label = EXPORT_FORMAT_LABELS[format_key]
            if not available:
                label += " (unavailable)"
            box = self._checkbox(
                self._production_export_initial["formats"].get(format_key, True)
                and available
            )
            box.setText(label)
            box.setEnabled(available)
            box.setToolTip(
                capability.get("reason", "Exporter detected and available.")
            )
            self.production_format_boxes[format_key] = box
            formats_layout.addWidget(box)
        formats_layout.addStretch(1)
        production_layout.addWidget(formats_group)

        self.production_selection_boxes = {}

        def add_export_selection(group_layout, key, text, tooltip):
            box = self._checkbox(
                self._production_export_initial["selections"].get(key, True)
            )
            box.setText(text)
            box.setToolTip(tooltip)
            self.production_selection_boxes[key] = box
            group_layout.addWidget(box)
            return box

        output_groups_layout = QtWidgets.QHBoxLayout()

        cutting_group = QtWidgets.QGroupBox("2D cutting and internal profiles — DXF / SVG")
        cutting_layout = QtWidgets.QVBoxLayout(cutting_group)
        add_export_selection(cutting_layout, "track_template_compound_2d", "Complete track-template profiles", "Closed plan profiles for the complete printable strip compound.")
        add_export_selection(cutting_layout, "track_template_sections_2d", "Individual track-template section profiles", "One closed cutting profile per track strip and travel-order section.")
        add_export_selection(cutting_layout, "track_template_fixing_holes", "Track-template fixing-hole profiles", "Separate internal centreline fixing-hole profiles.")
        add_export_selection(cutting_layout, "track_template_joints", "Track-template joint geometry", "Separate tongue, socket or pin profile geometry.")
        add_export_selection(cutting_layout, "platform_plan_outline", "Platform plan outline", "Closed platform footprint for cutting or construction reference.")
        add_export_selection(cutting_layout, "platform_sections_2d", "Individual platform section outlines", "Closed plan outline for each existing platform section.")
        add_export_selection(cutting_layout, "formation_perimeter", "Formation-board perimeter", "Complete closed formation-board cutting perimeter.")
        add_export_selection(cutting_layout, "formation_sections_2d", "Individual formation-board section perimeters", "Closed cutting perimeter for every sectioned board piece.")
        add_export_selection(cutting_layout, "registration_holes", "Registration holes", "Separate internal alignment-hole profiles.")
        add_export_selection(cutting_layout, "formation_matching_holes", "Matching track-template fixing holes", "Separate matching fixing-hole profiles for the formation board.")
        add_export_selection(cutting_layout, "registration_joints", "Formation registration-joint geometry", "Separate formation tongue, groove, pin or socket profiles.")
        cutting_layout.addStretch(1)
        output_groups_layout.addWidget(cutting_group)

        engraving_group = QtWidgets.QGroupBox("Engraving geometry — DXF / SVG")
        engraving_layout = QtWidgets.QVBoxLayout(engraving_group)
        add_export_selection(engraving_layout, "track_centrelines", "Track centrelines", "One engraving line set per generated track centreline.")
        add_export_selection(engraving_layout, "platform_edges", "Platform-edge engraving", "The generated track-side platform edge lines.")
        add_export_selection(engraving_layout, "section_numbers", "Section-number engraving", "Travel-order section-number line geometry.")
        add_export_selection(engraving_layout, "other_engraving", "Other EngravingGeometry objects", "Any recognised current-set engraving role not covered above.")
        add_export_selection(engraving_layout, ASSEMBLY_LABEL_SELECTION_KEY, "Assembly labels", "Compact optional identification engraving generated only where a safe placement exists.")
        engraving_layout.addStretch(1)
        output_groups_layout.addWidget(engraving_group)

        solid_group = QtWidgets.QGroupBox("3D solids — STL / STEP")
        solid_layout = QtWidgets.QVBoxLayout(solid_group)
        add_export_selection(solid_layout, "track_template_compound_3d", "Complete track-template compound", "Actual generated solid geometry for the complete printable template.")
        add_export_selection(solid_layout, "track_template_sections_3d", "Individual track-template sections", "Actual final section solids, including joints and fixing holes, one track at a time.")
        add_export_selection(solid_layout, "platform_body", "Complete platform body", "The complete generated 3D platform solid where one exists.")
        add_export_selection(solid_layout, "platform_sections_3d", "Individual platform sections", "Each existing platform section solid.")
        add_export_selection(solid_layout, "formation_body", "Complete formation-board solid", "The complete generated formation-board solid.")
        add_export_selection(solid_layout, "formation_sections_3d", "Individual formation-board sections", "Each existing formation-board section solid.")
        solid_layout.addStretch(1)
        output_groups_layout.addWidget(solid_group)

        production_layout.addLayout(output_groups_layout)
        production_note = QtWidgets.QLabel(
            "The export planner validates all selected shapes and calculates every filename before writing. "
            "Cutting profiles, internal holes, joint profiles and engraving remain in separate files; "
            "temporary FreeCAD objects are removed after each exporter call."
        )
        production_note.setWordWrap(True)
        production_layout.addWidget(production_note)

        self.production_schedule_button = QtWidgets.QPushButton(
            "Production schedule..."
        )
        self.production_schedule_button.setToolTip(
            "View recognised production records for an existing template set, "
            "update its FreeCAD schedule sheet or export the schedule as CSV. "
            "This utility does not regenerate or alter railway geometry."
        )
        production_layout.addWidget(self.production_schedule_button)
        self.material_report_button = QtWidgets.QPushButton(
            "Material and length report..."
        )
        self.material_report_button.setToolTip(
            "Measure recognised production parts, review exact and estimated totals, "
            "configure the rectangular sheet-use estimate, update a FreeCAD report sheet "
            "or export the report as CSV. This utility does not alter railway geometry."
        )
        production_layout.addWidget(self.material_report_button)
        self.production_preflight_button = QtWidgets.QPushButton(
            "Production preflight..."
        )
        self.production_preflight_button.setToolTip(
            "Run read-only metadata, geometry, numbering, assembly-feature, filename, "
            "overwrite, output-path and temporary SVG/DXF exporter-bound checks for an "
            "existing template set. Preflight does not regenerate or alter railway geometry."
        )
        production_layout.addWidget(self.production_preflight_button)
        self.assembly_label_button = QtWidgets.QPushButton(
            "Assembly labels..."
        )
        self.assembly_label_button.setToolTip(
            "Configure, preview, apply or remove compact assembly labels for an existing template set. "
            "Visible railway geometry remains unchanged; labelled export sources are kept separately."
        )
        production_layout.addWidget(self.assembly_label_button)
        self.selected_export_button = QtWidgets.QPushButton(
            "Export selected items..."
        )
        self.selected_export_button.setToolTip(
            "Export only selected FreeCAD objects, one section, one complete track, "
            "one platform, one formation board, one route or one template set. The utility "
            "reuses the established exporters, runs production preflight and commits all "
            "files together only after every staged output succeeds."
        )
        production_layout.addWidget(self.selected_export_button)
        self.configuration_io_button = QtWidgets.QPushButton(
            "Configuration import and export..."
        )
        self.configuration_io_button.setToolTip(
            "Export the complete reusable dialogue configuration as readable JSON, "
            "or validate and import a JSON configuration into this dialogue. Import "
            "does not regenerate geometry or alter existing document objects."
        )
        production_layout.addWidget(self.configuration_io_button)
        self.named_presets_button = QtWidgets.QPushButton(
            "Named presets..."
        )
        self.named_presets_button.setToolTip(
            "Create, update, rename, duplicate, apply and delete reusable configuration presets. "
            "Preset application changes only this dialogue. The persistent user library changes "
            "only when Save preset library is deliberately selected."
        )
        production_layout.addWidget(self.named_presets_button)
        self.turnout_manager_button = QtWidgets.QPushButton(
            "REA C10 turnout and crossover manager..."
        )
        self.turnout_manager_button.setToolTip(
            "Open one unified manager for source-driven REA C10 turnouts and managed crossover geometry, analysis and automatic timber resolution. "
            "Turnouts and crossovers share the same host-centreline and picked-position workflow. "
            "Existing host geometry is not trimmed, deleted or regenerated."
        )
        production_layout.addWidget(self.turnout_manager_button)
        # Backward-compatible attribute alias for integrations which still look up the former button.
        self.crossover_manager_button = self.turnout_manager_button
        content_layout.addWidget(production_group)

        self._refresh_platform_track_choices()
        self._refresh_platform_manager_table(self._platform_current_index)
        self.platform_table.selectRow(self._platform_current_index)
        self._load_platform_editor(self._platform_current_index)

        self.parallel_count_box.valueChanged.connect(self._set_parallel_count)
        self.parallel_count_box.valueChanged.connect(self._refresh_platform_track_choices)
        self.add_track_button.clicked.connect(self._add_track)
        self.remove_track_button.clicked.connect(self._remove_last_track)
        self.duplicate_track_button.clicked.connect(self._duplicate_selected_track)
        self.add_straight_button.clicked.connect(self._add_straight)
        self.add_connected_pair_button.clicked.connect(
            self._add_curve_connection_pair
        )
        self.remove_straight_button.clicked.connect(self._remove_selected_straight)
        self.duplicate_straight_button.clicked.connect(self._duplicate_selected_straight)
        self.straight_table.itemSelectionChanged.connect(
            self._straight_selection_changed
        )

        self.platform_table.itemSelectionChanged.connect(
            self._platform_selection_changed
        )
        self.add_platform_button.clicked.connect(self._add_platform)
        self.duplicate_platform_button.clicked.connect(self._duplicate_platform)
        self.remove_platform_button.clicked.connect(self._remove_platform)
        self.move_platform_up_button.clicked.connect(self._move_platform_up)
        self.move_platform_down_button.clicked.connect(self._move_platform_down)

        self.platform_arrangement_box.currentIndexChanged.connect(
            self._platform_arrangement_changed
        )
        self.platform_body_output_box.currentIndexChanged.connect(
            self._update_platform_controls
        )
        self.platform_entry_end_style_box.currentIndexChanged.connect(
            self._update_platform_controls
        )
        self.platform_exit_end_style_box.currentIndexChanged.connect(
            self._update_platform_controls
        )
        self.platform_entry_taper_length_box.valueChanged.connect(
            self._update_platform_controls
        )
        self.platform_match_end_profiles_box.toggled.connect(
            self._update_platform_controls
        )
        self.platform_enabled_box.toggled.connect(self._update_platform_controls)
        self.platform_create_edges_box.toggled.connect(self._update_platform_controls)

        for box in (
            self.platform_enabled_box,
            self.platform_match_end_profiles_box,
            self.platform_check_clearance_box,
            self.platform_create_edges_box,
            self.platform_show_edges_box,
            self.platform_show_body_box,
        ):
            box.toggled.connect(self._platform_editor_changed)
        self.platform_name_box.textChanged.connect(self._platform_editor_changed)
        for combo in (
            self.platform_arrangement_box,
            self.platform_track_a_box,
            self.platform_track_b_box,
            self.platform_outside_side_box,
            self.platform_coverage_box,
            self.platform_entry_end_style_box,
            self.platform_exit_end_style_box,
            self.platform_body_output_box,
        ):
            combo.currentIndexChanged.connect(self._platform_editor_changed)
        for spin_box in (
            self.platform_clearance_a_box,
            self.platform_clearance_b_box,
            self.platform_length_box,
            self.platform_centre_offset_box,
            self.platform_entry_taper_length_box,
            self.platform_exit_taper_length_box,
            self.platform_width_box,
            self.platform_required_clearance_box,
            self.platform_height_box,
        ):
            spin_box.valueChanged.connect(self._platform_editor_changed)

        self.formation_enabled_box.toggled.connect(self._update_formation_section_controls)
        self.formation_output_type_box.currentIndexChanged.connect(self._update_formation_section_controls)
        self.formation_smooth_box.toggled.connect(self._update_formation_section_controls)
        self.section_enabled_box.toggled.connect(self._update_formation_section_controls)
        self.section_max_length_box.valueChanged.connect(self._update_formation_section_controls)
        self.section_formation_box.toggled.connect(self._update_formation_section_controls)
        self.section_tracks_box.toggled.connect(self._update_formation_section_controls)
        self.registration_type_box.currentIndexChanged.connect(self._update_formation_section_controls)
        self.template_assembly_enabled_box.toggled.connect(self._update_formation_section_controls)
        self.template_joint_type_box.currentIndexChanged.connect(self._update_formation_section_controls)
        self.template_fixing_holes_box.toggled.connect(self._update_formation_section_controls)
        self.section_platform_box.toggled.connect(self._update_production_export_controls)
        self.section_number_box.toggled.connect(self._update_production_export_controls)
        self.formation_track_engraving_box.toggled.connect(self._update_production_export_controls)
        self.formation_platform_engraving_box.toggled.connect(self._update_production_export_controls)
        self.template_matching_formation_holes_box.toggled.connect(self._update_production_export_controls)
        self.production_export_enabled_box.toggled.connect(self._update_production_export_controls)
        self.production_export_browse_button.clicked.connect(self._browse_production_export_directory)
        self.production_schedule_button.clicked.connect(self._open_production_schedule)
        self.material_report_button.clicked.connect(self._open_material_report)
        self.production_preflight_button.clicked.connect(self._open_production_preflight)
        self.assembly_label_button.clicked.connect(self._open_assembly_labels)
        self.selected_export_button.clicked.connect(self._open_selected_export)
        self.configuration_io_button.clicked.connect(self._open_configuration_io)
        self.named_presets_button.clicked.connect(self._open_named_presets)
        self.turnout_manager_button.clicked.connect(self._open_turnout_manager)
        self._update_formation_section_controls()
        self._update_production_export_controls()

        content_layout.addStretch(1)
        layout.addWidget(scroll_area, 1)

        try:
            ok_button = QtWidgets.QDialogButtonBox.Ok
            cancel_button = QtWidgets.QDialogButtonBox.Cancel
        except AttributeError:
            ok_button = QtWidgets.QDialogButtonBox.StandardButton.Ok
            cancel_button = QtWidgets.QDialogButtonBox.StandardButton.Cancel
        buttons = QtWidgets.QDialogButtonBox(ok_button | cancel_button)
        buttons.accepted.connect(self.accept)
        buttons.rejected.connect(self.reject)
        layout.addWidget(buttons)

    @staticmethod
    def _length_box(value, minimum, maximum, step):
        box = QtWidgets.QDoubleSpinBox()
        box.setDecimals(3)
        box.setRange(minimum, maximum)
        box.setSingleStep(step)
        box.setSuffix(" mm")
        box.setValue(float(value))
        return box

    @staticmethod
    def _number_box(value, minimum, maximum, suffix, step):
        box = QtWidgets.QDoubleSpinBox()
        box.setDecimals(3)
        box.setRange(minimum, maximum)
        box.setSingleStep(step)
        box.setSuffix(suffix)
        box.setValue(float(value))
        return box

    @staticmethod
    def _checkbox(checked):
        box = QtWidgets.QCheckBox()
        box.setChecked(bool(checked))
        return box

    def _set_parallel_count(self, count):
        count = int(count)
        current_count = self.track_table.rowCount()

        if count < current_count:
            self.track_table.setRowCount(count)
            return

        self.track_table.setRowCount(count)
        for row in range(current_count, count):
            if row < len(self._initial_configs):
                config = clone_track_config(
                    self._initial_configs[row],
                    float(self.transition_box.value()),
                )
            else:
                config = default_track_config(
                    row,
                    float(self.transition_box.value()),
                )
            self._populate_row(row, config)

    def _add_track(self):
        if self.parallel_count_box.value() < MAX_PARALLEL_TRACKS:
            self.parallel_count_box.setValue(self.parallel_count_box.value() + 1)

    def _remove_last_track(self):
        if self.parallel_count_box.value() > 0:
            self.parallel_count_box.setValue(self.parallel_count_box.value() - 1)

    def _row_config(self, row):
        if row < 0 or row >= self.track_table.rowCount():
            return None

        widgets = {
            key: self.track_table.cellWidget(row, column)
            for key, column in self.COLUMNS.items()
        }
        if any(widget is None for widget in widgets.values()):
            return None

        return {
            "name": str(widgets["name"].text()).strip() or "Track {}".format(row + 2),
            "side": str(widgets["side"].currentText()),
            "alignment_mode": str(widgets["mode"].currentText()),
            "start_spacing": float(widgets["start"].value()),
            "curve_spacing": float(widgets["curve"].value()),
            "finish_spacing": float(widgets["finish"].value()),
            "entry_transition_length": float(widgets["entry_transition"].value()),
            "exit_transition_length": float(widgets["exit_transition"].value()),
            "width": float(widgets["width"].value()),
            "create_template": bool(widgets["template"].isChecked()),
            "show_centreline": bool(widgets["centreline"].isChecked()),
        }

    def _duplicate_selected_track(self):
        row = self.track_table.currentRow()
        config = self._row_config(row)
        if config is None or self.parallel_count_box.value() >= MAX_PARALLEL_TRACKS:
            return
        config["name"] = "{} copy".format(config["name"])
        new_row = self.track_table.rowCount()
        self.parallel_count_box.setValue(new_row + 1)
        self._populate_row(new_row, config)
        self.track_table.selectRow(new_row)

    def _populate_row(self, row, config):
        name_box = QtWidgets.QLineEdit(str(config["name"]))

        side_box = QtWidgets.QComboBox()
        side_box.addItems(["Outside", "Inside"])
        side_box.setCurrentIndex(1 if config["side"] == "Inside" else 0)

        mode_box = QtWidgets.QComboBox()
        mode_box.addItems([MODE_MATCH_SPACINGS, MODE_USE_LENGTHS, MODE_PLATFORM])
        selected_mode = config["alignment_mode"]
        mode_index = {
            MODE_MATCH_SPACINGS: 0,
            MODE_USE_LENGTHS: 1,
            MODE_PLATFORM: 2,
        }.get(selected_mode, 0)
        mode_box.setCurrentIndex(mode_index)

        start_box = self._length_box(config["start_spacing"], 0.001, 100000.0, 1.0)
        curve_box = self._length_box(config["curve_spacing"], 0.001, 100000.0, 1.0)
        finish_box = self._length_box(config["finish_spacing"], 0.001, 100000.0, 1.0)
        entry_box = self._length_box(
            config["entry_transition_length"], 0.0, 100000.0, 10.0
        )
        exit_box = self._length_box(
            config["exit_transition_length"], 0.0, 100000.0, 10.0
        )
        width_box = self._length_box(config["width"], 0.1, 1000.0, 1.0)
        template_box = self._checkbox(config["create_template"])
        centreline_box = self._checkbox(config["show_centreline"])

        name_box.setToolTip(
            "Name used for this track and its generated FreeCAD centreline object."
        )
        name_box.textChanged.connect(self._refresh_platform_track_choices)
        side_box.setToolTip(
            "Outside increases the main constant radius by the Curve spacing. "
            "Inside decreases it by the Curve spacing."
        )
        mode_box.setToolTip(
            "Euler - match spacings solves standard Euler easement lengths. "
            "Euler - use lengths honours standard Euler lengths and calculates "
            "the straight spacings. Platform widening honours both the entered "
            "spacings and transition lengths using continuous same-direction "
            "compound curvature."
        )
        start_box.setToolTip(
            "Perpendicular centre-to-centre spacing from the main track on the "
            "entry straight."
        )
        curve_box.setToolTip(
            "Exact radial centre-to-centre spacing through the concentric "
            "constant-radius section."
        )
        finish_box.setToolTip(
            "Perpendicular centre-to-centre spacing from the main track on the "
            "exit straight."
        )
        entry_box.setToolTip(
            "Entry transition length for the selected alignment mode."
        )
        exit_box.setToolTip(
            "Exit transition length for the selected alignment mode."
        )
        width_box.setToolTip(
            "Width of this track's printable strip. A value of 32 mm represents "
            "an 8 ft prototype sleeper at OO scale."
        )
        template_box.setToolTip(
            "Create this track's solid printable template strip."
        )
        centreline_box.setToolTip(
            "Create and display this track's coloured centreline."
        )

        self.track_table.setCellWidget(row, self.COLUMNS["name"], name_box)
        self.track_table.setCellWidget(row, self.COLUMNS["side"], side_box)
        self.track_table.setCellWidget(row, self.COLUMNS["mode"], mode_box)
        self.track_table.setCellWidget(row, self.COLUMNS["start"], start_box)
        self.track_table.setCellWidget(row, self.COLUMNS["curve"], curve_box)
        self.track_table.setCellWidget(row, self.COLUMNS["finish"], finish_box)
        self.track_table.setCellWidget(row, self.COLUMNS["entry_transition"], entry_box)
        self.track_table.setCellWidget(row, self.COLUMNS["exit_transition"], exit_box)
        self.track_table.setCellWidget(row, self.COLUMNS["width"], width_box)
        self.track_table.setCellWidget(row, self.COLUMNS["template"], template_box)
        self.track_table.setCellWidget(row, self.COLUMNS["centreline"], centreline_box)

        mode_box.currentIndexChanged.connect(
            lambda _value, selected_row=row: self._update_row_mode(selected_row)
        )
        self._update_row_mode(row)

    def _update_row_mode(self, row):
        mode_box = self.track_table.cellWidget(row, self.COLUMNS["mode"])
        start_box = self.track_table.cellWidget(row, self.COLUMNS["start"])
        finish_box = self.track_table.cellWidget(row, self.COLUMNS["finish"])
        entry_box = self.track_table.cellWidget(row, self.COLUMNS["entry_transition"])
        exit_box = self.track_table.cellWidget(row, self.COLUMNS["exit_transition"])
        if any(widget is None for widget in (mode_box, start_box, finish_box, entry_box, exit_box)):
            return

        selected_mode = str(mode_box.currentText())
        match_spacings = selected_mode == MODE_MATCH_SPACINGS
        platform_mode = selected_mode == MODE_PLATFORM

        start_box.setEnabled(match_spacings or platform_mode)
        finish_box.setEnabled(match_spacings or platform_mode)
        entry_box.setEnabled(not match_spacings)
        exit_box.setEnabled(not match_spacings)

        if match_spacings:
            entry_box.setToolTip(
                "Calculated automatically to achieve the requested Entry spacing "
                "using a standard Euler easement."
            )
            exit_box.setToolTip(
                "Calculated automatically to achieve the requested Exit spacing "
                "using a standard Euler easement."
            )
            start_box.setToolTip(
                "Requested perpendicular centre-to-centre spacing from the main "
                "track on the entry straight."
            )
            finish_box.setToolTip(
                "Requested perpendicular centre-to-centre spacing from the main "
                "track on the exit straight."
            )
        elif platform_mode:
            entry_box.setToolTip(
                "Exact length of the same-direction platform widening transition "
                "on the entry side. Shorter lengths require tighter peak curvature."
            )
            exit_box.setToolTip(
                "Exact length of the same-direction platform narrowing transition "
                "on the exit side. Shorter lengths require tighter peak curvature."
            )
            start_box.setToolTip(
                "Exact entry-straight centre spacing. Platform widening solves a "
                "continuous positive-curvature profile to reach Curve spacing."
            )
            finish_box.setToolTip(
                "Exact exit-straight centre spacing. Platform widening solves a "
                "continuous positive-curvature profile from Curve spacing."
            )
        else:
            entry_box.setToolTip(
                "Entered independent standard Euler entry-easement length."
            )
            exit_box.setToolTip(
                "Entered independent standard Euler exit-easement length."
            )
            start_box.setToolTip(
                "Calculated entry-straight spacing produced by the entered Entry "
                "Euler easement length."
            )
            finish_box.setToolTip(
                "Calculated exit-straight spacing produced by the entered Exit "
                "Euler easement length."
            )

    def _straight_selection_changed(self):
        if self._straight_loading:
            return
        self._straight_current_index = self.straight_table.currentRow()

    def _straight_row_config(self, row):
        if row < 0 or row >= self.straight_table.rowCount():
            return None
        widgets = {
            key: self.straight_table.cellWidget(row, column)
            for key, column in self.STRAIGHT_COLUMNS.items()
        }
        if any(widget is None for widget in widgets.values()):
            return None
        existing_id = ""
        if row < len(self._straight_configs):
            existing_id = str(
                self._straight_configs[row].get("manager_id", "")
            ).strip()
        config = {
            "manager_id": existing_id or new_straight_manager_id(),
            "enabled": bool(widgets["enabled"].isChecked()),
            "name": str(widgets["name"].text()).strip()
            or "Straight {}".format(row + 1),
            "connection_mode": str(widgets["connection"].currentText()),
            "length": float(widgets["length"].value()),
            "direction": str(widgets["direction"].currentText()),
            "track_count": int(widgets["track_count"].value()),
            "track_spacing": float(widgets["spacing"].value()),
            "parallel_side": str(widgets["side"].currentText()),
            "template_width": float(widgets["width"].value()),
            "template_thickness": float(widgets["thickness"].value()),
            "start_x": float(widgets["start_x"].value()),
            "start_y": float(widgets["start_y"].value()),
            "rotation_degrees": float(widgets["rotation"].value()),
            "create_template": bool(widgets["template"].isChecked()),
            "show_centreline": bool(widgets["centreline"].isChecked()),
        }
        return clone_straight_config(config, row)

    def _populate_straight_row(self, row, config):
        config = clone_straight_config(config, row)
        enabled_box = self._checkbox(config["enabled"])
        name_box = QtWidgets.QLineEdit(config["name"])

        connection_box = QtWidgets.QComboBox()
        connection_box.addItems(
            [
                STRAIGHT_CONNECTION_INDEPENDENT,
                STRAIGHT_CONNECTION_CURVE_ENTRANCE,
                STRAIGHT_CONNECTION_CURVE_EXIT,
            ]
        )
        connection_box.setCurrentIndex(
            {
                STRAIGHT_CONNECTION_INDEPENDENT: 0,
                STRAIGHT_CONNECTION_CURVE_ENTRANCE: 1,
                STRAIGHT_CONNECTION_CURVE_EXIT: 2,
            }.get(config["connection_mode"], 0)
        )

        length_box = self._length_box(config["length"], 0.001, 1000000.0, 10.0)
        direction_box = QtWidgets.QComboBox()
        direction_box.addItems(
            [STRAIGHT_DIRECTION_FORWARD, STRAIGHT_DIRECTION_REVERSE]
        )
        direction_box.setCurrentIndex(
            1 if config["direction"] == STRAIGHT_DIRECTION_REVERSE else 0
        )
        track_count_box = QtWidgets.QSpinBox()
        track_count_box.setRange(1, MAX_PARALLEL_TRACKS + 1)
        track_count_box.setValue(config["track_count"])
        spacing_box = self._length_box(
            config["track_spacing"], 0.001, 100000.0, 1.0
        )
        side_box = QtWidgets.QComboBox()
        side_box.addItems([STRAIGHT_PARALLEL_LEFT, STRAIGHT_PARALLEL_RIGHT])
        side_box.setCurrentIndex(
            1 if config["parallel_side"] == STRAIGHT_PARALLEL_RIGHT else 0
        )
        width_box = self._length_box(
            config["template_width"], 0.001, 10000.0, 1.0
        )
        thickness_box = self._length_box(
            config["template_thickness"], 0.001, 1000.0, 0.1
        )
        start_x_box = self._number_box(
            config["start_x"], -1000000.0, 1000000.0, " mm", 10.0
        )
        start_y_box = self._number_box(
            config["start_y"], -1000000.0, 1000000.0, " mm", 10.0
        )
        rotation_box = self._number_box(
            config["rotation_degrees"], -360.0, 360.0, " deg", 1.0
        )
        template_box = self._checkbox(config["create_template"])
        centreline_box = self._checkbox(config["show_centreline"])

        widgets = {
            "enabled": enabled_box,
            "name": name_box,
            "connection": connection_box,
            "length": length_box,
            "direction": direction_box,
            "track_count": track_count_box,
            "spacing": spacing_box,
            "side": side_box,
            "width": width_box,
            "thickness": thickness_box,
            "start_x": start_x_box,
            "start_y": start_y_box,
            "rotation": rotation_box,
            "template": template_box,
            "centreline": centreline_box,
        }
        for key, widget in widgets.items():
            self.straight_table.setCellWidget(
                row, self.STRAIGHT_COLUMNS[key], widget
            )
        if row >= len(self._straight_configs):
            self._straight_configs.append(config)
        else:
            self._straight_configs[row] = config
        connection_box.currentIndexChanged.connect(
            self._update_all_straight_row_modes
        )

    def _update_all_straight_row_modes(self, *_args):
        if self._straight_loading:
            return
        for row in range(self.straight_table.rowCount()):
            connection_box = self.straight_table.cellWidget(
                row, self.STRAIGHT_COLUMNS["connection"]
            )
            if connection_box is None:
                continue
            independent = (
                str(connection_box.currentText())
                == STRAIGHT_CONNECTION_INDEPENDENT
            )
            track_count_widget = self.straight_table.cellWidget(
                row, self.STRAIGHT_COLUMNS["track_count"]
            )
            if not independent and track_count_widget is not None:
                track_count_widget.setValue(1 + self.track_table.rowCount())
            for key in (
                "direction",
                "track_count",
                "spacing",
                "side",
                "width",
                "thickness",
                "start_x",
                "start_y",
                "rotation",
            ):
                widget = self.straight_table.cellWidget(
                    row, self.STRAIGHT_COLUMNS[key]
                )
                if widget is not None:
                    widget.setEnabled(independent)
            connection_box.setToolTip(
                "Independent routes use the entered datum and geometry. Connected routes inherit the exact curve endpoints, headings, track centres and widths."
            )

    def _add_straight(self):
        if self.straight_table.rowCount() >= MAX_STRAIGHT_ROUTES:
            return
        row = self.straight_table.rowCount()
        config = default_straight_config(row)
        self.straight_table.setRowCount(row + 1)
        self._populate_straight_row(row, config)
        self._update_all_straight_row_modes()
        self.straight_table.selectRow(row)

    def _add_curve_connection_pair(self):
        # This is deliberately a deterministic test control. Earlier revisions
        # appended the connected pair and left independent datum rows enabled,
        # which could reproduce the original forward/reverse test and mask the
        # connected geometry. Replace every row so the accepted values can only
        # contain one entrance route and one exit route.
        entrance_config = default_straight_config(0)
        entrance_config["name"] = "Curve Entrance Straight"
        entrance_config["connection_mode"] = (
            STRAIGHT_CONNECTION_CURVE_ENTRANCE
        )
        entrance_config["direction"] = STRAIGHT_DIRECTION_FORWARD
        entrance_config["track_count"] = 1 + self.track_table.rowCount()

        exit_config = default_straight_config(1)
        exit_config["name"] = "Curve Exit Straight"
        exit_config["connection_mode"] = STRAIGHT_CONNECTION_CURVE_EXIT
        exit_config["direction"] = STRAIGHT_DIRECTION_FORWARD
        exit_config["track_count"] = 1 + self.track_table.rowCount()

        self._straight_configs = clone_straight_configs(
            [entrance_config, exit_config]
        )
        self._straight_loading = True
        try:
            self.straight_table.setRowCount(0)
            self.straight_table.setRowCount(2)
            for index, config in enumerate(self._straight_configs):
                self._populate_straight_row(index, config)
        finally:
            self._straight_loading = False
        self._update_all_straight_row_modes()
        self._straight_current_index = 0
        self.straight_table.selectRow(0)

    def _remove_selected_straight(self):
        row = self.straight_table.currentRow()
        if row < 0 or row >= self.straight_table.rowCount():
            return
        configs = self._straight_values()
        del configs[row]
        self._straight_configs = configs
        self._straight_loading = True
        self.straight_table.setRowCount(0)
        self.straight_table.setRowCount(len(configs))
        for index, config in enumerate(configs):
            self._populate_straight_row(index, config)
        self._straight_loading = False
        self._update_all_straight_row_modes()
        if configs:
            new_row = min(row, len(configs) - 1)
            self.straight_table.selectRow(new_row)
            self._straight_current_index = new_row
        else:
            self._straight_current_index = -1

    def _duplicate_selected_straight(self):
        row = self.straight_table.currentRow()
        config = self._straight_row_config(row)
        if config is None or self.straight_table.rowCount() >= MAX_STRAIGHT_ROUTES:
            return
        config["manager_id"] = new_straight_manager_id()
        config["name"] = "{} copy".format(config["name"])
        new_row = self.straight_table.rowCount()
        self.straight_table.setRowCount(new_row + 1)
        self._populate_straight_row(new_row, config)
        self._update_all_straight_row_modes()
        self.straight_table.selectRow(new_row)

    def _straight_values(self):
        configs = []
        for row in range(self.straight_table.rowCount()):
            config = self._straight_row_config(row)
            if config is None:
                raise ValueError(
                    "Straight row {} is incomplete. Close and reopen the macro.".format(
                        row + 1
                    )
                )
            configs.append(config)
        self._straight_configs = clone_straight_configs(configs)
        return self._straight_configs

    def _platform_track_labels(self):
        labels = ["Main Track"]
        for row in range(self.track_table.rowCount()):
            name_widget = self.track_table.cellWidget(row, self.COLUMNS["name"])
            name = str(name_widget.text()).strip() if name_widget is not None else ""
            labels.append(name or "Track {}".format(row + 2))
        return labels

    def _set_platform_track_choices(self, selected_a, selected_b):
        labels = self._platform_track_labels()
        for combo, selected in (
            (self.platform_track_a_box, selected_a),
            (self.platform_track_b_box, selected_b),
        ):
            combo.blockSignals(True)
            combo.clear()
            combo.addItems(labels)
            combo.setCurrentIndex(min(max(0, int(selected)), len(labels) - 1))
            combo.blockSignals(False)

    def _refresh_platform_track_choices(self, *_args):
        if not hasattr(self, "platform_track_a_box"):
            return
        current_a = max(0, self.platform_track_a_box.currentIndex())
        current_b = max(0, self.platform_track_b_box.currentIndex())
        self._set_platform_track_choices(current_a, current_b)
        if not self._platform_loading:
            self._save_platform_editor_to_config()
            self._refresh_platform_manager_table(self._platform_current_index)

    def _read_platform_editor_config(self):
        manager_id = ""
        if 0 <= self._platform_current_index < len(self._platform_configs):
            manager_id = str(
                self._platform_configs[self._platform_current_index].get(
                    "manager_id", ""
                )
            ).strip()
        if not manager_id:
            manager_id = new_platform_manager_id()
        return clone_platform_config({
            "manager_id": manager_id,
            "defaults_version": PLATFORM_DEFAULTS_SCHEMA_VERSION,
            "outside_platform_preset_version": OUTSIDE_PLATFORM_PRESET_VERSION,
            "enabled": bool(self.platform_enabled_box.isChecked()),
            "name": str(self.platform_name_box.text()).strip() or "Platform {}".format(
                self._platform_current_index + 1
            ),
            "arrangement": str(self.platform_arrangement_box.currentText()),
            "track_a_index": int(self.platform_track_a_box.currentIndex()),
            "track_b_index": int(self.platform_track_b_box.currentIndex()),
            "outside_side": str(self.platform_outside_side_box.currentText()),
            "clearance_a": float(self.platform_clearance_a_box.value()),
            "clearance_b": float(self.platform_clearance_b_box.value()),
            "coverage": str(self.platform_coverage_box.currentText()),
            "platform_length": float(self.platform_length_box.value()),
            "centre_offset": float(self.platform_centre_offset_box.value()),
            "entry_end_style": str(self.platform_entry_end_style_box.currentText()),
            "exit_end_style": str(self.platform_exit_end_style_box.currentText()),
            "match_end_profiles": bool(
                self.platform_match_end_profiles_box.isChecked()
            ),
            "entry_taper_length": float(
                self.platform_entry_taper_length_box.value()
            ),
            "exit_taper_length": float(
                self.platform_exit_taper_length_box.value()
            ),
            "platform_width": float(self.platform_width_box.value()),
            "required_clearance": float(
                self.platform_required_clearance_box.value()
            ),
            "check_clearance": bool(
                self.platform_check_clearance_box.isChecked()
            ),
            "create_edges": bool(self.platform_create_edges_box.isChecked()),
            "show_edges": bool(self.platform_show_edges_box.isChecked()),
            "body_output": str(self.platform_body_output_box.currentText()),
            "platform_height": float(self.platform_height_box.value()),
            "show_body": bool(self.platform_show_body_box.isChecked()),
            "export_stl": False,
            "stl_directory": "",
        })

    def _save_platform_editor_to_config(self, index=None):
        if self._platform_loading or not self._platform_configs:
            return
        target = self._platform_current_index if index is None else int(index)
        if 0 <= target < len(self._platform_configs):
            self._platform_configs[target] = self._read_platform_editor_config()

    def _load_platform_editor(self, index):
        if not self._platform_configs:
            self._platform_configs = [default_platform_config()]
        index = min(max(0, int(index)), len(self._platform_configs) - 1)
        config = clone_platform_config(self._platform_configs[index])
        self._platform_current_index = index
        self._platform_loading = True
        try:
            self.platform_enabled_box.setChecked(config["enabled"])
            self.platform_name_box.setText(config["name"])
            self.platform_arrangement_box.setCurrentIndex(
                1 if config["arrangement"] == PLATFORM_OUTSIDE else 0
            )
            self._set_platform_track_choices(
                config["track_a_index"], config["track_b_index"]
            )
            self.platform_outside_side_box.setCurrentIndex(
                1 if config["outside_side"] == PLATFORM_RIGHT else 0
            )
            self.platform_clearance_a_box.setValue(config["clearance_a"])
            self.platform_clearance_b_box.setValue(config["clearance_b"])
            coverage_index = {
                PLATFORM_CONSTANT: 0,
                PLATFORM_ENTRY: 1,
                PLATFORM_EXIT: 2,
                PLATFORM_CORE: 3,
            }.get(config["coverage"], 0)
            self.platform_coverage_box.setCurrentIndex(coverage_index)
            self.platform_length_box.setValue(config["platform_length"])
            self.platform_centre_offset_box.setValue(config["centre_offset"])
            self.platform_match_end_profiles_box.setChecked(
                config["match_end_profiles"]
            )
            self.platform_entry_end_style_box.setCurrentIndex(
                1 if config["entry_end_style"] == PLATFORM_END_TAPERED else 0
            )
            self.platform_exit_end_style_box.setCurrentIndex(
                1 if config["exit_end_style"] == PLATFORM_END_TAPERED else 0
            )
            self.platform_entry_taper_length_box.setValue(
                config["entry_taper_length"]
            )
            self.platform_exit_taper_length_box.setValue(
                config["exit_taper_length"]
            )
            self.platform_width_box.setValue(config["platform_width"])
            self.platform_required_clearance_box.setValue(
                config["required_clearance"]
            )
            self.platform_check_clearance_box.setChecked(
                config["check_clearance"]
            )
            self.platform_create_edges_box.setChecked(config["create_edges"])
            self.platform_show_edges_box.setChecked(config["show_edges"])
            output_index = {
                PLATFORM_EDGES_ONLY: 0,
                PLATFORM_FACE: 1,
                PLATFORM_SOLID: 2,
            }.get(config["body_output"], 2)
            self.platform_body_output_box.setCurrentIndex(output_index)
            self.platform_height_box.setValue(config["platform_height"])
            self.platform_show_body_box.setChecked(config["show_body"])
        finally:
            self._platform_loading = False
        self._update_platform_controls()
        self._refresh_platform_manager_table(index)

    def _refresh_platform_manager_table(self, selected_index=None):
        if not hasattr(self, "platform_table"):
            return
        if selected_index is None:
            selected_index = self._platform_current_index
        labels = self._platform_track_labels()
        previous_loading = self._platform_loading
        self._platform_loading = True
        self.platform_table.blockSignals(True)
        try:
            self.platform_table.setRowCount(len(self._platform_configs))
            for row, config in enumerate(self._platform_configs):
                config = clone_platform_config(config)
                track_a = (
                    labels[config["track_a_index"]]
                    if config["track_a_index"] < len(labels)
                    else "Missing track"
                )
                if config["arrangement"] == PLATFORM_BETWEEN:
                    track_b = (
                        labels[config["track_b_index"]]
                        if config["track_b_index"] < len(labels)
                        else "Missing track"
                    )
                else:
                    track_b = config["outside_side"]
                entry_end = (
                    PLATFORM_END_TAPERED_LABEL
                    if config["entry_end_style"] == PLATFORM_END_TAPERED
                    else PLATFORM_END_SQUARE
                )
                values = [
                    "Yes" if config["enabled"] else "No",
                    config["name"],
                    config["arrangement"],
                    track_a,
                    track_b,
                    config["coverage"],
                    entry_end,
                    config["body_output"],
                    "{:.3f} mm".format(config["platform_length"]),
                ]
                for column, value in enumerate(values):
                    self.platform_table.setItem(
                        row, column, QtWidgets.QTableWidgetItem(str(value))
                    )
            if self._platform_configs:
                selected_index = min(
                    max(0, int(selected_index)), len(self._platform_configs) - 1
                )
                self.platform_table.selectRow(selected_index)
        finally:
            self.platform_table.blockSignals(False)
            self._platform_loading = previous_loading
        self._update_platform_manager_buttons()

    def _update_platform_manager_buttons(self):
        count = len(self._platform_configs)
        index = self._platform_current_index
        self.add_platform_button.setEnabled(count < MAX_PLATFORMS)
        self.duplicate_platform_button.setEnabled(count < MAX_PLATFORMS)
        self.remove_platform_button.setEnabled(count > 0)
        self.move_platform_up_button.setEnabled(index > 0)
        self.move_platform_down_button.setEnabled(index < count - 1)

    def _platform_selection_changed(self):
        if self._platform_loading:
            return
        selected = int(self.platform_table.currentRow())
        if selected < 0 or selected >= len(self._platform_configs):
            return
        if selected == self._platform_current_index:
            return
        self._save_platform_editor_to_config(self._platform_current_index)
        self._load_platform_editor(selected)

    def _platform_editor_changed(self, *_args):
        if self._platform_loading:
            return
        self._save_platform_editor_to_config()
        self._refresh_platform_manager_table(self._platform_current_index)
        if hasattr(self, "production_export_enabled_box"):
            self._update_production_export_controls()

    def _unique_platform_name(self, base_name):
        existing = {
            str(config.get("name", "")).strip().casefold()
            for config in self._platform_configs
        }
        candidate = str(base_name).strip() or "Platform"
        if candidate.casefold() not in existing:
            return candidate[:MAX_PLATFORM_NAME_LENGTH]
        number = 2
        while True:
            suffix = " {}".format(number)
            trimmed = candidate[:max(1, MAX_PLATFORM_NAME_LENGTH - len(suffix))]
            proposed = "{}{}".format(trimmed, suffix)
            if proposed.casefold() not in existing:
                return proposed
            number += 1

    def _add_platform(self):
        self._save_platform_editor_to_config()
        if len(self._platform_configs) >= MAX_PLATFORMS:
            QtWidgets.QMessageBox.information(
                self,
                versioned_dialog_title("Platform limit"),
                "A maximum of {} platform definitions is supported.".format(
                    MAX_PLATFORMS
                ),
            )
            return
        config = default_platform_config()
        config["enabled"] = True
        config["name"] = self._unique_platform_name(
            "Platform {}".format(len(self._platform_configs) + 1)
        )
        self._platform_configs.append(config)
        self._load_platform_editor(len(self._platform_configs) - 1)

    def _duplicate_platform(self):
        self._save_platform_editor_to_config()
        if len(self._platform_configs) >= MAX_PLATFORMS:
            QtWidgets.QMessageBox.information(
                self,
                versioned_dialog_title("Platform limit"),
                "A maximum of {} platform definitions is supported.".format(
                    MAX_PLATFORMS
                ),
            )
            return
        source = clone_platform_config(
            self._platform_configs[self._platform_current_index]
        )
        source["manager_id"] = new_platform_manager_id()
        source["name"] = self._unique_platform_name(
            "{} Copy".format(source["name"])
        )
        insert_at = self._platform_current_index + 1
        self._platform_configs.insert(insert_at, source)
        self._load_platform_editor(insert_at)

    def _remove_platform(self):
        self._save_platform_editor_to_config()
        if len(self._platform_configs) <= 1:
            self._platform_configs = [default_platform_config()]
            self._load_platform_editor(0)
            return
        del self._platform_configs[self._platform_current_index]
        new_index = min(
            self._platform_current_index, len(self._platform_configs) - 1
        )
        self._load_platform_editor(new_index)

    def _move_platform_up(self):
        self._save_platform_editor_to_config()
        index = self._platform_current_index
        if index <= 0:
            return
        self._platform_configs[index - 1], self._platform_configs[index] = (
            self._platform_configs[index],
            self._platform_configs[index - 1],
        )
        self._load_platform_editor(index - 1)

    def _move_platform_down(self):
        self._save_platform_editor_to_config()
        index = self._platform_current_index
        if index >= len(self._platform_configs) - 1:
            return
        self._platform_configs[index + 1], self._platform_configs[index] = (
            self._platform_configs[index],
            self._platform_configs[index + 1],
        )
        self._load_platform_editor(index + 1)

    def _browse_production_export_directory(self):
        start = str(self.production_export_directory_box.text()).strip()
        selected = QtWidgets.QFileDialog.getExistingDirectory(
            self,
            "Select production export directory",
            start,
        )
        if selected:
            self.production_export_directory_box.setText(str(selected))

    def _open_production_schedule(self):
        doc = getattr(App, "ActiveDocument", None)
        if doc is None:
            QtWidgets.QMessageBox.information(
                self,
                versioned_dialog_title("Production schedule"),
                "Open a FreeCAD document containing a generated template set first.",
            )
            return
        dialog = ProductionScheduleDialog(doc, self)
        dialog_exec(dialog)

    def _open_material_report(self):
        doc = getattr(App, "ActiveDocument", None)
        if doc is None:
            QtWidgets.QMessageBox.information(
                self,
                versioned_dialog_title("Material and length report"),
                "Open a FreeCAD document containing a generated template set first.",
            )
            return
        dialog = MaterialLengthReportDialog(doc, self)
        dialog_exec(dialog)
        self._material_report_config = read_last_material_report_config()

    def _open_production_preflight(self):
        doc = getattr(App, "ActiveDocument", None)
        if doc is None:
            QtWidgets.QMessageBox.information(
                self,
                versioned_dialog_title("Production preflight"),
                "Open a FreeCAD document containing a generated template set first.",
            )
            return
        dialog = ProductionPreflightDialog(doc, self)
        dialog_exec(dialog)

    def _open_assembly_labels(self):
        doc = getattr(App, "ActiveDocument", None)
        if doc is None:
            QtWidgets.QMessageBox.information(
                self,
                versioned_dialog_title("Assembly labels"),
                "Open a FreeCAD document containing a generated template set first.",
            )
            return
        dialog = AssemblyLabelDialog(doc, self)
        dialog_exec(dialog)
        settings = latest_generated_settings(doc)
        if settings is not None:
            self._assembly_label_config = read_assembly_label_config(settings)

    def _open_selected_export(self):
        doc = getattr(App, "ActiveDocument", None)
        if doc is None:
            QtWidgets.QMessageBox.information(
                self,
                versioned_dialog_title("Export selected production items"),
                "Open a FreeCAD document containing a generated template set first.",
            )
            return
        dialog = SelectedProductionExportDialog(doc, self)
        dialog_exec(dialog)

    def _open_configuration_io(self):
        try:
            dialog = ConfigurationImportExportDialog(self, self)
            dialog_exec(dialog)
        except Exception as error:
            show_error(str(error))

    def _open_named_presets(self):
        try:
            dialog = NamedPresetManagerDialog(self, self)
            dialog_exec(dialog)
        except Exception as error:
            show_error(str(error))

    def _open_turnout_manager(self):
        doc = getattr(App, "ActiveDocument", None)
        if doc is None:
            QtWidgets.QMessageBox.information(
                self,
                versioned_dialog_title("REA C10 turnout manager"),
                "Open a FreeCAD document containing a generated template set first.",
            )
            return
        try:
            dialog = TurnoutManagerDialog(doc, self)
            dialog_exec(dialog)
        except Exception as error:
            show_error(str(error))

    def _open_crossover_manager(self):
        # Compatibility entry point: crossovers now live in the unified turnout manager.
        self._open_turnout_manager()

    def build_current_configuration_payload(self):
        (
            transition,
            radius,
            angle,
            main_width,
            track_configs,
            straight_configs,
            _selected_straight_index,
            platform_configs,
            _selected_platform_id,
            _selected_platform_index,
            formation_config,
            section_config,
            registration_config,
            template_assembly_config,
            assembly_label_config,
            production_export_config,
            material_report_config,
            output_mode,
        ) = self.values()
        return build_complete_configuration_payload(
            transition,
            radius,
            angle,
            main_width,
            track_configs,
            straight_configs,
            platform_configs,
            formation_config,
            section_config,
            registration_config,
            template_assembly_config,
            assembly_label_config,
            production_export_config,
            material_report_config,
            output_mode,
            presets=self._configuration_presets,
        )

    @staticmethod
    def _set_combo_text(combo, text):
        index = combo.findText(str(text))
        if index < 0:
            raise ValueError(
                "The imported value '{}' is unavailable in the current dialogue.".format(text)
            )
        combo.setCurrentIndex(index)

    def apply_configuration_payload(self, payload):
        normalised = normalise_configuration_payload(payload)
        config = normalised["configuration"]
        curve = config["curve"]
        # Complete the transported-preset merge before changing any widget. If
        # the combined library would exceed limits or fail validation, the
        # open dialogue remains completely unchanged.
        merged_presets, preset_merge_report = merge_named_preset_collections(
            self._configuration_presets,
            normalised.get("presets", []),
        )

        self.transition_box.setValue(curve["transition"])
        self.radius_box.setValue(curve["radius"])
        self.angle_box.setValue(curve["angle"])
        self.main_width_box.setValue(curve["main_width"])

        tracks = [
            clone_track_config(item, curve["transition"])
            for item in config["tracks"]
        ]
        self.parallel_count_box.setValue(len(tracks))
        self.track_table.setRowCount(len(tracks))
        for row, track in enumerate(tracks):
            self._populate_row(row, track)

        straight_configs = clone_straight_configs(config["straight_routes"])
        self._straight_loading = True
        try:
            self._straight_configs = straight_configs
            self.straight_table.setRowCount(0)
            self.straight_table.setRowCount(len(straight_configs))
            for index, straight in enumerate(straight_configs):
                self._populate_straight_row(index, straight)
        finally:
            self._straight_loading = False
        self._update_all_straight_row_modes()
        self._straight_current_index = 0 if straight_configs else -1
        if straight_configs:
            self.straight_table.selectRow(0)

        self._platform_configs = clone_platform_configs(config["platforms"])
        self._platform_current_index = 0
        self._refresh_platform_track_choices()
        self._refresh_platform_manager_table(0)
        self._load_platform_editor(0)

        formation = config["formation_board"]
        self.formation_enabled_box.setChecked(formation["enabled"])
        self.formation_include_tracks_box.setChecked(formation["include_track_templates"])
        self.formation_include_platform_box.setChecked(formation["include_platform"])
        self.formation_margin_box.setValue(formation["outer_margin"])
        self.formation_neck_box.setValue(formation["minimum_neck_width"])
        self.formation_fill_gaps_box.setChecked(formation["fill_enclosed_gaps"])
        self.formation_smooth_box.setChecked(formation["smooth_outline"])
        self.formation_smoothing_tolerance_box.setValue(formation["smoothing_tolerance"])
        self._set_combo_text(self.formation_output_type_box, formation["output_type"])
        self.formation_thickness_box.setValue(formation["board_thickness"])
        self.formation_show_outline_box.setChecked(formation["show_outline"])
        self.formation_show_solid_box.setChecked(formation["show_solid"])
        self.formation_track_engraving_box.setChecked(formation["create_track_engraving"])
        self.formation_platform_engraving_box.setChecked(formation["create_platform_engraving"])

        sectioning = config["sectioning"]
        self.section_enabled_box.setChecked(sectioning["enabled"])
        self.section_max_length_box.setValue(sectioning["maximum_section_length"])
        self.section_balance_box.setChecked(sectioning["balance_lengths"])
        self.section_min_length_box.setValue(sectioning["minimum_section_length"])
        self.section_tracks_box.setChecked(sectioning["section_track_templates"])
        self.section_platform_box.setChecked(sectioning["section_platform"])
        self.section_formation_box.setChecked(sectioning["section_formation"])
        self.section_preserve_box.setChecked(sectioning["preserve_unsplit"])
        self.section_number_box.setChecked(sectioning["number_in_travel_order"])

        registration = config["registration"]
        self._set_combo_text(self.registration_type_box, registration["joint_type"])
        self.registration_depth_box.setValue(registration["joint_depth"])
        self.registration_width_box.setValue(registration["joint_width"])
        self.registration_clearance_box.setValue(registration["fit_clearance"])
        self.registration_hole_diameter_box.setValue(registration["alignment_hole_diameter"])
        self.registration_hole_offset_box.setValue(registration["alignment_hole_offset"])

        assembly = config["template_joints"]
        self.template_assembly_enabled_box.setChecked(assembly["enabled"])
        self._set_combo_text(self.template_joint_type_box, assembly["joint_type"])
        self.template_joint_depth_box.setValue(assembly["joint_depth"])
        self.template_joint_width_box.setValue(assembly["joint_width"])
        self.template_joint_clearance_box.setValue(assembly["fit_clearance"])
        self.template_fixing_holes_box.setChecked(assembly["fixing_holes_enabled"])
        self.template_holes_per_section_box.setValue(assembly["holes_per_section"])
        self.template_hole_diameter_box.setValue(assembly["hole_diameter"])
        self.template_hole_end_clearance_box.setValue(assembly["minimum_end_clearance"])
        self.template_matching_formation_holes_box.setChecked(assembly["matching_formation_holes"])
        self.template_show_hole_geometry_box.setChecked(assembly["show_hole_geometry"])

        production = config["production_export"]
        self.production_export_enabled_box.setChecked(production["enabled"])
        self.production_export_directory_box.setText(production["output_directory"])
        self.production_include_role_box.setChecked(production["include_object_role"])
        self.production_include_track_box.setChecked(production["include_track_number"])
        self.production_include_section_box.setChecked(production["include_section_number"])
        self.production_each_section_box.setChecked(production["export_each_section"])
        self.production_combined_box.setChecked(production["create_combined_files"])
        self.production_overwrite_box.setChecked(production["overwrite_existing"])
        self.production_manifest_box.setChecked(production["create_manifest"])
        self.production_open_directory_box.setChecked(production["open_output_directory"])
        for key, box in self.production_format_boxes.items():
            box.setChecked(bool(production["formats"].get(key, False)))
        for key, box in self.production_selection_boxes.items():
            box.setChecked(bool(production["selections"].get(key, False)))

        self._assembly_label_config = validate_assembly_label_config(
            config["assembly_labels"]
        )
        self._material_report_config = validate_material_report_config(
            config["material_report"]
        )
        self._configuration_presets = merged_presets
        self._last_preset_merge_report = preset_merge_report
        self._set_combo_text(
            self.output_mode_box,
            config["production_utilities"]["output_mode"],
        )
        self._update_formation_section_controls()
        self._update_production_export_controls()

    def _platform_arrangement_changed(self, *_args):
        if not hasattr(self, "platform_arrangement_box"):
            return
        apply_outside_defaults = bool(
            not self._platform_loading
            and str(self.platform_arrangement_box.currentText()) == PLATFORM_OUTSIDE
        )
        if apply_outside_defaults:
            # Block the individual editor signals while the complete outside-
            # platform preset is applied, then save the finished configuration
            # once. This prevents an intermediate value from overwriting the
            # preset or leaving the manager row out of sync.
            widgets = (
                self.platform_width_box,
                self.platform_coverage_box,
                self.platform_match_end_profiles_box,
                self.platform_entry_end_style_box,
                self.platform_exit_end_style_box,
                self.platform_entry_taper_length_box,
                self.platform_exit_taper_length_box,
                self.platform_body_output_box,
                self.platform_show_body_box,
            )
            for widget in widgets:
                widget.blockSignals(True)
            try:
                self.platform_width_box.setValue(DEFAULT_OUTSIDE_PLATFORM_WIDTH)
                self.platform_coverage_box.setCurrentIndex(3)
                self.platform_match_end_profiles_box.setChecked(True)
                self.platform_entry_end_style_box.setCurrentIndex(1)
                self.platform_exit_end_style_box.setCurrentIndex(1)
                self.platform_entry_taper_length_box.setValue(100.0)
                self.platform_exit_taper_length_box.setValue(100.0)
                self.platform_body_output_box.setCurrentIndex(2)
                self.platform_show_body_box.setChecked(True)
            finally:
                for widget in widgets:
                    widget.blockSignals(False)
        self._update_platform_controls()
        if apply_outside_defaults:
            self._save_platform_editor_to_config()
            self._refresh_platform_manager_table(self._platform_current_index)

    def _update_platform_controls(self, *_args):
        if not hasattr(self, "platform_arrangement_box"):
            return
        between = str(self.platform_arrangement_box.currentText()) == PLATFORM_BETWEEN
        body_output = str(self.platform_body_output_box.currentText())
        solid = body_output == PLATFORM_SOLID
        body_exists = body_output in (PLATFORM_FACE, PLATFORM_SOLID)

        # Use railway-facing Up-side / Down-side terminology only where two
        # platform-face tracks exist. Outside platforms retain neutral labels.
        if hasattr(self, "platform_track_a_label"):
            if between:
                self.platform_track_a_label.setText("Up-side track:")
                self.platform_track_b_label.setText("Down-side track:")
                self.platform_clearance_a_label.setText("Up-side edge clearance:")
                self.platform_clearance_b_label.setText("Down-side edge clearance:")
            else:
                self.platform_track_a_label.setText("Adjacent track:")
                self.platform_track_b_label.setText("Second track (not used):")
                self.platform_clearance_a_label.setText("Track edge clearance:")
                self.platform_clearance_b_label.setText("Second-track clearance:")
            self.platform_track_b_label.setEnabled(between)
            self.platform_clearance_b_label.setEnabled(between)

        matched = self.platform_match_end_profiles_box.isChecked()
        if matched:
            entry_index = self.platform_entry_end_style_box.currentIndex()
            self.platform_exit_end_style_box.blockSignals(True)
            self.platform_exit_end_style_box.setCurrentIndex(entry_index)
            self.platform_exit_end_style_box.blockSignals(False)
            self.platform_exit_taper_length_box.blockSignals(True)
            self.platform_exit_taper_length_box.setValue(
                self.platform_entry_taper_length_box.value()
            )
            self.platform_exit_taper_length_box.blockSignals(False)

        entry_tapered = (
            str(self.platform_entry_end_style_box.currentText())
            == PLATFORM_END_TAPERED_LABEL
        )
        exit_tapered = (
            str(self.platform_exit_end_style_box.currentText())
            == PLATFORM_END_TAPERED_LABEL
        )

        self.platform_track_b_box.setEnabled(between)
        self.platform_clearance_b_box.setEnabled(between)
        self.platform_outside_side_box.setEnabled(not between)
        self.platform_width_box.setEnabled(not between)
        self.platform_entry_taper_length_box.setEnabled(entry_tapered)
        self.platform_exit_end_style_box.setEnabled(not matched)
        self.platform_exit_taper_length_box.setEnabled(
            exit_tapered and not matched
        )
        self.platform_height_box.setEnabled(solid)
        self.platform_show_body_box.setEnabled(body_exists)
        self.platform_show_edges_box.setEnabled(
            self.platform_create_edges_box.isChecked()
        )
        if not self._platform_loading:
            self._save_platform_editor_to_config()
            self._refresh_platform_manager_table(self._platform_current_index)
        if hasattr(self, "production_export_enabled_box"):
            self._update_production_export_controls()

    def _update_formation_section_controls(self, *_args):
        if not hasattr(self, "formation_enabled_box"):
            return
        formation_enabled = self.formation_enabled_box.isChecked()
        output_type = str(self.formation_output_type_box.currentText())
        has_outline = output_type in (FORMATION_OUTLINE_ONLY, FORMATION_BOTH)
        has_solid = output_type in (FORMATION_SOLID_ONLY, FORMATION_BOTH)
        for widget in (
            self.formation_include_tracks_box, self.formation_include_platform_box,
            self.formation_margin_box, self.formation_neck_box, self.formation_fill_gaps_box,
            self.formation_smooth_box, self.formation_output_type_box,
            self.formation_track_engraving_box, self.formation_platform_engraving_box,
        ):
            widget.setEnabled(formation_enabled)
        self.formation_smoothing_tolerance_box.setEnabled(formation_enabled and self.formation_smooth_box.isChecked())
        self.formation_thickness_box.setEnabled(formation_enabled and has_solid)
        self.formation_show_outline_box.setEnabled(formation_enabled and has_outline)
        self.formation_show_solid_box.setEnabled(formation_enabled and has_solid)

        section_active = self.section_enabled_box.isChecked() and self.section_max_length_box.value() > 0.0
        for widget in (
            self.section_balance_box, self.section_min_length_box, self.section_tracks_box,
            self.section_platform_box, self.section_formation_box, self.section_preserve_box,
            self.section_number_box,
        ):
            widget.setEnabled(section_active)
        registration_active = formation_enabled and section_active and self.section_formation_box.isChecked()
        self.registration_type_box.setEnabled(registration_active)
        joint_type = str(self.registration_type_box.currentText())
        shaped_joint = registration_active and joint_type in (REGISTRATION_PINS, REGISTRATION_TONGUE)
        hole_joint = registration_active and joint_type == REGISTRATION_HOLES
        self.registration_depth_box.setEnabled(shaped_joint)
        self.registration_width_box.setEnabled(shaped_joint)
        self.registration_clearance_box.setEnabled(shaped_joint)
        self.registration_hole_diameter_box.setEnabled(hole_joint)
        self.registration_hole_offset_box.setEnabled(hole_joint)

        template_section_active = section_active and self.section_tracks_box.isChecked()
        self.template_assembly_enabled_box.setEnabled(template_section_active)
        template_assembly_active = template_section_active and self.template_assembly_enabled_box.isChecked()
        self.template_joint_type_box.setEnabled(template_assembly_active)
        template_joint_type = str(self.template_joint_type_box.currentText())
        shaped_template_joint = template_assembly_active and template_joint_type != TEMPLATE_JOINT_PLAIN
        self.template_joint_depth_box.setEnabled(shaped_template_joint)
        self.template_joint_width_box.setEnabled(shaped_template_joint)
        self.template_joint_clearance_box.setEnabled(shaped_template_joint)
        self.template_fixing_holes_box.setEnabled(template_assembly_active)
        fixing_active = template_assembly_active and self.template_fixing_holes_box.isChecked()
        self.template_holes_per_section_box.setEnabled(fixing_active)
        self.template_hole_diameter_box.setEnabled(fixing_active)
        self.template_hole_end_clearance_box.setEnabled(fixing_active)
        self.template_matching_formation_holes_box.setEnabled(fixing_active)
        self.template_show_hole_geometry_box.setEnabled(fixing_active)
        if hasattr(self, "production_export_enabled_box"):
            self._update_production_export_controls()

    def _update_production_export_controls(self, *_args):
        if not hasattr(self, "production_export_enabled_box"):
            return
        enabled = bool(self.production_export_enabled_box.isChecked())
        for widget in (
            self.production_export_directory_box,
            self.production_export_browse_button,
            self.production_include_role_box,
            self.production_include_track_box,
            self.production_include_section_box,
            self.production_each_section_box,
            self.production_combined_box,
            self.production_overwrite_box,
            self.production_manifest_box,
            self.production_open_directory_box,
        ):
            widget.setEnabled(enabled)

        for format_key, box in self.production_format_boxes.items():
            available = bool(
                self._exporter_capabilities.get(format_key, {}).get(
                    "available", False
                )
            )
            box.setEnabled(enabled and available)

        section_active = bool(
            self.section_enabled_box.isChecked()
            and self.section_max_length_box.value() > 0.0
        )
        section_tracks = bool(section_active and self.section_tracks_box.isChecked())
        section_platform = bool(
            section_active and self.section_platform_box.isChecked()
        )
        section_formation = bool(
            section_active and self.section_formation_box.isChecked()
        )
        preserve_unsplit = bool(
            self.section_preserve_box.isChecked() or not section_active
        )

        if not self._platform_loading:
            self._save_platform_editor_to_config()
        enabled_platforms = [
            clone_platform_config(config)
            for config in self._platform_configs
            if config.get("enabled", False)
        ]
        platform_enabled = bool(enabled_platforms)
        platform_has_body = any(
            config["body_output"] in (PLATFORM_FACE, PLATFORM_SOLID)
            for config in enabled_platforms
        )
        platform_has_solid = any(
            config["body_output"] == PLATFORM_SOLID
            for config in enabled_platforms
        )
        platform_edges = any(
            config["create_edges"] for config in enabled_platforms
        )

        formation_enabled = bool(self.formation_enabled_box.isChecked())
        formation_output = str(self.formation_output_type_box.currentText())
        formation_has_outline = formation_output in (
            FORMATION_OUTLINE_ONLY,
            FORMATION_BOTH,
        )
        formation_has_solid = formation_output in (
            FORMATION_SOLID_ONLY,
            FORMATION_BOTH,
        )

        template_assembly_active = bool(
            section_tracks
            and self.template_assembly_enabled_box.isChecked()
        )
        template_joint_active = bool(
            template_assembly_active
            and str(self.template_joint_type_box.currentText())
            != TEMPLATE_JOINT_PLAIN
        )
        fixing_active = bool(
            template_assembly_active
            and self.template_fixing_holes_box.isChecked()
        )
        matching_formation_holes = bool(
            fixing_active
            and formation_enabled
            and self.template_matching_formation_holes_box.isChecked()
        )

        registration_active = bool(
            formation_enabled and section_formation
        )
        registration_type = str(self.registration_type_box.currentText())
        registration_holes = bool(
            registration_active and registration_type == REGISTRATION_HOLES
        )
        registration_joints = bool(
            registration_active
            and registration_type in (REGISTRATION_PINS, REGISTRATION_TONGUE)
        )

        complete_template = bool(
            preserve_unsplit or not section_tracks
        )
        complete_platform = bool(
            platform_enabled
            and platform_has_body
            and (preserve_unsplit or not section_platform)
        )
        complete_formation = bool(
            formation_enabled
            and (preserve_unsplit or not section_formation)
        )
        section_numbers = bool(
            section_active and self.section_number_box.isChecked()
        )
        other_engraving = bool(
            formation_enabled
            and (
                self.formation_track_engraving_box.isChecked()
                or (
                    platform_enabled
                    and self.formation_platform_engraving_box.isChecked()
                )
            )
        )

        availability = {
            "track_template_compound_2d": complete_template,
            "track_template_sections_2d": section_tracks,
            "track_template_fixing_holes": fixing_active,
            "track_template_joints": template_joint_active,
            "platform_plan_outline": platform_enabled,
            "platform_sections_2d": section_platform and platform_has_body,
            "formation_perimeter": complete_formation and formation_has_outline,
            "formation_sections_2d": section_formation and formation_has_outline,
            "registration_holes": registration_holes,
            "formation_matching_holes": matching_formation_holes,
            "registration_joints": registration_joints,
            "track_centrelines": True,
            "platform_edges": platform_edges,
            "section_numbers": section_numbers,
            "other_engraving": other_engraving,
            ASSEMBLY_LABEL_SELECTION_KEY: True,
            "track_template_compound_3d": complete_template,
            "track_template_sections_3d": section_tracks,
            "platform_body": complete_platform and platform_has_solid,
            "platform_sections_3d": section_platform and platform_has_solid,
            "formation_body": complete_formation and formation_has_solid,
            "formation_sections_3d": section_formation and formation_has_solid,
        }
        for key, box in self.production_selection_boxes.items():
            box.setEnabled(enabled and bool(availability.get(key, False)))

    def _formation_values(self):
        return clone_formation_config({
            "enabled": bool(self.formation_enabled_box.isChecked()),
            "include_track_templates": bool(self.formation_include_tracks_box.isChecked()),
            "include_platform": bool(self.formation_include_platform_box.isChecked()),
            "outer_margin": float(self.formation_margin_box.value()),
            "minimum_neck_width": float(self.formation_neck_box.value()),
            "fill_enclosed_gaps": bool(self.formation_fill_gaps_box.isChecked()),
            "smooth_outline": bool(self.formation_smooth_box.isChecked()),
            "smoothing_tolerance": float(self.formation_smoothing_tolerance_box.value()),
            "output_type": str(self.formation_output_type_box.currentText()),
            "board_thickness": float(self.formation_thickness_box.value()),
            "show_outline": bool(self.formation_show_outline_box.isChecked()),
            "show_solid": bool(self.formation_show_solid_box.isChecked()),
            "create_track_engraving": bool(self.formation_track_engraving_box.isChecked()),
            "create_platform_engraving": bool(self.formation_platform_engraving_box.isChecked()),
        })

    def _section_values(self):
        return clone_section_config({
            "enabled": bool(self.section_enabled_box.isChecked()),
            "maximum_section_length": float(self.section_max_length_box.value()),
            "balance_lengths": bool(self.section_balance_box.isChecked()),
            "minimum_section_length": float(self.section_min_length_box.value()),
            "section_track_templates": bool(self.section_tracks_box.isChecked()),
            "section_platform": bool(self.section_platform_box.isChecked()),
            "section_formation": bool(self.section_formation_box.isChecked()),
            "preserve_unsplit": bool(self.section_preserve_box.isChecked()),
            "number_in_travel_order": bool(self.section_number_box.isChecked()),
        })

    def _registration_values(self):
        return clone_registration_config({
            "joint_type": str(self.registration_type_box.currentText()),
            "joint_depth": float(self.registration_depth_box.value()),
            "joint_width": float(self.registration_width_box.value()),
            "fit_clearance": float(self.registration_clearance_box.value()),
            "alignment_hole_diameter": float(self.registration_hole_diameter_box.value()),
            "alignment_hole_offset": float(self.registration_hole_offset_box.value()),
        })

    def _template_assembly_values(self):
        return clone_template_assembly_config({
            "enabled": bool(self.template_assembly_enabled_box.isChecked()),
            "joint_type": str(self.template_joint_type_box.currentText()),
            "joint_depth": float(self.template_joint_depth_box.value()),
            "joint_width": float(self.template_joint_width_box.value()),
            "fit_clearance": float(self.template_joint_clearance_box.value()),
            "fixing_holes_enabled": bool(self.template_fixing_holes_box.isChecked()),
            "holes_per_section": int(self.template_holes_per_section_box.value()),
            "hole_diameter": float(self.template_hole_diameter_box.value()),
            "minimum_end_clearance": float(self.template_hole_end_clearance_box.value()),
            "matching_formation_holes": bool(self.template_matching_formation_holes_box.isChecked()),
            "show_hole_geometry": bool(self.template_show_hole_geometry_box.isChecked()),
        })

    def _platform_values(self):
        self._save_platform_editor_to_config()
        return clone_platform_configs(self._platform_configs)

    def _production_export_values(self):
        return clone_production_export_config({
            "enabled": bool(self.production_export_enabled_box.isChecked()),
            "output_directory": str(
                self.production_export_directory_box.text()
            ).strip(),
            "include_set_identifier": True,
            "include_object_role": bool(
                self.production_include_role_box.isChecked()
            ),
            "include_track_number": bool(
                self.production_include_track_box.isChecked()
            ),
            "include_section_number": bool(
                self.production_include_section_box.isChecked()
            ),
            "export_each_section": bool(
                self.production_each_section_box.isChecked()
            ),
            "create_combined_files": bool(
                self.production_combined_box.isChecked()
            ),
            "overwrite_existing": bool(
                self.production_overwrite_box.isChecked()
            ),
            "create_manifest": bool(
                self.production_manifest_box.isChecked()
            ),
            "open_output_directory": bool(
                self.production_open_directory_box.isChecked()
            ),
            "current_template_set_only": True,
            "formats": {
                key: bool(box.isChecked())
                for key, box in self.production_format_boxes.items()
            },
            "selections": {
                key: bool(box.isChecked())
                for key, box in self.production_selection_boxes.items()
            },
        })

    def values(self):
        tracks = []
        for row in range(self.track_table.rowCount()):
            config = self._row_config(row)
            if config is None:
                raise ValueError(
                    "Track row {} is incomplete. Close and reopen the macro.".format(row + 1)
                )
            tracks.append(config)

        straight_configs = self._straight_values()
        selected_straight_index = straight_manager_selection_index(
            straight_configs,
            self.straight_table.currentRow(),
        )
        platform_configs = self._platform_values()
        selected_platform_index = platform_manager_selection_index(
            platform_configs,
            (
                platform_configs[self._platform_current_index].get("manager_id", "")
                if platform_configs
                and 0 <= self._platform_current_index < len(platform_configs)
                else ""
            ),
            self._platform_current_index,
        )
        selected_platform_id = (
            str(platform_configs[selected_platform_index].get("manager_id", "")).strip()
            if platform_configs
            else ""
        )

        return (
            float(self.transition_box.value()),
            float(self.radius_box.value()),
            float(self.angle_box.value()),
            float(self.main_width_box.value()),
            tracks,
            straight_configs,
            selected_straight_index,
            platform_configs,
            selected_platform_id,
            selected_platform_index,
            self._formation_values(),
            self._section_values(),
            self._registration_values(),
            self._template_assembly_values(),
            validate_assembly_label_config(self._assembly_label_config),
            self._production_export_values(),
            validate_material_report_config(self._material_report_config),
            str(self.output_mode_box.currentText()),
        )


def quantity_value(obj, property_name, fallback):
    if obj is None or property_name not in getattr(obj, "PropertiesList", []):
        return fallback
    try:
        value = getattr(obj, property_name)
        return float(value.Value) if hasattr(value, "Value") else float(value)
    except (TypeError, ValueError, AttributeError):
        return fallback


def string_value(obj, property_name, fallback=""):
    if obj is None or property_name not in getattr(obj, "PropertiesList", []):
        return fallback
    try:
        return str(getattr(obj, property_name))
    except Exception:
        return fallback


def read_track_configs(obj, main_transition):
    stored = string_value(obj, "TrackConfigurationJSON", "")
    if stored:
        try:
            decoded = json.loads(stored)
            if isinstance(decoded, list):
                configs = [
                    clone_track_config(item, main_transition)
                    for item in decoded
                    if isinstance(item, dict)
                ]
                return configs[:MAX_PARALLEL_TRACKS]
        except Exception:
            pass

    if obj is not None:
        end_spacing = quantity_value(obj, "EndTrackSpacing", 50.0)
        curve_spacing = quantity_value(obj, "CurveTrackSpacing", 55.0)
        width = quantity_value(obj, "TemplateWidth", DEFAULT_MAIN_TEMPLATE_WIDTH)
        return [
            {
                "name": "Track 2",
                "side": "Outside",
                "alignment_mode": MODE_MATCH_SPACINGS,
                "start_spacing": end_spacing,
                "curve_spacing": curve_spacing,
                "finish_spacing": end_spacing,
                "entry_transition_length": main_transition,
                "exit_transition_length": main_transition,
                "width": width,
                "create_template": True,
                "show_centreline": True,
            }
        ]

    return [clone_track_config(item, main_transition) for item in DEFAULT_PARALLEL_TRACKS]


def read_straight_configs(obj):
    stored = string_value(obj, STRAIGHT_CONFIGS_PROPERTY, "")
    if stored:
        try:
            decoded = json.loads(stored)
            if isinstance(decoded, list):
                return clone_straight_configs(decoded)
        except Exception:
            pass
    return []


def read_platform_config(obj):
    stored = string_value(obj, "PlatformConfigurationJSON", "")
    if stored:
        try:
            decoded = json.loads(stored)
            if isinstance(decoded, list):
                decoded = decoded[0] if decoded else {}
            if isinstance(decoded, dict):
                decoded = dict(decoded)
                if "centre_offset" not in decoded:
                    legacy_start = max(0.0, float(decoded.get("start_inset", 0.0)))
                    legacy_finish = max(0.0, float(decoded.get("finish_inset", 0.0)))
                    decoded["centre_offset"] = 0.5 * (
                        legacy_start - legacy_finish
                    )
                if "platform_length" not in decoded:
                    summary = string_value(obj, "PlatformSummary", "")
                    match = re.search(
                        r"(?:^|;)\s*length\s+([0-9]+(?:\.[0-9]+)?)\s+mm(?:;|$)",
                        summary,
                    )
                    if match:
                        decoded["platform_length"] = float(match.group(1))
                return clone_platform_config(decoded)
        except Exception:
            pass
    return default_platform_config()


def read_platform_configs(obj):
    stored = string_value(obj, PLATFORM_CONFIGS_PROPERTY, "")
    if stored:
        try:
            decoded = json.loads(stored)
            if isinstance(decoded, list):
                configs = [
                    clone_platform_config(item)
                    for item in decoded[:MAX_PLATFORMS]
                    if isinstance(item, dict)
                ]
                if configs:
                    return configs
        except Exception:
            pass
    # Version 8 and earlier stored one platform dictionary. Promote it to the
    # first entry without changing its geometry settings.
    return [read_platform_config(obj)]


def read_formation_config(obj):
    stored = string_value(obj, "FormationConfigurationJSON", "")
    if stored:
        try:
            decoded = json.loads(stored)
            if isinstance(decoded, dict):
                return clone_formation_config(decoded)
        except Exception:
            pass
    return default_formation_config()


def read_section_config(obj):
    stored = string_value(obj, "SectionConfigurationJSON", "")
    if stored:
        try:
            decoded = json.loads(stored)
            if isinstance(decoded, dict):
                return clone_section_config(decoded)
        except Exception:
            pass
    return default_section_config()


def read_registration_config(obj):
    stored = string_value(obj, "RegistrationConfigurationJSON", "")
    if stored:
        try:
            decoded = json.loads(stored)
            if isinstance(decoded, dict):
                return clone_registration_config(decoded)
        except Exception:
            pass
    return default_registration_config()


def read_template_assembly_config(obj):
    stored = string_value(obj, "TrackTemplateAssemblyConfigurationJSON", "")
    if stored:
        try:
            decoded = json.loads(stored)
            if isinstance(decoded, dict):
                return clone_template_assembly_config(decoded)
        except Exception:
            pass
    return default_template_assembly_config()



def read_production_export_config(obj):
    stored = string_value(obj, PRODUCTION_EXPORT_SETTINGS_PROPERTY, "")
    if stored:
        try:
            decoded = json.loads(stored)
            if isinstance(decoded, dict):
                return clone_production_export_config(decoded)
        except Exception:
            pass
    return default_production_export_config()


def read_material_report_config(obj):
    stored = string_value(obj, MATERIAL_REPORT_SETTINGS_PROPERTY, "")
    if stored:
        try:
            decoded = json.loads(stored)
            if isinstance(decoded, dict):
                return validate_material_report_config(decoded)
        except Exception:
            pass
    return read_last_material_report_config()


def store_material_report_config(obj, config):
    if obj is None:
        raise ValueError("The selected template set has no settings object.")
    normalised = remember_last_material_report_config(config)
    prop = ensure_property(
        obj,
        "App::PropertyString",
        MATERIAL_REPORT_SETTINGS_PROPERTY,
        "Production utilities",
        "Stored material and sheet-estimate settings",
    )
    setattr(obj, MATERIAL_REPORT_SETTINGS_PROPERTY, json.dumps(normalised, sort_keys=True))
    set_read_only(obj, [prop])
    return normalised


def detect_exporter_capabilities():
    capabilities = {}
    try:
        import importDXF
        available = callable(getattr(importDXF, "export", None))
        capabilities[EXPORT_FORMAT_DXF] = {
            "available": available,
            "reason": (
                "FreeCAD importDXF exporter detected."
                if available
                else "FreeCAD importDXF is present but has no export function."
            ),
        }
    except Exception as error:
        capabilities[EXPORT_FORMAT_DXF] = {
            "available": False,
            "reason": "FreeCAD DXF exporter unavailable: {}".format(error),
        }

    try:
        import importSVG
        available = callable(getattr(importSVG, "export", None))
        capabilities[EXPORT_FORMAT_SVG] = {
            "available": available,
            "reason": (
                "FreeCAD importSVG exporter detected."
                if available
                else "FreeCAD importSVG is present but has no export function."
            ),
        }
    except Exception as error:
        capabilities[EXPORT_FORMAT_SVG] = {
            "available": False,
            "reason": "FreeCAD SVG exporter unavailable: {}".format(error),
        }

    try:
        import Mesh
        available = callable(getattr(Mesh, "export", None))
        capabilities[EXPORT_FORMAT_STL] = {
            "available": available,
            "reason": (
                "FreeCAD Mesh exporter detected."
                if available
                else "FreeCAD Mesh is present but has no export function."
            ),
        }
    except Exception as error:
        capabilities[EXPORT_FORMAT_STL] = {
            "available": False,
            "reason": "FreeCAD STL exporter unavailable: {}".format(error),
        }

    available = callable(getattr(Part, "export", None))
    capabilities[EXPORT_FORMAT_STEP] = {
        "available": available,
        "reason": (
            "FreeCAD Part STEP exporter detected."
            if available
            else "FreeCAD Part module has no export function for STEP output."
        ),
    }
    return capabilities

def dialog_exec(dialog):
    if hasattr(dialog, "exec"):
        return dialog.exec()
    return dialog.exec_()


def versioned_dialog_title(title):
    """Return a compact message-box title carrying the exact macro version."""
    label = str(title or "").strip()
    prefix = "Version {}".format(MACRO_VERSION_NUMBER)
    return "{} - {}".format(prefix, label) if label else prefix


def crossover_dialog_title(title):
    """Return a plain operator-facing title for crossover controls."""
    label = str(title or "").strip()
    prefix = "Version {}".format(CROSSOVER_OPERATOR_VERSION_NUMBER)
    return "{} - {}".format(prefix, label) if label else prefix


def show_error(message):
    QtWidgets.QMessageBox.critical(
        None,
        versioned_dialog_title("Railway template error"),
        message,
    )


def ensure_property(obj, property_type, name, group, description):
    if name not in obj.PropertiesList:
        obj.addProperty(property_type, name, group, description)
    return name


def set_read_only(obj, property_names):
    for name in property_names:
        try:
            obj.setEditorMode(name, 1)
        except Exception:
            pass


def object_string_property(obj, property_name, fallback=""):
    if obj is None or property_name not in getattr(obj, "PropertiesList", []):
        return fallback
    try:
        return str(getattr(obj, property_name))
    except Exception:
        return fallback



def _persistent_property_values_equal(current, requested):
    """Compare a FreeCAD property value with its requested persisted value exactly.

    Length properties expose a Quantity object in live FreeCAD; ordinary scalar
    stubs expose the value directly.  The comparison deliberately uses no
    engineering tolerance: an actual value change must still be written.
    """
    try:
        if isinstance(requested, bool):
            return bool(current) is bool(requested)
        if isinstance(requested, int) and not isinstance(requested, bool):
            return int(current) == int(requested)
        if isinstance(requested, float):
            current_value = getattr(current, "Value", current)
            return float(current_value) == float(requested)
        if isinstance(requested, str):
            return str(current) == requested
        return current == requested
    except Exception:
        return False


def _set_persistent_property_if_changed(obj, property_name, value, statistics=None):
    """Assign one persistent property only when its exact value changed."""
    try:
        current = getattr(obj, property_name)
    except Exception:
        current = None
    if _persistent_property_values_equal(current, value):
        if isinstance(statistics, dict):
            statistics["unchanged_property_writes_skipped"] = int(
                statistics.get("unchanged_property_writes_skipped") or 0
            ) + 1
        return False
    setattr(obj, property_name, value)
    if isinstance(statistics, dict):
        statistics["property_writes_performed"] = int(
            statistics.get("property_writes_performed") or 0
        ) + 1
    return True


def is_generated_template(obj):
    if obj is None:
        return False
    if object_string_property(obj, "GeneratedBy") == GENERATOR_ID:
        return object_string_property(obj, "GeneratedRole") == "Template"
    properties = set(getattr(obj, "PropertiesList", []))
    has_core_inputs = {"TransitionLength", "CurveRadius"}.issubset(properties)
    has_template_width = (
        "MainTemplateWidth" in properties or "TemplateWidth" in properties
    )
    return has_core_inputs and (
        "TrackConfigurationJSON" in properties or has_template_width
    )


def is_generated_centreline(obj):
    if obj is None:
        return False
    if object_string_property(obj, "GeneratedBy") == GENERATOR_ID:
        return object_string_property(obj, "GeneratedRole") == "Centreline"
    name = str(getattr(obj, "Name", ""))
    return name.startswith(CENTRELINE_PREFIX) or name in LEGACY_CENTRELINE_NAMES


def is_generated_platform_output(obj):
    if obj is None:
        return False
    if object_string_property(obj, "GeneratedBy") != GENERATOR_ID:
        return False
    return object_string_property(obj, "GeneratedRole") in (
        "PlatformEdge",
        "PlatformBody",
    )


def is_generated_settings(obj):
    if obj is None:
        return False
    return (
        object_string_property(obj, "GeneratedBy") == GENERATOR_ID
        and object_string_property(obj, "GeneratedRole") == "Settings"
    )


def is_any_generated_output(obj):
    if obj is None:
        return False
    if object_string_property(obj, "GeneratedBy") == GENERATOR_ID:
        return True
    return (
        is_generated_template(obj)
        or is_generated_centreline(obj)
        or is_generated_group(obj)
    )


def is_generated_group(obj):
    if obj is None:
        return False
    if object_string_property(obj, "GeneratedBy") == GENERATOR_ID:
        return object_string_property(obj, "GeneratedRole") == "Group"
    return str(getattr(obj, "Name", "")).startswith(GROUP_NAME)


def generated_templates(doc):
    return [obj for obj in list(doc.Objects) if is_generated_template(obj)]


def generated_set_count(doc):
    tagged_ids = set()
    legacy_count = 0
    for obj in list(doc.Objects):
        if object_string_property(obj, "GeneratedBy") == GENERATOR_ID:
            set_id = object_string_property(obj, "TemplateSetID", "")
            if set_id:
                tagged_ids.add(set_id)
        elif is_generated_template(obj):
            legacy_count += 1
    return len(tagged_ids) + legacy_count


def latest_generated_settings(doc):
    candidates = [obj for obj in list(doc.Objects) if is_generated_settings(obj)]
    if Gui is not None:
        try:
            for obj in reversed(Gui.Selection.getSelection()):
                if is_generated_settings(obj):
                    return obj
                if (
                    is_generated_template(obj)
                    or object_string_property(obj, "GeneratedBy") == GENERATOR_ID
                ):
                    set_id = object_string_property(obj, "TemplateSetID", "")
                    for candidate in reversed(candidates):
                        if object_string_property(candidate, "TemplateSetID", "") == set_id:
                            return candidate
        except Exception:
            pass
    return candidates[-1] if candidates else None


def latest_generated_template(doc):
    if Gui is not None:
        try:
            for obj in reversed(Gui.Selection.getSelection()):
                if is_generated_template(obj):
                    return obj
        except Exception:
            pass
    templates = generated_templates(doc)
    return templates[-1] if templates else None


def unique_internal_name(doc, base_name):
    if doc.getObject(base_name) is None:
        return base_name
    suffix = 1
    while True:
        candidate = "{}_{:03d}".format(base_name, suffix)
        if doc.getObject(candidate) is None:
            return candidate
        suffix += 1


def next_template_set_id(doc):
    used = set()
    for obj in list(doc.Objects):
        value = object_string_property(obj, "TemplateSetID", "")
        if value:
            used.add(value)
    number = 1
    while True:
        candidate = "SET-{:03d}".format(number)
        if candidate not in used:
            return candidate
        number += 1


def planned_template_set_id(doc, output_mode):
    if output_mode == OUTPUT_REPLACE:
        return "SET-001"
    return next_template_set_id(doc)


def tag_generated_object(obj, role, set_id):
    ensure_property(
        obj,
        "App::PropertyString",
        "GeneratedBy",
        "Template identity",
        "Identifier used to recognise objects generated by this macro",
    )
    ensure_property(
        obj,
        "App::PropertyString",
        "GeneratedRole",
        "Template identity",
        "Role of this object within its generated template set",
    )
    ensure_property(
        obj,
        "App::PropertyString",
        "TemplateSetID",
        "Template identity",
        "Unique identifier shared by all objects in this template set",
    )
    ensure_property(
        obj,
        "App::PropertyString",
        "GeneratorVersion",
        "Template identity",
        "Macro version that generated this object",
    )
    obj.GeneratedBy = GENERATOR_ID
    obj.GeneratedRole = role
    obj.TemplateSetID = set_id
    obj.GeneratorVersion = MACRO_VERSION
    set_read_only(
        obj,
        ["GeneratedBy", "GeneratedRole", "TemplateSetID", "GeneratorVersion"],
    )


def tag_route_metadata(obj, route_id, route_name):
    properties = [
        ensure_property(
            obj,
            "App::PropertyString",
            "RouteID",
            "Railway route",
            "Stable identifier for the curve or straight fabrication route",
        ),
        ensure_property(
            obj,
            "App::PropertyString",
            "RouteName",
            "Railway route",
            "User-facing route name",
        ),
    ]
    obj.RouteID = str(route_id or "")
    obj.RouteName = str(route_name or "")
    set_read_only(obj, properties)


def remove_all_generated_outputs(doc):
    objects = list(doc.Objects)
    generated_parts = [
        obj for obj in objects
        if is_any_generated_output(obj) and not is_generated_group(obj)
    ]
    generated_groups = [obj for obj in objects if is_generated_group(obj)]

    removed_names = []
    for obj in generated_parts:
        name = str(obj.Name)
        if doc.getObject(name) is not None:
            doc.removeObject(name)
            removed_names.append(name)

    for obj in generated_groups:
        name = str(obj.Name)
        if doc.getObject(name) is not None:
            doc.removeObject(name)
            removed_names.append(name)

    if removed_names:
        _document_recompute(doc)
    return removed_names


def vector_xy(x, y):
    return App.Vector(float(x), float(y), 0.0)


def rotate_xy(x, y, angle):
    cosine = math.cos(angle)
    sine = math.sin(angle)
    return (
        (x * cosine) - (y * sine),
        (x * sine) + (y * cosine),
    )


def left_normal(heading):
    return (-math.sin(heading), math.cos(heading))


def dot_xy(x, y, ux, uy):
    return (x * ux) + (y * uy)


def integrate_path_segment(
    points,
    headings,
    x,
    y,
    heading,
    length,
    curvature_function,
):
    if length <= GEOMETRY_TOLERANCE:
        return x, y, heading

    steps = max(1, int(math.ceil(length / SAMPLE_SPACING)))
    distance_step = length / float(steps)

    for index in range(steps):
        local_midpoint = (index + 0.5) * distance_step
        curvature = curvature_function(local_midpoint)
        new_heading = heading + (curvature * distance_step)

        if abs(curvature) < 1.0e-14:
            x += distance_step * math.cos(heading)
            y += distance_step * math.sin(heading)
        else:
            x += (math.sin(new_heading) - math.sin(heading)) / curvature
            y += (-math.cos(new_heading) + math.cos(heading)) / curvature

        heading = new_heading
        points.append(vector_xy(x, y))
        headings.append(heading)

    return x, y, heading


def clothoid_entry_displacement(length, radius, integration_steps=240):
    """Return accurate local x/y displacement and angle for an Euler entry."""
    if radius <= 0.0:
        raise ValueError("A clothoid radius must be greater than zero.")
    if length <= GEOMETRY_TOLERANCE:
        return 0.0, 0.0, 0.0

    # Simpson integration of theta(u) = alpha*u^2 over u in [0, 1].
    steps = max(40, int(integration_steps))
    if steps % 2:
        steps += 1
    alpha = length / (2.0 * radius)
    interval = 1.0 / float(steps)
    cosine_sum = 0.0
    sine_sum = 0.0

    for index in range(steps + 1):
        u = index * interval
        theta = alpha * u * u
        weight = 1.0
        if index not in (0, steps):
            weight = 4.0 if index % 2 else 2.0
        cosine_sum += weight * math.cos(theta)
        sine_sum += weight * math.sin(theta)

    scale = length * interval / 3.0
    return scale * cosine_sum, scale * sine_sum, alpha


def clothoid_exit_displacement(length, radius, integration_steps=240):
    """Return accurate local x/y displacement and angle for an Euler exit."""
    if radius <= 0.0:
        raise ValueError("A clothoid radius must be greater than zero.")
    if length <= GEOMETRY_TOLERANCE:
        return 0.0, 0.0, 0.0

    steps = max(40, int(integration_steps))
    if steps % 2:
        steps += 1
    alpha = length / (2.0 * radius)
    interval = 1.0 / float(steps)
    cosine_sum = 0.0
    sine_sum = 0.0

    for index in range(steps + 1):
        u = index * interval
        theta = (2.0 * alpha * u) - (alpha * u * u)
        weight = 1.0
        if index not in (0, steps):
            weight = 4.0 if index % 2 else 2.0
        cosine_sum += weight * math.cos(theta)
        sine_sum += weight * math.sin(theta)

    scale = length * interval / 3.0
    return scale * cosine_sum, scale * sine_sum, alpha



def platform_transition_displacement(
    length,
    radius,
    shape_parameter,
    transition_kind,
    integration_steps=320,
):
    """Return local displacement and angle for a same-direction platform transition.

    Curvature is a smooth polynomial with zero curvature and zero curvature
    gradient at the straight end, exact 1/radius curvature and zero curvature
    gradient at the circular end, plus an automatically solved smooth bump.
    The bump allows a track to diverge to a wider concentric curve without using
    a geometric reverse curve.
    """
    if radius <= 0.0:
        raise ValueError("A platform-transition radius must be greater than zero.")
    if length <= GEOMETRY_TOLERANCE:
        return 0.0, 0.0, 0.0
    if shape_parameter < -0.25 - 1.0e-10:
        raise ValueError("A platform-transition shape parameter became invalid.")
    if transition_kind not in ("entry", "exit"):
        raise ValueError("Unknown platform-transition direction.")

    steps = max(80, int(integration_steps))
    if steps % 2:
        steps += 1
    interval = 1.0 / float(steps)
    length_over_radius = length / radius
    cosine_sum = 0.0
    sine_sum = 0.0

    for index in range(steps + 1):
        u = index * interval
        common_bump_integral = 16.0 * (
            (u * u * u / 3.0)
            - (u * u * u * u / 2.0)
            + (u * u * u * u * u / 5.0)
        )
        if transition_kind == "entry":
            heading = length_over_radius * (
                (u * u * u)
                - (0.5 * u * u * u * u)
                + (shape_parameter * common_bump_integral)
            )
        else:
            heading = length_over_radius * (
                u
                - (u * u * u)
                + (0.5 * u * u * u * u)
                + (shape_parameter * common_bump_integral)
            )

        weight = 1.0
        if index not in (0, steps):
            weight = 4.0 if index % 2 else 2.0
        cosine_sum += weight * math.cos(heading)
        sine_sum += weight * math.sin(heading)

    scale = length * interval / 3.0
    total_angle = length_over_radius * (
        0.5 + ((8.0 / 15.0) * shape_parameter)
    )
    return scale * cosine_sum, scale * sine_sum, total_angle


def platform_peak_curvature_factor(shape_parameter):
    """Maximum curvature divided by the constant-curve curvature."""
    candidates = [0.0, 1.0]
    coefficient_a = 64.0 * shape_parameter
    coefficient_b = -6.0 - (96.0 * shape_parameter)
    coefficient_c = 6.0 + (32.0 * shape_parameter)

    if abs(coefficient_a) <= 1.0e-14:
        if abs(coefficient_b) > 1.0e-14:
            root = -coefficient_c / coefficient_b
            if 0.0 < root < 1.0:
                candidates.append(root)
    else:
        discriminant = (
            coefficient_b * coefficient_b
            - (4.0 * coefficient_a * coefficient_c)
        )
        if discriminant >= 0.0:
            root_term = math.sqrt(discriminant)
            for root in (
                (-coefficient_b - root_term) / (2.0 * coefficient_a),
                (-coefficient_b + root_term) / (2.0 * coefficient_a),
            ):
                if 0.0 < root < 1.0:
                    candidates.append(root)

    maximum = 0.0
    for u in candidates:
        base = (3.0 * u * u) - (2.0 * u * u * u)
        bump = 16.0 * shape_parameter * u * u * (1.0 - u) * (1.0 - u)
        maximum = max(maximum, base + bump)
    return max(1.0, maximum)


def platform_transition_angle(length, radius, shape_parameter):
    if length <= GEOMETRY_TOLERANCE:
        return 0.0
    return (length / radius) * (
        0.5 + ((8.0 / 15.0) * shape_parameter)
    )


def platform_line_offset(
    circle_centre,
    radius,
    length,
    shape_parameter,
    total_angle,
    transition_kind,
    integration_steps=240,
):
    """Signed normal coordinate of the straight attached to a transition."""
    dx, dy, angle = platform_transition_displacement(
        length,
        radius,
        shape_parameter,
        transition_kind,
        integration_steps,
    )
    centre_x, centre_y = circle_centre

    if transition_kind == "entry":
        return centre_y - (radius * math.cos(angle)) - dy

    normal_x, normal_y = left_normal(total_angle)
    centre_normal_coordinate = dot_xy(
        centre_x,
        centre_y,
        normal_x,
        normal_y,
    )
    transition_normal_displacement = (
        (-dx * math.sin(angle)) + (dy * math.cos(angle))
    )
    return (
        centre_normal_coordinate
        - (radius * math.cos(angle))
        + transition_normal_displacement
    )


def _platform_parameter_grid(lower, upper):
    """Generate a dense, low-curvature-first search grid."""
    if upper < lower:
        return []

    values = [lower]
    if lower < 0.0 < upper:
        negative_steps = 36
        for index in range(1, negative_steps + 1):
            fraction = index / float(negative_steps)
            values.append(lower + ((0.0 - lower) * fraction))
    elif upper <= 0.0:
        steps = 80
        for index in range(1, steps + 1):
            fraction = index / float(steps)
            values.append(lower + ((upper - lower) * fraction))
        return values

    positive_start = max(0.0, lower)
    if upper > positive_start:
        positive_steps = 240
        for index in range(1, positive_steps + 1):
            fraction = index / float(positive_steps)
            # Quadratic spacing gives extra resolution near the gentlest shapes.
            values.append(
                positive_start
                + ((upper - positive_start) * fraction * fraction)
            )

    if abs(values[-1] - upper) > 1.0e-12:
        values.append(upper)
    return values


def solve_platform_shape_parameter(
    circle_centre,
    radius,
    transition_length,
    target_line_offset,
    total_angle,
    track_name,
    end_name,
    transition_kind,
):
    """Solve the gentlest same-direction platform transition for one end."""
    if radius <= 0.0:
        raise ValueError(
            "The platform curve radius for '{}' must be greater than zero.".format(
                track_name
            )
        )
    if transition_length < 0.0:
        raise ValueError(
            "The {} platform transition for '{}' cannot be negative.".format(
                end_name.lower(),
                track_name,
            )
        )

    if transition_length <= GEOMETRY_TOLERANCE:
        actual_offset = platform_line_offset(
            circle_centre,
            radius,
            0.0,
            0.0,
            total_angle,
            transition_kind,
        )
        if abs(actual_offset - target_line_offset) > 1.0e-6:
            raise ValueError(
                "{} platform spacing for '{}' needs a non-zero transition length.\n\n"
                "Requested signed straight offset: {:+.3f} mm\n"
                "Zero-length offset: {:+.3f} mm".format(
                    end_name,
                    track_name,
                    target_line_offset,
                    actual_offset,
                )
            )
        return {
            "shape_parameter": 0.0,
            "angle": 0.0,
            "peak_factor": 1.0,
            "minimum_radius": radius,
        }

    length_over_radius = transition_length / radius
    minimum_shape = -0.187499
    maximum_angle = max(1.0e-8, total_angle - 1.0e-8)
    maximum_shape = (15.0 / 8.0) * (
        (maximum_angle / length_over_radius) - 0.5
    )

    if maximum_shape < minimum_shape:
        minimum_possible_angle = platform_transition_angle(
            transition_length,
            radius,
            minimum_shape,
        )
        raise ValueError(
            "The {} platform transition for '{}' is too long for the total turn.\n\n"
            "Transition length: {:.3f} mm\n"
            "Smallest possible transition angle: {:.3f} deg\n"
            "Complete turn angle: {:.3f} deg\n\n"
            "Shorten this transition or increase the complete turn angle.".format(
                end_name.lower(),
                track_name,
                transition_length,
                math.degrees(minimum_possible_angle),
                math.degrees(total_angle),
            )
        )

    grid = _platform_parameter_grid(minimum_shape, maximum_shape)
    samples = []
    for parameter in grid:
        offset = platform_line_offset(
            circle_centre,
            radius,
            transition_length,
            parameter,
            total_angle,
            transition_kind,
            integration_steps=240,
        )
        samples.append((parameter, offset - target_line_offset, offset))

    brackets = []
    exact_parameters = []
    for parameter, difference, _offset in samples:
        if abs(difference) <= 1.0e-7:
            exact_parameters.append(parameter)
    for first, second in zip(samples[:-1], samples[1:]):
        if first[1] * second[1] < 0.0:
            brackets.append((first[0], second[0]))

    candidate_parameters = list(exact_parameters)

    # A valid spacing can touch the edge of the achievable range without
    # crossing it, so a sign-change search alone is insufficient. Refine the
    # closest sampled point and accept it when the residual is negligible.
    if samples:
        best_index = min(range(len(samples)), key=lambda index: abs(samples[index][1]))
        left_index = max(0, best_index - 1)
        right_index = min(len(samples) - 1, best_index + 1)
        search_low = samples[left_index][0]
        search_high = samples[right_index][0]

        if search_high > search_low:
            golden_ratio = (math.sqrt(5.0) - 1.0) / 2.0

            def squared_residual(parameter):
                difference = platform_line_offset(
                    circle_centre,
                    radius,
                    transition_length,
                    parameter,
                    total_angle,
                    transition_kind,
                    integration_steps=360,
                ) - target_line_offset
                return difference * difference

            a = search_low
            b = search_high
            c = b - (golden_ratio * (b - a))
            d = a + (golden_ratio * (b - a))
            value_c = squared_residual(c)
            value_d = squared_residual(d)
            for _iteration in range(72):
                if value_c <= value_d:
                    b = d
                    d = c
                    value_d = value_c
                    c = b - (golden_ratio * (b - a))
                    value_c = squared_residual(c)
                else:
                    a = c
                    c = d
                    value_c = value_d
                    d = a + (golden_ratio * (b - a))
                    value_d = squared_residual(d)
            minimum_parameter = 0.5 * (a + b)
            minimum_residual = math.sqrt(squared_residual(minimum_parameter))
            if minimum_residual <= 1.0e-5:
                candidate_parameters.append(minimum_parameter)

    for low, high in brackets:
        value_low = platform_line_offset(
            circle_centre,
            radius,
            transition_length,
            low,
            total_angle,
            transition_kind,
            integration_steps=320,
        ) - target_line_offset

        for _iteration in range(72):
            midpoint = 0.5 * (low + high)
            value_midpoint = platform_line_offset(
                circle_centre,
                radius,
                transition_length,
                midpoint,
                total_angle,
                transition_kind,
                integration_steps=320,
            ) - target_line_offset
            if abs(value_midpoint) <= 1.0e-10 or (high - low) <= 1.0e-9:
                low = midpoint
                high = midpoint
                break
            if value_low * value_midpoint <= 0.0:
                high = midpoint
            else:
                low = midpoint
                value_low = value_midpoint
        candidate_parameters.append(0.5 * (low + high))

    if not candidate_parameters:
        offsets = [item[2] for item in samples]
        lower_offset = min(offsets)
        upper_offset = max(offsets)
        raise ValueError(
            "{} platform spacing for '{}' cannot be produced with the entered "
            "transition length while keeping all curvature in the same turn "
            "direction.\n\n"
            "Transition length: {:.3f} mm\n"
            "Requested signed straight offset: {:+.3f} mm\n"
            "Achievable signed range: {:+.3f} to {:+.3f} mm\n\n"
            "Change the transition length, straight spacing, curve spacing, main "
            "radius or total turn angle.".format(
                end_name,
                track_name,
                transition_length,
                target_line_offset,
                lower_offset,
                upper_offset,
            )
        )

    # Prefer the solution with the largest minimum radius. This selects the
    # gentlest valid curvature profile if the equation has more than one root.
    candidates = []
    for parameter in candidate_parameters:
        angle = platform_transition_angle(
            transition_length,
            radius,
            parameter,
        )
        peak_factor = platform_peak_curvature_factor(parameter)
        candidates.append(
            {
                "shape_parameter": parameter,
                "angle": angle,
                "peak_factor": peak_factor,
                "minimum_radius": radius / peak_factor,
            }
        )
    candidates.sort(
        key=lambda item: (
            -item["minimum_radius"],
            item["angle"],
            abs(item["shape_parameter"]),
        )
    )
    return candidates[0]


def build_platform_core(
    circle_centre,
    radius,
    entry_transition,
    exit_transition,
    entry_shape_parameter,
    exit_shape_parameter,
    total_angle,
    label,
):
    """Build a concentric core with same-direction platform transitions."""
    if radius <= 0.0:
        raise ValueError(
            "The constant radius for '{}' must be greater than zero.".format(label)
        )
    if entry_transition < 0.0 or exit_transition < 0.0:
        raise ValueError(
            "Platform transition lengths for '{}' cannot be negative.".format(label)
        )

    entry_dx, entry_dy, entry_angle = platform_transition_displacement(
        entry_transition,
        radius,
        entry_shape_parameter,
        "entry",
        integration_steps=480,
    )
    exit_dx, exit_dy, exit_angle = platform_transition_displacement(
        exit_transition,
        radius,
        exit_shape_parameter,
        "exit",
        integration_steps=480,
    )
    circular_angle = total_angle - entry_angle - exit_angle
    if circular_angle < -1.0e-8:
        combined_angle = entry_angle + exit_angle
        scale = 0.90 * total_angle / combined_angle if combined_angle > 0.0 else 1.0
        suggested_entry = max(1.0, entry_transition * min(1.0, scale))
        suggested_exit = max(1.0, exit_transition * min(1.0, scale))
        raise ValueError(
            "The platform transitions for '{}' use more angle than the complete "
            "curve.\n\n"
            "Entry transition angle: {:.3f} deg\n"
            "Exit transition angle: {:.3f} deg\n"
            "Combined transition angle: {:.3f} deg\n"
            "Complete turn angle: {:.3f} deg\n\n"
            "Shorten one or both platform transition lengths. As a conservative "
            "starting point, try about {:.0f} mm entry and {:.0f} mm exit, then "
            "increase them if the macro confirms that the geometry still fits.".format(
                label,
                math.degrees(entry_angle),
                math.degrees(exit_angle),
                math.degrees(combined_angle),
                math.degrees(total_angle),
                suggested_entry,
                suggested_exit,
            )
        )
    circular_angle = max(0.0, circular_angle)

    centre_x, centre_y = circle_centre
    entry_normal_x, entry_normal_y = left_normal(entry_angle)
    circle_start_x = centre_x - (radius * entry_normal_x)
    circle_start_y = centre_y - (radius * entry_normal_y)
    start_x = circle_start_x - entry_dx
    start_y = circle_start_y - entry_dy

    points = [vector_xy(start_x, start_y)]
    headings = [0.0]
    x = start_x
    y = start_y
    heading = 0.0

    if entry_transition > GEOMETRY_TOLERANCE:
        x, y, heading = integrate_path_segment(
            points,
            headings,
            x,
            y,
            heading,
            entry_transition,
            lambda station: (1.0 / radius)
            * (
                (3.0 * (station / entry_transition) ** 2)
                - (2.0 * (station / entry_transition) ** 3)
                + (
                    16.0
                    * entry_shape_parameter
                    * (station / entry_transition) ** 2
                    * (1.0 - (station / entry_transition)) ** 2
                )
            ),
        )

    x = circle_start_x
    y = circle_start_y
    heading = entry_angle
    points[-1] = vector_xy(x, y)
    headings[-1] = heading

    circular_length = radius * circular_angle
    if circular_length > GEOMETRY_TOLERANCE:
        x, y, heading = integrate_path_segment(
            points,
            headings,
            x,
            y,
            heading,
            circular_length,
            lambda _station: 1.0 / radius,
        )

    circle_end_heading = total_angle - exit_angle
    exit_normal_x, exit_normal_y = left_normal(circle_end_heading)
    circle_end_x = centre_x - (radius * exit_normal_x)
    circle_end_y = centre_y - (radius * exit_normal_y)
    x = circle_end_x
    y = circle_end_y
    heading = circle_end_heading
    points[-1] = vector_xy(x, y)
    headings[-1] = heading

    if exit_transition > GEOMETRY_TOLERANCE:
        x, y, heading = integrate_path_segment(
            points,
            headings,
            x,
            y,
            heading,
            exit_transition,
            lambda station: (1.0 / radius)
            * (
                1.0
                - (3.0 * (station / exit_transition) ** 2)
                + (2.0 * (station / exit_transition) ** 3)
                + (
                    16.0
                    * exit_shape_parameter
                    * (station / exit_transition) ** 2
                    * (1.0 - (station / exit_transition)) ** 2
                )
            ),
        )

        rotated_dx, rotated_dy = rotate_xy(
            exit_dx,
            exit_dy,
            circle_end_heading,
        )
        x = circle_end_x + rotated_dx
        y = circle_end_y + rotated_dy
        points[-1] = vector_xy(x, y)

    heading = total_angle
    headings[-1] = heading

    entry_peak = platform_peak_curvature_factor(entry_shape_parameter)
    exit_peak = platform_peak_curvature_factor(exit_shape_parameter)
    minimum_radius = radius / max(1.0, entry_peak, exit_peak)

    return {
        "label": label,
        "points": points,
        "headings": headings,
        "start": (start_x, start_y),
        "end": (x, y),
        "radius": radius,
        "entry_transition": entry_transition,
        "exit_transition": exit_transition,
        "entry_angle": entry_angle,
        "exit_angle": exit_angle,
        "circular_angle": circular_angle,
        "circular_length": circular_length,
        "core_length": entry_transition + circular_length + exit_transition,
        "entry_shape_parameter": entry_shape_parameter,
        "exit_shape_parameter": exit_shape_parameter,
        "minimum_radius": minimum_radius,
    }


def main_circle_centre(main_transition, main_radius):
    x_end, y_end, entry_angle = clothoid_entry_displacement(
        main_transition,
        main_radius,
    )
    normal_x, normal_y = left_normal(entry_angle)
    return (
        x_end + (main_radius * normal_x),
        y_end + (main_radius * normal_y),
    )


def transition_start_signed_offset(circle_centre_y, radius, transition_length):
    """Signed offset of an entry/exit tangent line in canonical left-turn space."""
    _x_end, y_end, angle = clothoid_entry_displacement(
        transition_length,
        radius,
    )
    return circle_centre_y - y_end - (radius * math.cos(angle))


def solve_transition_length(
    circle_centre_y,
    radius,
    target_signed_offset,
    total_angle,
    track_name,
    end_name,
):
    """Solve a monotonic Euler transition length for a requested tangent offset."""
    if radius <= 0.0:
        raise ValueError("The radius for '{}' must be greater than zero.".format(track_name))

    maximum_length = max(0.0, (2.0 * radius * total_angle) - 1.0e-6)
    offset_at_zero = transition_start_signed_offset(circle_centre_y, radius, 0.0)
    offset_at_maximum = transition_start_signed_offset(
        circle_centre_y,
        radius,
        maximum_length,
    )

    upper_offset = max(offset_at_zero, offset_at_maximum)
    lower_offset = min(offset_at_zero, offset_at_maximum)
    if target_signed_offset < lower_offset - 1.0e-6 or target_signed_offset > upper_offset + 1.0e-6:
        raise ValueError(
            "{} spacing for '{}' cannot be produced by a single same-direction "
            "Euler easement with the selected curve radius and turn angle.\n\n"
            "Requested signed offset: {:+.3f} mm\n"
            "Achievable signed range: {:+.3f} to {:+.3f} mm\n\n"
            "Change the straight spacing, curve spacing, main radius or total "
            "turn angle.".format(
                end_name,
                track_name,
                target_signed_offset,
                lower_offset,
                upper_offset,
            )
        )

    if abs(target_signed_offset - offset_at_zero) <= 1.0e-8:
        return 0.0
    if abs(target_signed_offset - offset_at_maximum) <= 1.0e-8:
        return maximum_length

    low = 0.0
    high = maximum_length
    value_low = offset_at_zero - target_signed_offset
    value_high = offset_at_maximum - target_signed_offset

    if value_low * value_high > 0.0:
        raise ValueError(
            "Could not bracket the {} easement solution for '{}'.".format(
                end_name.lower(),
                track_name,
            )
        )

    for _iteration in range(72):
        midpoint = 0.5 * (low + high)
        value_midpoint = (
            transition_start_signed_offset(circle_centre_y, radius, midpoint)
            - target_signed_offset
        )
        if abs(value_midpoint) <= 1.0e-10 or (high - low) <= 1.0e-7:
            return midpoint

        if value_low * value_midpoint <= 0.0:
            high = midpoint
            value_high = value_midpoint
        else:
            low = midpoint
            value_low = value_midpoint

    return 0.5 * (low + high)


def build_concentric_core(
    circle_centre,
    radius,
    entry_transition,
    exit_transition,
    total_angle,
    label,
):
    """Build one canonical left-turn Euler-circle-Euler alignment."""
    if radius <= 0.0:
        raise ValueError("The constant radius for '{}' must be greater than zero.".format(label))
    if entry_transition < 0.0 or exit_transition < 0.0:
        raise ValueError("Easement lengths for '{}' cannot be negative.".format(label))

    entry_angle = entry_transition / (2.0 * radius)
    exit_angle = exit_transition / (2.0 * radius)
    circular_angle = total_angle - entry_angle - exit_angle
    if circular_angle < -1.0e-9:
        raise ValueError(
            "The independent easements for '{}' consume more angle than the "
            "complete curve.\n\nEntry easement: {:.3f} mm\nExit easement: "
            "{:.3f} mm\nMaximum combined length: {:.3f} mm".format(
                label,
                entry_transition,
                exit_transition,
                2.0 * radius * total_angle,
            )
        )
    circular_angle = max(0.0, circular_angle)

    centre_x, centre_y = circle_centre
    entry_x, entry_y, _entry_angle_check = clothoid_entry_displacement(
        entry_transition,
        radius,
    )

    entry_normal_x, entry_normal_y = left_normal(entry_angle)
    circle_start_x = centre_x - (radius * entry_normal_x)
    circle_start_y = centre_y - (radius * entry_normal_y)
    start_x = circle_start_x - entry_x
    start_y = circle_start_y - entry_y

    points = [vector_xy(start_x, start_y)]
    headings = [0.0]
    x = start_x
    y = start_y
    heading = 0.0

    if entry_transition > GEOMETRY_TOLERANCE:
        x, y, heading = integrate_path_segment(
            points,
            headings,
            x,
            y,
            heading,
            entry_transition,
            lambda station: station / (radius * entry_transition),
        )

    # Snap to the exact concentric-circle start to remove accumulated sampling error.
    x = circle_start_x
    y = circle_start_y
    heading = entry_angle
    points[-1] = vector_xy(x, y)
    headings[-1] = heading

    circular_length = radius * circular_angle
    if circular_length > GEOMETRY_TOLERANCE:
        x, y, heading = integrate_path_segment(
            points,
            headings,
            x,
            y,
            heading,
            circular_length,
            lambda _station: 1.0 / radius,
        )

    circle_end_heading = total_angle - exit_angle
    exit_normal_x, exit_normal_y = left_normal(circle_end_heading)
    circle_end_x = centre_x - (radius * exit_normal_x)
    circle_end_y = centre_y - (radius * exit_normal_y)
    x = circle_end_x
    y = circle_end_y
    heading = circle_end_heading
    points[-1] = vector_xy(x, y)
    headings[-1] = heading

    if exit_transition > GEOMETRY_TOLERANCE:
        x, y, heading = integrate_path_segment(
            points,
            headings,
            x,
            y,
            heading,
            exit_transition,
            lambda station: (1.0 - (station / exit_transition)) / radius,
        )

        # Snap the endpoint to an independently integrated high-accuracy value.
        exit_dx, exit_dy, _exit_angle_check = clothoid_exit_displacement(
            exit_transition,
            radius,
        )
        rotated_dx, rotated_dy = rotate_xy(
            exit_dx,
            exit_dy,
            circle_end_heading,
        )
        x = circle_end_x + rotated_dx
        y = circle_end_y + rotated_dy
        points[-1] = vector_xy(x, y)

    heading = total_angle
    headings[-1] = heading

    return {
        "label": label,
        "points": points,
        "headings": headings,
        "start": (start_x, start_y),
        "end": (x, y),
        "radius": radius,
        "entry_transition": entry_transition,
        "exit_transition": exit_transition,
        "entry_angle": entry_angle,
        "exit_angle": exit_angle,
        "circular_angle": circular_angle,
        "circular_length": circular_length,
        "core_length": entry_transition + circular_length + exit_transition,
    }


def add_common_straight_extensions(alignments, total_angle):
    """Extend all independent tracks to shared entry and exit cross-sections."""
    if not alignments:
        return

    common_start_x = min(item["start"][0] for item in alignments)
    tangent_x = math.cos(total_angle)
    tangent_y = math.sin(total_angle)
    common_end_projection = max(
        dot_xy(item["end"][0], item["end"][1], tangent_x, tangent_y)
        for item in alignments
    )

    for item in alignments:
        points = item["points"]
        headings = item["headings"]
        start_x, start_y = item["start"]
        entry_extension = max(0.0, start_x - common_start_x)
        if entry_extension > GEOMETRY_TOLERANCE:
            points.insert(0, vector_xy(common_start_x, start_y))
            headings.insert(0, 0.0)

        end_x, end_y = item["end"]
        current_projection = dot_xy(end_x, end_y, tangent_x, tangent_y)
        exit_extension = max(0.0, common_end_projection - current_projection)
        if exit_extension > GEOMETRY_TOLERANCE:
            end_x += exit_extension * tangent_x
            end_y += exit_extension * tangent_y
            points.append(vector_xy(end_x, end_y))
            headings.append(total_angle)

        item["entry_extension"] = entry_extension
        item["exit_extension"] = exit_extension
        item["total_length"] = item["core_length"] + entry_extension + exit_extension
        item["extended_start"] = (common_start_x, start_y)
        item["extended_end"] = (end_x, end_y)


def mirror_alignment_for_turn(alignment, turn_sign):
    if turn_sign > 0.0:
        return
    alignment["points"] = [vector_xy(point.x, -point.y) for point in alignment["points"]]
    alignment["headings"] = [-heading for heading in alignment["headings"]]
    for key in ("start", "end", "extended_start", "extended_end"):
        if key in alignment:
            x, y = alignment[key]
            alignment[key] = (x, -y)


def signed_side_factor(side):
    return 1.0 if side == "Inside" else -1.0


def effective_constant_radius(main_radius, curve_spacing, side):
    if side == "Inside":
        return main_radius - curve_spacing
    return main_radius + curve_spacing


def prepare_track_alignment(
    config,
    circle_centre,
    main_radius,
    total_angle,
    main_alignment,
):
    name = config["name"]
    side = config["side"]
    side_factor = signed_side_factor(side)

    if min(
        config["start_spacing"],
        config["curve_spacing"],
        config["finish_spacing"],
        config["width"],
    ) <= 0.0:
        raise ValueError(
            "All spacing and width values for '{}' must be greater than zero.".format(
                name
            )
        )

    radius = effective_constant_radius(
        main_radius,
        config["curve_spacing"],
        side,
    )
    if radius <= config["width"] / 2.0:
        raise ValueError(
            "The constant radius for '{}' is {:.3f} mm, which is too small for "
            "its {:.3f} mm template width.".format(name, radius, config["width"])
        )

    mode = config["alignment_mode"]
    if mode == MODE_MATCH_SPACINGS:
        entry_transition = solve_transition_length(
            circle_centre[1],
            radius,
            side_factor * config["start_spacing"],
            total_angle,
            name,
            "Entry",
        )
        exit_transition = solve_transition_length(
            circle_centre[1],
            radius,
            side_factor * config["finish_spacing"],
            total_angle,
            name,
            "Exit",
        )
        actual_start_spacing = config["start_spacing"]
        actual_finish_spacing = config["finish_spacing"]
        alignment = build_concentric_core(
            circle_centre,
            radius,
            entry_transition,
            exit_transition,
            total_angle,
            name,
        )
        alignment["minimum_radius"] = radius

    elif mode == MODE_USE_LENGTHS:
        entry_transition = config["entry_transition_length"]
        exit_transition = config["exit_transition_length"]
        signed_entry = transition_start_signed_offset(
            circle_centre[1],
            radius,
            entry_transition,
        )
        signed_exit = transition_start_signed_offset(
            circle_centre[1],
            radius,
            exit_transition,
        )

        if signed_entry * side_factor <= GEOMETRY_TOLERANCE:
            raise ValueError(
                "The manual entry Euler easement for '{}' places its entry straight "
                "on the wrong side of the main track. Change the entry length or "
                "select Platform widening.".format(name)
            )
        if signed_exit * side_factor <= GEOMETRY_TOLERANCE:
            raise ValueError(
                "The manual exit Euler easement for '{}' places its exit straight "
                "on the wrong side of the main track. Change the exit length or "
                "select Platform widening.".format(name)
            )

        actual_start_spacing = abs(signed_entry)
        actual_finish_spacing = abs(signed_exit)
        alignment = build_concentric_core(
            circle_centre,
            radius,
            entry_transition,
            exit_transition,
            total_angle,
            name,
        )
        alignment["minimum_radius"] = radius

    elif mode == MODE_PLATFORM:
        entry_transition = config["entry_transition_length"]
        exit_transition = config["exit_transition_length"]
        if entry_transition <= GEOMETRY_TOLERANCE:
            raise ValueError(
                "Platform widening for '{}' needs a positive Entry transition "
                "length.".format(name)
            )
        if exit_transition <= GEOMETRY_TOLERANCE:
            raise ValueError(
                "Platform widening for '{}' needs a positive Exit transition "
                "length.".format(name)
            )

        main_entry_line_offset = main_alignment["start"][1]
        final_normal_x, final_normal_y = left_normal(total_angle)
        main_exit_line_offset = dot_xy(
            main_alignment["end"][0],
            main_alignment["end"][1],
            final_normal_x,
            final_normal_y,
        )
        target_entry_line_offset = (
            main_entry_line_offset + (side_factor * config["start_spacing"])
        )
        target_exit_line_offset = (
            main_exit_line_offset + (side_factor * config["finish_spacing"])
        )

        entry_solution = solve_platform_shape_parameter(
            circle_centre,
            radius,
            entry_transition,
            target_entry_line_offset,
            total_angle,
            name,
            "Entry",
            "entry",
        )
        exit_solution = solve_platform_shape_parameter(
            circle_centre,
            radius,
            exit_transition,
            target_exit_line_offset,
            total_angle,
            name,
            "Exit",
            "exit",
        )

        alignment = build_platform_core(
            circle_centre,
            radius,
            entry_transition,
            exit_transition,
            entry_solution["shape_parameter"],
            exit_solution["shape_parameter"],
            total_angle,
            name,
        )
        actual_start_spacing = config["start_spacing"]
        actual_finish_spacing = config["finish_spacing"]
        alignment["entry_shape_parameter"] = entry_solution["shape_parameter"]
        alignment["exit_shape_parameter"] = exit_solution["shape_parameter"]

        if alignment["minimum_radius"] <= config["width"] / 2.0:
            raise ValueError(
                "The platform widening for '{}' produces a peak minimum radius "
                "of {:.3f} mm, which is too small for its {:.3f} mm template "
                "width. Increase the platform transition length or reduce the "
                "spacing change.".format(
                    name,
                    alignment["minimum_radius"],
                    config["width"],
                )
            )
    else:
        raise ValueError(
            "Unknown alignment mode '{}' for '{}'.".format(mode, name)
        )

    # Store the exact values that produced the geometry. This lets the dialogue
    # reopen with accurate calculated values in every mode.
    config["entry_transition_length"] = entry_transition
    config["exit_transition_length"] = exit_transition
    config["start_spacing"] = actual_start_spacing
    config["finish_spacing"] = actual_finish_spacing

    alignment.update(
        {
            "name": name,
            "side": side,
            "alignment_mode": mode,
            "start_spacing": actual_start_spacing,
            "curve_spacing": config["curve_spacing"],
            "finish_spacing": actual_finish_spacing,
            "width": config["width"],
            "create_template": config["create_template"],
            "show_centreline": config["show_centreline"],
        }
    )
    return alignment


def polyline_length(points):
    total = 0.0
    for point_a, point_b in zip(points[:-1], points[1:]):
        total += math.hypot(point_b.x - point_a.x, point_b.y - point_a.y)
    return total


def _straight_heading_delta(first, second):
    return abs(math.atan2(math.sin(first - second), math.cos(first - second)))


def _straight_alignment_record(
    route_id,
    route_name,
    track_number,
    name,
    points,
    heading,
    width,
    thickness,
    create_template,
    show_centreline,
    connection_mode,
    source_alignment_name="",
):
    total_length = polyline_length(points)
    if total_length <= GEOMETRY_TOLERANCE:
        raise ValueError("A straight track length must be greater than zero.")
    return {
        "route_id": route_id,
        "route_name": route_name,
        "track_number": int(track_number),
        "name": name,
        "points": points,
        "headings": [heading for _point in points],
        "width": float(width),
        "template_thickness": float(thickness),
        "create_template": bool(create_template),
        "show_centreline": bool(show_centreline),
        "connection_mode": connection_mode,
        "source_alignment_name": source_alignment_name,
        "total_length": total_length,
        "core_length": total_length,
        "entry_extension": 0.0,
        "exit_extension": 0.0,
        "start": (points[0].x, points[0].y),
        "end": (points[-1].x, points[-1].y),
        "extended_start": (points[0].x, points[0].y),
        "extended_end": (points[-1].x, points[-1].y),
    }


def build_straight_route(config, curve_alignments):
    config = clone_straight_config(config)
    if not config["enabled"]:
        return None
    if config["length"] <= GEOMETRY_TOLERANCE:
        raise ValueError(
            "Straight route '{}' must have a length greater than zero.".format(
                config["name"]
            )
        )
    if not config["create_template"] and not config["show_centreline"]:
        raise ValueError(
            "Straight route '{}' must create a strip, a centreline, or both.".format(
                config["name"]
            )
        )

    route_id = "straight-{}".format(config["manager_id"])
    route_name = config["name"]
    connection_mode = config["connection_mode"]
    alignments = []

    if connection_mode == STRAIGHT_CONNECTION_INDEPENDENT:
        heading = math.radians(config["rotation_degrees"])
        if config["direction"] == STRAIGHT_DIRECTION_REVERSE:
            heading += math.pi
        tangent_x = math.cos(heading)
        tangent_y = math.sin(heading)
        normal_x, normal_y = left_normal(heading)
        side_factor = (
            -1.0
            if config["parallel_side"] == STRAIGHT_PARALLEL_RIGHT
            else 1.0
        )
        for track_index in range(config["track_count"]):
            offset = side_factor * track_index * config["track_spacing"]
            start_x = config["start_x"] + (offset * normal_x)
            start_y = config["start_y"] + (offset * normal_y)
            finish_x = start_x + (config["length"] * tangent_x)
            finish_y = start_y + (config["length"] * tangent_y)
            points = [
                vector_xy(start_x, start_y),
                vector_xy(finish_x, finish_y),
            ]
            track_name = (
                route_name
                if config["track_count"] == 1
                else "{} - Track {}".format(route_name, track_index + 1)
            )
            alignments.append(
                _straight_alignment_record(
                    route_id,
                    route_name,
                    track_index + 1,
                    track_name,
                    points,
                    heading,
                    config["template_width"],
                    config["template_thickness"],
                    config["create_template"],
                    config["show_centreline"],
                    connection_mode,
                )
            )
    else:
        if not curve_alignments:
            raise ValueError(
                "Straight route '{}' cannot connect because no curve tracks exist.".format(
                    route_name
                )
            )
        reference_heading = None
        for track_index, source_alignment in enumerate(curve_alignments):
            source_points = list(source_alignment.get("points", []))
            source_headings = list(source_alignment.get("headings", []))
            if len(source_points) < 2 or len(source_points) != len(source_headings):
                raise ValueError(
                    "Straight route '{}' cannot connect to incomplete curve track '{}'.".format(
                        route_name,
                        source_alignment.get("name", track_index + 1),
                    )
                )
            if connection_mode == STRAIGHT_CONNECTION_CURVE_ENTRANCE:
                join_point = source_points[0]
                heading = source_headings[0]
                remote_point = vector_xy(
                    join_point.x - (config["length"] * math.cos(heading)),
                    join_point.y - (config["length"] * math.sin(heading)),
                )
                points = [remote_point, vector_xy(join_point.x, join_point.y)]
                joined_point = points[-1]
            else:
                join_point = source_points[-1]
                heading = source_headings[-1]
                remote_point = vector_xy(
                    join_point.x + (config["length"] * math.cos(heading)),
                    join_point.y + (config["length"] * math.sin(heading)),
                )
                points = [vector_xy(join_point.x, join_point.y), remote_point]
                joined_point = points[0]

            if reference_heading is None:
                reference_heading = heading
            elif _straight_heading_delta(heading, reference_heading) > 1.0e-10:
                raise ValueError(
                    "Straight route '{}' cannot connect because the selected curve tracks do not share one tangent direction.".format(
                        route_name
                    )
                )

            join_error = math.hypot(
                joined_point.x - join_point.x,
                joined_point.y - join_point.y,
            )
            source_heading = (
                source_headings[0]
                if connection_mode == STRAIGHT_CONNECTION_CURVE_ENTRANCE
                else source_headings[-1]
            )
            if join_error > 1.0e-7 or _straight_heading_delta(
                heading, source_heading
            ) > 1.0e-10:
                raise ValueError(
                    "Internal straight connection check failed for '{}' and '{}'.".format(
                        route_name,
                        source_alignment.get("name", track_index + 1),
                    )
                )

            source_name = str(
                source_alignment.get("name", "Track {}".format(track_index + 1))
            )
            alignments.append(
                _straight_alignment_record(
                    route_id,
                    route_name,
                    track_index + 1,
                    "{} - {}".format(route_name, source_name),
                    points,
                    heading,
                    source_alignment["width"],
                    TEMPLATE_THICKNESS,
                    config["create_template"]
                    and source_alignment.get("create_template", True),
                    config["show_centreline"]
                    and source_alignment.get("show_centreline", True),
                    connection_mode,
                    source_name,
                )
            )

    if not alignments:
        raise ValueError(
            "Straight route '{}' did not produce any track alignments.".format(
                route_name
            )
        )
    return {
        "route_id": route_id,
        "name": route_name,
        "connection_mode": connection_mode,
        "config": config,
        "alignments": alignments,
        "length": config["length"],
    }


def build_straight_routes(straight_configs, curve_alignments):
    routes = []
    seen_ids = set()
    for index, stored_config in enumerate(straight_configs):
        config = clone_straight_config(stored_config, index)
        if config["manager_id"] in seen_ids:
            config["manager_id"] = new_straight_manager_id()
        seen_ids.add(config["manager_id"])
        route = build_straight_route(config, curve_alignments)
        if route is not None:
            routes.append(route)
    return routes


def validate_connected_straight_routes(straight_routes, curve_alignments):
    expected_count = len(curve_alignments)
    for route in straight_routes:
        mode = route.get("connection_mode")
        if mode == STRAIGHT_CONNECTION_INDEPENDENT:
            continue
        alignments = list(route.get("alignments", []))
        if len(alignments) != expected_count:
            raise ValueError(
                "Connected straight route '{}' produced {} track(s), but the curve contains {} track(s). No existing generated objects have been removed.".format(
                    route.get("name", "Unnamed straight"),
                    len(alignments),
                    expected_count,
                )
            )
        for index, (straight, curve) in enumerate(zip(alignments, curve_alignments)):
            straight_points = list(straight.get("points", []))
            curve_points = list(curve.get("points", []))
            straight_headings = list(straight.get("headings", []))
            curve_headings = list(curve.get("headings", []))
            if len(straight_points) != 2 or not curve_points:
                raise ValueError(
                    "Connected straight route '{}' contains incomplete Track {} geometry. No existing generated objects have been removed.".format(
                        route.get("name", "Unnamed straight"), index + 1
                    )
                )
            if mode == STRAIGHT_CONNECTION_CURVE_ENTRANCE:
                straight_join = straight_points[-1]
                curve_join = curve_points[0]
                straight_heading = straight_headings[-1]
                curve_heading = curve_headings[0]
                travel_projection = dot_xy(
                    straight_points[0].x - curve_join.x,
                    straight_points[0].y - curve_join.y,
                    math.cos(curve_heading),
                    math.sin(curve_heading),
                )
                expected_sign_ok = travel_projection < -GEOMETRY_TOLERANCE
            else:
                straight_join = straight_points[0]
                curve_join = curve_points[-1]
                straight_heading = straight_headings[0]
                curve_heading = curve_headings[-1]
                travel_projection = dot_xy(
                    straight_points[-1].x - curve_join.x,
                    straight_points[-1].y - curve_join.y,
                    math.cos(curve_heading),
                    math.sin(curve_heading),
                )
                expected_sign_ok = travel_projection > GEOMETRY_TOLERANCE
            join_error = math.hypot(
                straight_join.x - curve_join.x,
                straight_join.y - curve_join.y,
            )
            if (
                join_error > 1.0e-7
                or _straight_heading_delta(straight_heading, curve_heading) > 1.0e-10
                or not expected_sign_ok
            ):
                raise ValueError(
                    "Connected straight route '{}' failed its Track {} endpoint or tangent validation. No existing generated objects have been removed.".format(
                        route.get("name", "Unnamed straight"), index + 1
                    )
                )


def alignment_station_data(alignment):
    points = list(alignment.get("points", []))
    headings = list(alignment.get("headings", []))
    if len(points) < 2 or len(points) != len(headings):
        raise ValueError("A selected track alignment is incomplete.")

    stations = [0.0]
    for point_a, point_b in zip(points[:-1], points[1:]):
        stations.append(
            stations[-1] + math.hypot(point_b.x - point_a.x, point_b.y - point_a.y)
        )
    total = stations[-1]
    entry_extension = min(max(0.0, alignment.get("entry_extension", 0.0)), total)
    exit_extension = min(max(0.0, alignment.get("exit_extension", 0.0)), total)
    core_start = entry_extension
    core_end = max(core_start, total - exit_extension)
    return {
        "alignment": alignment,
        "points": points,
        "headings": headings,
        "stations": stations,
        "total": total,
        "core_start": core_start,
        "core_end": core_end,
    }


def interpolate_alignment_station(data, station):
    station = min(max(float(station), 0.0), data["total"])
    stations = data["stations"]
    index = bisect.bisect_right(stations, station) - 1
    index = max(0, min(index, len(stations) - 2))
    start_station = stations[index]
    finish_station = stations[index + 1]
    span = finish_station - start_station
    fraction = 0.0 if span <= GEOMETRY_TOLERANCE else (station - start_station) / span
    point_a = data["points"][index]
    point_b = data["points"][index + 1]
    heading_a = data["headings"][index]
    heading_b = data["headings"][index + 1]
    return (
        vector_xy(
            point_a.x + ((point_b.x - point_a.x) * fraction),
            point_a.y + ((point_b.y - point_a.y) * fraction),
        ),
        heading_a + ((heading_b - heading_a) * fraction),
    )


def alignment_progress_at_station(data, station, turn_sign):
    _point, heading = interpolate_alignment_station(data, station)
    return max(0.0, heading * turn_sign)


def station_for_progress_heading(data, target_progress, turn_sign):
    low = data["core_start"]
    high = data["core_end"]
    progress_low = alignment_progress_at_station(data, low, turn_sign)
    progress_high = alignment_progress_at_station(data, high, turn_sign)
    target = min(max(float(target_progress), progress_low), progress_high)

    if target <= progress_low + 1.0e-11:
        return low
    if target >= progress_high - 1.0e-11:
        return high

    for _iteration in range(64):
        midpoint = 0.5 * (low + high)
        progress = alignment_progress_at_station(data, midpoint, turn_sign)
        if progress < target:
            low = midpoint
        else:
            high = midpoint
    return 0.5 * (low + high)


def platform_coverage_bounds(alignments, coverage, turn_sign):
    if not alignments:
        raise ValueError("A platform needs at least one selected track.")

    totals = []
    entry_limits = []
    exit_limits = []
    for alignment in alignments:
        data = alignment_station_data(alignment)
        total = alignment_progress_at_station(data, data["core_end"], turn_sign)
        totals.append(total)
        entry_limits.append(abs(float(alignment.get("entry_angle", 0.0))))
        exit_limits.append(total - abs(float(alignment.get("exit_angle", 0.0))))

    total_progress = min(totals)
    constant_start = max(entry_limits)
    constant_finish = min(exit_limits)
    if coverage == PLATFORM_CORE:
        return 0.0, total_progress
    if constant_finish <= constant_start + 1.0e-10:
        raise ValueError(
            "The selected tracks do not share a usable constant-curve heading range. "
            "Choose Both transitions and constant curve, or change the track geometry."
        )
    if coverage == PLATFORM_CONSTANT:
        return constant_start, constant_finish
    if coverage == PLATFORM_ENTRY:
        return 0.0, constant_finish
    if coverage == PLATFORM_EXIT:
        return constant_start, total_progress
    raise ValueError("Unknown platform coverage mode '{}'.".format(coverage))


def sample_station_interval(data, start_station, finish_station, turn_sign):
    length = finish_station - start_station
    if length <= GEOMETRY_TOLERANCE:
        raise ValueError("The platform start and finish positions leave no usable length.")
    steps = max(1, int(math.ceil(length / SAMPLE_SPACING)))
    samples = []
    for index in range(steps + 1):
        station = start_station + (length * index / float(steps))
        point, heading = interpolate_alignment_station(data, station)
        samples.append((point, heading, max(0.0, heading * turn_sign)))
    return samples


def unique_progress_values(values):
    result = []
    for value in sorted(values):
        if not result or abs(value - result[-1]) > 1.0e-10:
            result.append(value)
    return result


def offset_xy_point(point, heading, distance):
    normal_x, normal_y = left_normal(heading)
    return vector_xy(
        point.x + (distance * normal_x),
        point.y + (distance * normal_y),
    )


def validate_platform_inputs(config, all_alignments):
    if not config["enabled"]:
        return
    if not config["name"].strip():
        raise ValueError("The platform name cannot be blank.")
    if not all_alignments:
        raise ValueError("No track alignments are available for the platform.")

    maximum_index = len(all_alignments) - 1
    if config["track_a_index"] < 0 or config["track_a_index"] > maximum_index:
        raise ValueError("Platform Track A no longer exists. Select an available track.")
    if config["arrangement"] == PLATFORM_BETWEEN:
        if config["track_b_index"] < 0 or config["track_b_index"] > maximum_index:
            raise ValueError("Platform Track B no longer exists. Select an available track.")
        if config["track_a_index"] == config["track_b_index"]:
            raise ValueError("A between-track platform needs two different tracks.")

    if config["clearance_a"] <= 0.0:
        raise ValueError("The Track A platform-edge clearance must be greater than zero.")
    if config["arrangement"] == PLATFORM_BETWEEN and config["clearance_b"] <= 0.0:
        raise ValueError("The Track B platform-edge clearance must be greater than zero.")
    if config["platform_length"] <= 0.0:
        raise ValueError("Platform length must be greater than zero.")
    if config["arrangement"] == PLATFORM_OUTSIDE and config["platform_width"] <= 0.0:
        raise ValueError("An outside platform width must be greater than zero.")
    if config["body_output"] == PLATFORM_SOLID and config["platform_height"] <= 0.0:
        raise ValueError("A 3D platform height must be greater than zero.")
    if (
        config["body_output"] == PLATFORM_SOLID
        and config["vertical_end_ramps"]
        and config["platform_height"] <= TEMPLATE_THICKNESS + GEOMETRY_TOLERANCE
    ):
        raise ValueError(
            "A tapered 3D platform must be higher than the {:.3f} mm trackbed "
            "template surface.".format(TEMPLATE_THICKNESS)
        )
    if (
        config["entry_end_style"] == PLATFORM_END_TAPERED
        and config["entry_taper_length"] <= 0.0
    ):
        raise ValueError("A tapered entry ramp needs an entry end length greater than zero.")
    if (
        config["exit_end_style"] == PLATFORM_END_TAPERED
        and config["exit_taper_length"] <= 0.0
    ):
        raise ValueError("A tapered exit ramp needs an exit end length greater than zero.")
    if not config["create_edges"] and config["body_output"] == PLATFORM_EDGES_ONLY:
        raise ValueError(
            "The platform is enabled but both edge creation and body creation are disabled."
        )
    if config["check_clearance"]:
        required = config["required_clearance"]
        selected = [config["track_a_index"]]
        clearances = [config["clearance_a"]]
        if config["arrangement"] == PLATFORM_BETWEEN:
            selected.append(config["track_b_index"])
            clearances.append(config["clearance_b"])
        for track_index, clearance in zip(selected, clearances):
            track = all_alignments[track_index]
            template_half_width = (
                0.5 * float(track["width"])
                if track.get("create_template", False)
                else 0.0
            )
            minimum = max(required, template_half_width)
            if clearance + 1.0e-9 < minimum:
                raise ValueError(
                    "Platform clearance beside '{}' is {:.3f} mm, but the enabled "
                    "clearance check requires at least {:.3f} mm. Increase the edge "
                    "clearance, reduce the required envelope, or untick the check.".format(
                        track["name"], clearance, minimum
                    )
                )


def validate_platform_configurations(platform_configs):
    enabled = [
        (index + 1, clone_platform_config(config))
        for index, config in enumerate(platform_configs)
        if config.get("enabled", False)
    ]
    names = {}
    for platform_number, config in enabled:
        key = config["name"].strip().casefold()
        if key in names:
            raise ValueError(
                "Platforms {:02d} and {:02d} use the same name '{}'. "
                "Give every enabled platform a unique name.".format(
                    names[key], platform_number, config["name"]
                )
            )
        names[key] = platform_number


def validate_platform_relationships(platform_results, all_alignments):
    for result in platform_results:
        config = result["config"]
        plan_face = result.get("plan_face")
        if plan_face is None or not config.get("check_clearance", False):
            continue
        selected_tracks = {int(config["track_a_index"])}
        if config["arrangement"] == PLATFORM_BETWEEN:
            selected_tracks.add(int(config["track_b_index"]))
        required = float(config.get("required_clearance", 0.0))
        if required <= 0.0:
            continue
        for track_index, alignment in enumerate(all_alignments):
            if track_index in selected_tracks:
                continue
            template_half_width = (
                0.5 * float(alignment["width"])
                if alignment.get("create_template", False)
                else 0.0
            )
            minimum_clearance = max(required, template_half_width)
            clearance_face = create_template_plan_face(
                alignment["points"],
                alignment["headings"],
                2.0 * minimum_clearance,
            )
            common = plan_face.common(clearance_face)
            if (
                common is not None
                and not common.isNull()
                and float(getattr(common, "Area", 0.0)) > 1.0e-5
            ):
                raise ValueError(
                    "Platform {:02d} '{}' enters the {:.3f} mm clearance "
                    "envelope of '{}'. Adjust its width, position or track choice.".format(
                        result["platform_number"],
                        config["name"],
                        minimum_clearance,
                        alignment["name"],
                    )
                )

    for left_index, left in enumerate(platform_results):
        left_face = left.get("plan_face")
        if left_face is None:
            continue
        for right in platform_results[left_index + 1:]:
            right_face = right.get("plan_face")
            if right_face is None:
                continue
            common = left_face.common(right_face)
            if (
                common is not None
                and not common.isNull()
                and float(getattr(common, "Area", 0.0)) > 1.0e-5
            ):
                raise ValueError(
                    "Platform {:02d} '{}' overlaps Platform {:02d} '{}'. "
                    "Adjust their lengths, centre offsets, widths or track choices.".format(
                        left["platform_number"],
                        left["config"]["name"],
                        right["platform_number"],
                        right["config"]["name"],
                    )
                )


def _projection_point_distance_squared(point_a, point_b):
    return ((point_a.x - point_b.x) ** 2) + ((point_a.y - point_b.y) ** 2)


def _find_normal_projection_station(
    data,
    point_at_station,
    reference_point,
    reference_heading,
    preferred_station=None,
    minimum_station=0.0,
    description="selected track",
):
    tangent_x = math.cos(reference_heading)
    tangent_y = math.sin(reference_heading)
    minimum_station = min(max(float(minimum_station), 0.0), data["total"])

    def projection_value(station):
        point = point_at_station(station)
        return dot_xy(
            point.x - reference_point.x,
            point.y - reference_point.y,
            tangent_x,
            tangent_y,
        )

    stations = data["stations"]

    def collect_candidates(segment_indices):
        candidates = []
        for index in segment_indices:
            if index < 0 or index >= len(stations) - 1:
                continue
            segment_start = stations[index]
            segment_finish = stations[index + 1]
            if segment_finish < minimum_station - GEOMETRY_TOLERANCE:
                continue

            low = max(segment_start, minimum_station)
            high = segment_finish
            if high < low + GEOMETRY_TOLERANCE:
                continue

            value_low = projection_value(low)
            value_high = projection_value(high)
            if abs(value_low) <= 1.0e-10:
                candidates.append(low)
            if value_low * value_high < 0.0 or abs(value_high) <= 1.0e-10:
                if abs(value_high) <= 1.0e-10:
                    candidates.append(high)
                else:
                    for _iteration in range(48):
                        midpoint = 0.5 * (low + high)
                        value_mid = projection_value(midpoint)
                        if value_low * value_mid <= 0.0:
                            high = midpoint
                            value_high = value_mid
                        else:
                            low = midpoint
                            value_low = value_mid
                    candidates.append(0.5 * (low + high))
        return candidates

    candidates = []
    if preferred_station is not None:
        preferred_index = bisect.bisect_right(stations, preferred_station) - 1
        local_radius = 10
        local_indices = range(
            max(0, preferred_index - local_radius),
            min(len(stations) - 1, preferred_index + local_radius + 1),
        )
        candidates = collect_candidates(local_indices)

    if not candidates:
        candidates = collect_candidates(range(len(stations) - 1))

    unique_candidates = []
    for station in sorted(candidates):
        if (
            not unique_candidates
            or abs(station - unique_candidates[-1]) > 1.0e-7
        ):
            unique_candidates.append(station)

    if not unique_candidates:
        closest_station = None
        closest_error = None
        if preferred_station is not None:
            preferred_index = bisect.bisect_right(stations, preferred_station) - 1
            sample_indices = range(
                max(0, preferred_index - 12),
                min(len(stations), preferred_index + 13),
            )
        else:
            sample_indices = range(len(stations))
        for index in sample_indices:
            station = stations[index]
            if station + GEOMETRY_TOLERANCE < minimum_station:
                continue
            error = abs(projection_value(station))
            if closest_error is None or error < closest_error:
                closest_error = error
                closest_station = station
        if (
            closest_station is not None
            and closest_error is not None
            and closest_error <= PLATFORM_PROJECTION_TOLERANCE
        ):
            unique_candidates.append(closest_station)

    if not unique_candidates:
        raise ValueError(
            "A perpendicular platform cross-section from Track A does not meet {}. "
            "Reduce the platform length, move its centre towards the middle of the "
            "selected coverage, or check that the tracks remain alongside one another.".format(description)
        )

    if preferred_station is not None:
        return min(
            unique_candidates,
            key=lambda station: abs(station - preferred_station),
        )

    return min(
        unique_candidates,
        key=lambda station: _projection_point_distance_squared(
            point_at_station(station), reference_point
        ),
    )


def _project_centreline_to_reference_normal(
    data,
    reference_point,
    reference_heading,
    preferred_station=None,
    minimum_station=0.0,
):
    def point_at_station(station):
        point, _heading = interpolate_alignment_station(data, station)
        return point

    station = _find_normal_projection_station(
        data,
        point_at_station,
        reference_point,
        reference_heading,
        preferred_station,
        minimum_station,
        "Track B centreline",
    )
    point, heading = interpolate_alignment_station(data, station)
    return station, point, heading


def _offset_point_towards_reference(data, station, reference_point, clearance):
    point, heading = interpolate_alignment_station(data, station)
    normal_x, normal_y = left_normal(heading)
    signed_distance = dot_xy(
        reference_point.x - point.x,
        reference_point.y - point.y,
        normal_x,
        normal_y,
    )
    if abs(signed_distance) <= GEOMETRY_TOLERANCE:
        raise ValueError(
            "The selected platform tracks meet or cross, so Track B's platform "
            "edge side cannot be determined."
        )
    side_sign = 1.0 if signed_distance > 0.0 else -1.0
    return (
        offset_xy_point(point, heading, side_sign * clearance),
        point,
        heading,
        side_sign,
    )


def _project_offset_edge_to_reference_normal(
    data,
    reference_point,
    reference_heading,
    reference_edge_point,
    clearance,
    preferred_station=None,
    minimum_station=0.0,
):
    def point_at_station(station):
        edge_point, _point, _heading, _side_sign = _offset_point_towards_reference(
            data,
            station,
            reference_point,
            clearance,
        )
        return edge_point

    station = _find_normal_projection_station(
        data,
        point_at_station,
        reference_edge_point,
        reference_heading,
        preferred_station,
        minimum_station,
        "Track B platform edge",
    )
    edge_point, point, heading, side_sign = _offset_point_towards_reference(
        data,
        station,
        reference_point,
        clearance,
    )
    return station, edge_point, point, heading, side_sign


def _platform_point_distance(point_a, point_b):
    return math.hypot(point_b.x - point_a.x, point_b.y - point_a.y)


def _platform_relative_stations(sample_stations):
    if len(sample_stations) < 2:
        raise ValueError("The platform calculation produced too few station samples.")
    origin = float(sample_stations[0])
    relative = [max(0.0, float(value) - origin) for value in sample_stations]
    total = relative[-1]
    if total <= GEOMETRY_TOLERANCE:
        raise ValueError("The platform calculation produced no usable length.")
    return relative, total


def _validate_platform_end_lengths(config, platform_length):
    entry_taper = (
        config["entry_taper_length"]
        if config["entry_end_style"] == PLATFORM_END_TAPERED
        else 0.0
    )
    exit_taper = (
        config["exit_taper_length"]
        if config["exit_end_style"] == PLATFORM_END_TAPERED
        else 0.0
    )
    for label, value in (
        ("Entry end", entry_taper),
        ("Exit end", exit_taper),
    ):
        if value > platform_length + GEOMETRY_TOLERANCE:
            raise ValueError(
                "{} length {:.3f} mm exceeds the available platform length "
                "of {:.3f} mm.".format(label, value, platform_length)
            )
    if entry_taper + exit_taper > platform_length + GEOMETRY_TOLERANCE:
        raise ValueError(
            "Entry and exit end lengths total {:.3f} mm, exceeding the "
            "available platform length of {:.3f} mm. Reduce one or both end "
            "lengths.".format(entry_taper + exit_taper, platform_length)
        )


def _platform_taper_factor(config, station, platform_length, current_width):
    factor = 1.0
    if config["entry_end_style"] == PLATFORM_END_TAPERED:
        factor = min(factor, station / config["entry_taper_length"])
    if config["exit_end_style"] == PLATFORM_END_TAPERED:
        factor = min(
            factor,
            (platform_length - station) / config["exit_taper_length"],
        )
    factor = min(max(factor, 0.0), 1.0)
    minimum_factor = min(
        1.0,
        PLATFORM_MIN_NOSE_WIDTH / max(current_width, PLATFORM_MIN_NOSE_WIDTH),
    )
    return max(factor, minimum_factor)


def apply_platform_plan_tapers(edge_a, edge_b, stations, config):
    if len(edge_a) != len(edge_b) or len(edge_a) != len(stations):
        raise ValueError("Platform taper data is internally inconsistent.")
    if len(edge_a) < 2:
        raise ValueError("A platform taper needs at least two cross-sections.")

    platform_length = stations[-1]
    _validate_platform_end_lengths(config, platform_length)
    if (
        config["entry_end_style"] == PLATFORM_END_SQUARE
        and config["exit_end_style"] == PLATFORM_END_SQUARE
    ):
        widths = [
            _platform_point_distance(point_a, point_b)
            for point_a, point_b in zip(edge_a, edge_b)
        ]
        return list(edge_a), list(edge_b), min(widths)

    tapered_a = []
    tapered_b = []
    minimum_width = None
    between = config["arrangement"] == PLATFORM_BETWEEN
    for point_a, point_b, station in zip(edge_a, edge_b, stations):
        vector_x = point_b.x - point_a.x
        vector_y = point_b.y - point_a.y
        current_width = math.hypot(vector_x, vector_y)
        if current_width <= GEOMETRY_TOLERANCE:
            raise ValueError("The platform has no positive width before tapering.")
        factor = _platform_taper_factor(
            config,
            station,
            platform_length,
            current_width,
        )
        if between:
            midpoint_x = 0.5 * (point_a.x + point_b.x)
            midpoint_y = 0.5 * (point_a.y + point_b.y)
            half_x = 0.5 * vector_x * factor
            half_y = 0.5 * vector_y * factor
            new_a = vector_xy(midpoint_x - half_x, midpoint_y - half_y)
            new_b = vector_xy(midpoint_x + half_x, midpoint_y + half_y)
        else:
            new_a = vector_xy(point_a.x, point_a.y)
            new_b = vector_xy(
                point_a.x + (vector_x * factor),
                point_a.y + (vector_y * factor),
            )
        width = _platform_point_distance(new_a, new_b)
        minimum_width = width if minimum_width is None else min(minimum_width, width)
        tapered_a.append(new_a)
        tapered_b.append(new_b)

    return tapered_a, tapered_b, float(minimum_width)


def calculate_platform_top_heights(config, stations, platform_length):
    full_height = float(config["platform_height"])
    if config["body_output"] != PLATFORM_SOLID:
        return [full_height for _station in stations]

    entry_length = (
        float(config["entry_taper_length"])
        if config["entry_end_style"] == PLATFORM_END_TAPERED
        else 0.0
    )
    exit_length = (
        float(config["exit_taper_length"])
        if config["exit_end_style"] == PLATFORM_END_TAPERED
        else 0.0
    )
    trackbed_height = float(TEMPLATE_THICKNESS)
    heights = []
    for station in stations:
        height = full_height
        if entry_length > GEOMETRY_TOLERANCE and station < entry_length:
            fraction = min(max(station / entry_length, 0.0), 1.0)
            height = min(
                height,
                trackbed_height + ((full_height - trackbed_height) * fraction),
            )
        if (
            exit_length > GEOMETRY_TOLERANCE
            and (platform_length - station) < exit_length
        ):
            fraction = min(
                max((platform_length - station) / exit_length, 0.0),
                1.0,
            )
            height = min(
                height,
                trackbed_height + ((full_height - trackbed_height) * fraction),
            )
        heights.append(max(trackbed_height, height))
    return heights


def resolve_platform_longitudinal_bounds(config, base_start, base_finish):
    base_start = float(base_start)
    base_finish = float(base_finish)
    available = base_finish - base_start
    if available <= GEOMETRY_TOLERANCE:
        raise ValueError("The selected platform coverage has no usable length.")

    requested_length = float(config["platform_length"])
    if requested_length <= GEOMETRY_TOLERANCE:
        raise ValueError("Platform length must be greater than zero.")

    midpoint = 0.5 * (base_start + base_finish)
    centre_offset = float(config["centre_offset"])
    centre_station = midpoint + centre_offset
    half_available = 0.5 * available
    if (
        centre_station < base_start - GEOMETRY_TOLERANCE
        or centre_station > base_finish + GEOMETRY_TOLERANCE
    ):
        raise ValueError(
            "Platform centre offset {:.3f} mm lies outside the selected {:.3f} mm "
            "coverage. Keep the centre offset between {:.3f} mm and {:.3f} mm.".format(
                centre_offset,
                available,
                -half_available,
                half_available,
            )
        )

    centre_station = min(max(centre_station, base_start), base_finish)
    maximum_length = max(
        0.0,
        2.0 * min(centre_station - base_start, base_finish - centre_station),
    )
    if requested_length > maximum_length + GEOMETRY_TOLERANCE:
        raise ValueError(
            "Requested platform length {:.3f} mm does not fit around a centre offset "
            "of {:.3f} mm within the selected coverage. The maximum length at this "
            "centre is {:.3f} mm. Reduce Platform length to {:.3f} mm or move Centre "
            "offset towards 0 mm.".format(
                requested_length,
                centre_offset,
                maximum_length,
                maximum_length,
            )
        )

    start_station = centre_station - (0.5 * requested_length)
    finish_station = centre_station + (0.5 * requested_length)
    start_station = max(base_start, start_station)
    finish_station = min(base_finish, finish_station)
    return {
        "start_station": start_station,
        "finish_station": finish_station,
        "centre_station": centre_station,
        "centre_offset": centre_station - midpoint,
        "length": finish_station - start_station,
        "available_length": available,
        "start_inset": start_station - base_start,
        "finish_inset": base_finish - finish_station,
    }


def calculate_platform_boundaries(config, all_alignments, turn_sign):
    if not config["enabled"]:
        return None
    validate_platform_inputs(config, all_alignments)

    alignment_a = all_alignments[config["track_a_index"]]
    data_a = alignment_station_data(alignment_a)
    selected_alignments = [alignment_a]
    alignment_b = None
    data_b = None
    if config["arrangement"] == PLATFORM_BETWEEN:
        alignment_b = all_alignments[config["track_b_index"]]
        data_b = alignment_station_data(alignment_b)
        selected_alignments.append(alignment_b)

    start_progress, finish_progress = platform_coverage_bounds(
        selected_alignments,
        config["coverage"],
        turn_sign,
    )
    base_start_a = station_for_progress_heading(data_a, start_progress, turn_sign)
    base_finish_a = station_for_progress_heading(data_a, finish_progress, turn_sign)
    longitudinal = resolve_platform_longitudinal_bounds(
        config,
        base_start_a,
        base_finish_a,
    )
    start_station_a = longitudinal["start_station"]
    finish_station_a = longitudinal["finish_station"]

    actual_start_progress = alignment_progress_at_station(
        data_a, start_station_a, turn_sign
    )
    actual_finish_progress = alignment_progress_at_station(
        data_a, finish_station_a, turn_sign
    )
    if actual_finish_progress <= actual_start_progress + 1.0e-10:
        raise ValueError("The selected platform section has no usable turn progression.")

    edge_a = []
    edge_b = []
    sample_stations = []
    minimum_full_width = None
    maximum_tangent_mismatch = 0.0

    sample_length = finish_station_a - start_station_a
    _validate_platform_end_lengths(config, sample_length)
    sample_steps = max(1, int(math.ceil(sample_length / SAMPLE_SPACING)))
    relative_sample_stations = [
        sample_length * index / float(sample_steps)
        for index in range(sample_steps + 1)
    ]
    important_stations = []
    if config["entry_end_style"] == PLATFORM_END_TAPERED:
        important_stations.append(config["entry_taper_length"])
    if config["exit_end_style"] == PLATFORM_END_TAPERED:
        important_stations.append(sample_length - config["exit_taper_length"])
    if config["body_output"] == PLATFORM_SOLID and config["vertical_end_ramps"]:
        if config["entry_ramp_length"] > 0.0:
            important_stations.append(config["entry_ramp_length"])
        if config["exit_ramp_length"] > 0.0:
            important_stations.append(sample_length - config["exit_ramp_length"])
    relative_sample_stations.extend(
        min(max(value, 0.0), sample_length) for value in important_stations
    )
    relative_sample_stations = unique_progress_values(relative_sample_stations)

    samples_a = []
    for relative_station in relative_sample_stations:
        station_a = start_station_a + relative_station
        point_a, heading_a = interpolate_alignment_station(data_a, station_a)
        progress = max(0.0, heading_a * turn_sign)
        samples_a.append((station_a, point_a, heading_a, progress))

    if config["arrangement"] == PLATFORM_BETWEEN:
        side_sign = None
        previous_b_station = None

        for station_a, point_a, heading_a, progress in samples_a:
            minimum_b_station = (
                0.0
                if previous_b_station is None
                else max(0.0, previous_b_station - 1.0e-6)
            )
            centre_station_b, point_b, _heading_b = (
                _project_centreline_to_reference_normal(
                    data_b,
                    point_a,
                    heading_a,
                    previous_b_station,
                    0.0,
                )
            )

            normal_x, normal_y = left_normal(heading_a)
            tangent_x = math.cos(heading_a)
            tangent_y = math.sin(heading_a)
            difference_x = point_b.x - point_a.x
            difference_y = point_b.y - point_a.y
            normal_separation = dot_xy(
                difference_x, difference_y, normal_x, normal_y
            )
            if abs(normal_separation) <= GEOMETRY_TOLERANCE:
                raise ValueError("The selected platform tracks meet or cross.")

            current_sign = 1.0 if normal_separation > 0.0 else -1.0
            if side_sign is None:
                side_sign = current_sign
            elif current_sign != side_sign:
                raise ValueError(
                    "The selected platform tracks change sides within the requested section."
                )

            point_edge_a = offset_xy_point(
                point_a,
                heading_a,
                side_sign * config["clearance_a"],
            )
            (
                edge_station_b,
                point_edge_b,
                _point_b,
                _heading_b,
                _edge_side_b,
            ) = _project_offset_edge_to_reference_normal(
                data_b,
                point_a,
                heading_a,
                point_edge_a,
                config["clearance_b"],
                centre_station_b,
                minimum_b_station,
            )

            if (
                previous_b_station is not None
                and edge_station_b + 1.0e-6 < previous_b_station
            ):
                raise ValueError(
                    "Track B reverses along the platform cross-sections. Reduce the "
                    "coverage or check that the selected tracks remain parallel."
                )
            previous_b_station = edge_station_b

            edge_difference_x = point_edge_b.x - point_edge_a.x
            edge_difference_y = point_edge_b.y - point_edge_a.y
            available_width = side_sign * dot_xy(
                edge_difference_x,
                edge_difference_y,
                normal_x,
                normal_y,
            )
            tangent_mismatch = abs(
                dot_xy(
                    edge_difference_x,
                    edge_difference_y,
                    tangent_x,
                    tangent_y,
                )
            )
            maximum_tangent_mismatch = max(
                maximum_tangent_mismatch, tangent_mismatch
            )
            if tangent_mismatch > PLATFORM_PROJECTION_TOLERANCE:
                raise ValueError(
                    "An internal platform cross-section check failed at heading "
                    "{:.3f} deg: the two edges are misaligned by {:.3f} mm.".format(
                        math.degrees(progress), tangent_mismatch
                    )
                )

            if available_width <= GEOMETRY_TOLERANCE:
                raise ValueError(
                    "The between-track platform has no positive width at heading "
                    "{:.3f} deg. The perpendicular track-centre gap there is {:.3f} "
                    "mm and the two edge clearances total {:.3f} mm. Reduce the "
                    "clearances below {:.3f} mm combined or increase track spacing.".format(
                        math.degrees(progress),
                        abs(normal_separation),
                        config["clearance_a"] + config["clearance_b"],
                        abs(normal_separation),
                    )
                )

            minimum_full_width = (
                available_width
                if minimum_full_width is None
                else min(minimum_full_width, available_width)
            )
            sample_stations.append(station_a)
            edge_a.append(point_edge_a)
            edge_b.append(point_edge_b)

        description = "between '{}' and '{}'".format(
            alignment_a["name"], alignment_b["name"]
        )
    else:
        side_sign = 1.0 if config["outside_side"] == PLATFORM_LEFT else -1.0
        for station_a, point, heading, _progress in samples_a:
            sample_stations.append(station_a)
            edge_a.append(
                offset_xy_point(point, heading, side_sign * config["clearance_a"])
            )
            edge_b.append(
                offset_xy_point(
                    point,
                    heading,
                    side_sign * (config["clearance_a"] + config["platform_width"]),
                )
            )
        minimum_full_width = config["platform_width"]
        description = "{} of '{}'".format(
            config["outside_side"].lower(), alignment_a["name"]
        )

    if len(edge_a) < 2 or len(edge_b) < 2:
        raise ValueError("The platform calculation produced too few edge points.")

    relative_stations, platform_length = _platform_relative_stations(sample_stations)
    edge_a, edge_b, minimum_tapered_width = apply_platform_plan_tapers(
        edge_a,
        edge_b,
        relative_stations,
        config,
    )
    top_heights = calculate_platform_top_heights(
        config,
        relative_stations,
        platform_length,
    )
    boundary = edge_a + list(reversed(edge_b))
    return {
        "name": config["name"],
        "description": description,
        "edge_a": edge_a,
        "edge_b": edge_b,
        "boundary": boundary,
        "stations": relative_stations,
        "top_heights": top_heights,
        "length": platform_length,
        "requested_length": float(config["platform_length"]),
        "centre_offset": longitudinal["centre_offset"],
        "available_coverage_length": longitudinal["available_length"],
        "start_inset": longitudinal["start_inset"],
        "finish_inset": longitudinal["finish_inset"],
        "minimum_width": float(minimum_full_width),
        "minimum_tapered_width": float(minimum_tapered_width),
        "start_progress": actual_start_progress,
        "finish_progress": actual_finish_progress,
        "maximum_tangent_mismatch": maximum_tangent_mismatch,
        "track_a_name": alignment_a["name"],
        "track_b_name": alignment_b["name"] if alignment_b is not None else "",
        "track_a_index": int(config["track_a_index"]),
        "track_b_index": int(config["track_b_index"]),
        "arrangement": config["arrangement"],
    }


def _platform_points_close(point_a, point_b, tolerance=1.0e-7):
    return _platform_point_distance(point_a, point_b) <= tolerance


def _clean_platform_boundary(points):
    clean = []
    for point in points:
        if not clean or not _platform_points_close(clean[-1], point):
            clean.append(point)
    if len(clean) < 3:
        raise ValueError("The platform boundary has too few distinct points.")
    if _platform_points_close(clean[0], clean[-1]):
        clean[-1] = clean[0]
    else:
        clean.append(clean[0])
    if len(clean) < 4:
        raise ValueError("The platform boundary cannot form a closed face.")
    return clean


def _create_platform_face(boundary_points, z_height):
    clean = _clean_platform_boundary(boundary_points)
    vectors = [App.Vector(point.x, point.y, z_height) for point in clean]
    boundary_wire = Part.makePolygon(vectors)
    if not boundary_wire.isClosed():
        raise ValueError("FreeCAD could not close the platform boundary.")
    face = Part.Face(boundary_wire)
    if face.isNull():
        raise ValueError(
            "FreeCAD could not create the platform face. Reduce the platform "
            "length or check that the selected tracks do not cross."
        )
    try:
        if not face.isValid():
            raise ValueError(
                "The platform face is self-intersecting or otherwise invalid."
            )
    except AttributeError:
        pass
    return face


def _nearest_station_index(stations, target):
    position = bisect.bisect_left(stations, target)
    choices = []
    if position < len(stations):
        choices.append(position)
    if position > 0:
        choices.append(position - 1)
    return min(choices, key=lambda index: abs(stations[index] - target))


def _platform_loft_profile_indices(platform_geometry, config):
    stations = platform_geometry["stations"]
    platform_length = platform_geometry["length"]
    indices = {0, len(stations) - 1}
    last_station = stations[0]
    for index, station in enumerate(stations[1:-1], 1):
        if station - last_station >= PLATFORM_LOFT_PROFILE_SPACING:
            indices.add(index)
            last_station = station

    important_stations = []
    if config["entry_end_style"] == PLATFORM_END_TAPERED:
        important_stations.append(config["entry_taper_length"])
    if config["exit_end_style"] == PLATFORM_END_TAPERED:
        important_stations.append(platform_length - config["exit_taper_length"])
    for station in important_stations:
        station = min(max(station, 0.0), platform_length)
        indices.add(_nearest_station_index(stations, station))
    return sorted(indices)


def _create_platform_cross_section_wire(point_a, point_b, top_height):
    height = max(float(top_height), PLATFORM_MIN_RAMP_HEIGHT)
    bottom_a = App.Vector(point_a.x, point_a.y, 0.0)
    bottom_b = App.Vector(point_b.x, point_b.y, 0.0)
    top_b = App.Vector(point_b.x, point_b.y, height)
    top_a = App.Vector(point_a.x, point_a.y, height)
    wire = Part.makePolygon([bottom_a, bottom_b, top_b, top_a, bottom_a])
    if not wire.isClosed():
        raise ValueError("FreeCAD could not close a sloping-platform cross-section.")
    return wire


def _create_sloped_platform_solid(platform_geometry, config):
    indices = _platform_loft_profile_indices(platform_geometry, config)
    if len(indices) < 2:
        raise ValueError("A sloping platform needs at least two loft profiles.")
    profiles = []
    for index in indices:
        profiles.append(
            _create_platform_cross_section_wire(
                platform_geometry["edge_a"][index],
                platform_geometry["edge_b"][index],
                platform_geometry["top_heights"][index],
            )
        )
    try:
        body = Part.makeLoft(profiles, True, True)
    except TypeError:
        body = Part.makeLoft(profiles, True, True, False)
    if body.isNull():
        raise ValueError("FreeCAD could not loft the sloping platform body.")
    try:
        if not body.isValid():
            raise ValueError(
                "The sloping platform body is invalid. Reduce taper or ramp lengths, "
                "or increase the platform width."
            )
    except AttributeError:
        pass
    return body


def create_platform_shapes(platform_geometry, config):
    if platform_geometry is None:
        return None

    body_output = config["body_output"]
    if body_output == PLATFORM_SOLID:
        body_z = 0.0
    else:
        body_z = PLATFORM_2D_LIFT

    edge_shapes = []
    if config["create_edges"]:
        for points in (platform_geometry["edge_a"], platform_geometry["edge_b"]):
            lifted = []
            for index, point in enumerate(points):
                if body_output == PLATFORM_SOLID:
                    edge_z = (
                        max(
                            platform_geometry["top_heights"][index],
                            PLATFORM_MIN_RAMP_HEIGHT
                            if config["vertical_end_ramps"]
                            else 0.0,
                        )
                        + CENTRELINE_LIFT
                    )
                else:
                    edge_z = PLATFORM_2D_LIFT + CENTRELINE_LIFT
                lifted.append(App.Vector(point.x, point.y, edge_z))
            edge_shape = Part.makePolygon(lifted)
            if edge_shape.isNull():
                raise ValueError("FreeCAD could not create a platform-edge wire.")
            edge_shapes.append(edge_shape)

    body_shape = None
    if body_output == PLATFORM_FACE:
        body_shape = _create_platform_face(
            platform_geometry["boundary"],
            body_z,
        )
    elif body_output == PLATFORM_SOLID:
        if config["vertical_end_ramps"]:
            body_shape = _create_sloped_platform_solid(platform_geometry, config)
        else:
            face = _create_platform_face(platform_geometry["boundary"], body_z)
            body_shape = face.extrude(
                App.Vector(0.0, 0.0, config["platform_height"])
            )
            if body_shape.isNull():
                raise ValueError("FreeCAD could not create a solid platform body.")

    return {
        "edge_shapes": edge_shapes,
        "body_shape": body_shape,
        "body_is_solid": body_output == PLATFORM_SOLID,
    }

def create_template_shape(points, headings, template_width, template_thickness=TEMPLATE_THICKNESS):
    if template_width <= 0.0:
        raise ValueError("Every template width must be greater than zero.")
    if template_thickness <= 0.0:
        raise ValueError("Every template thickness must be greater than zero.")
    if len(points) < 2 or len(points) != len(headings):
        raise ValueError("A calculated centreline is incomplete.")

    half_width = template_width / 2.0
    left_edge = []
    right_edge = []

    for point, heading in zip(points, headings):
        normal_x, normal_y = left_normal(heading)
        left_edge.append(
            vector_xy(
                point.x + (half_width * normal_x),
                point.y + (half_width * normal_y),
            )
        )
        right_edge.append(
            vector_xy(
                point.x - (half_width * normal_x),
                point.y - (half_width * normal_y),
            )
        )

    boundary = left_edge + list(reversed(right_edge))
    boundary.append(boundary[0])
    boundary_wire = Part.makePolygon(boundary)
    if not boundary_wire.isClosed():
        raise ValueError("FreeCAD could not close a template boundary.")

    face = Part.Face(boundary_wire)
    if face.isNull():
        raise ValueError("FreeCAD could not create a template face.")

    solid = face.extrude(App.Vector(0.0, 0.0, template_thickness))
    if solid.isNull():
        raise ValueError("FreeCAD could not create a solid template.")
    return solid


def create_centreline_wire(points, template_thickness=TEMPLATE_THICKNESS):
    lifted_points = [
        App.Vector(point.x, point.y, template_thickness + CENTRELINE_LIFT)
        for point in points
    ]
    return Part.makePolygon(lifted_points)



def _xy_distance(point_a, point_b):
    return math.hypot(point_b.x - point_a.x, point_b.y - point_a.y)


def create_plan_polyline(points, description):
    """Create an open XY polyline from sampled plan points."""
    projected = []
    for point in points:
        candidate = vector_xy(point.x, point.y)
        if not projected or _xy_distance(projected[-1], candidate) > 1.0e-7:
            projected.append(candidate)
    if len(projected) < 2:
        raise ValueError("{} has too few distinct plan points.".format(description))
    wire = Part.makePolygon(projected)
    if wire.isNull():
        raise ValueError("FreeCAD could not create {}.".format(description))
    return wire


def _clean_closed_boundary(points, description):
    clean = []
    for point in points:
        if not clean or _xy_distance(clean[-1], point) > 1.0e-7:
            clean.append(vector_xy(point.x, point.y))
    if len(clean) >= 2 and _xy_distance(clean[0], clean[-1]) <= 1.0e-7:
        clean[-1] = clean[0]
    else:
        clean.append(clean[0])
    if len(clean) < 4:
        raise ValueError("{} has too few distinct points.".format(description))
    return clean


def _create_plan_face(points, description):
    boundary = _clean_closed_boundary(points, description)
    wire = Part.makePolygon(boundary)
    if not wire.isClosed():
        raise ValueError("FreeCAD could not close {}.".format(description))
    face = Part.Face(wire)
    if face.isNull():
        raise ValueError("FreeCAD could not create {}.".format(description))
    try:
        if not face.isValid():
            raise ValueError("{} is self-intersecting or invalid.".format(description))
    except AttributeError:
        pass
    return face


def create_template_plan_face(points, headings, template_width):
    if template_width <= 0.0:
        raise ValueError("Every template width must be greater than zero.")
    if len(points) < 2 or len(points) != len(headings):
        raise ValueError("A calculated centreline is incomplete.")
    half_width = 0.5 * template_width
    left_edge = []
    right_edge = []
    for point, heading in zip(points, headings):
        normal_x, normal_y = left_normal(heading)
        left_edge.append(vector_xy(point.x + half_width * normal_x, point.y + half_width * normal_y))
        right_edge.append(vector_xy(point.x - half_width * normal_x, point.y - half_width * normal_y))
    return _create_plan_face(left_edge + list(reversed(right_edge)), "a track-template plan footprint")


def create_alignment_envelope_face(alignment, outer_margin):
    points = list(alignment["points"])
    headings = list(alignment["headings"])
    if len(points) < 2 or len(points) != len(headings):
        raise ValueError("A selected formation track alignment is incomplete.")
    half_width = 0.5 * float(alignment["width"]) + float(outer_margin)
    left_edge = []
    right_edge = []
    for index, (point, heading) in enumerate(zip(points, headings)):
        tangent_shift = 0.0
        if index == 0:
            tangent_shift = -float(outer_margin)
        elif index == len(points) - 1:
            tangent_shift = float(outer_margin)
        base_x = point.x + tangent_shift * math.cos(heading)
        base_y = point.y + tangent_shift * math.sin(heading)
        normal_x, normal_y = left_normal(heading)
        left_edge.append(vector_xy(base_x + half_width * normal_x, base_y + half_width * normal_y))
        right_edge.append(vector_xy(base_x - half_width * normal_x, base_y - half_width * normal_y))
    return _create_plan_face(left_edge + list(reversed(right_edge)), "a formation track swept envelope")


def create_between_alignments_face(alignment_a, alignment_b):
    data_a = alignment_station_data(alignment_a)
    data_b = alignment_station_data(alignment_b)
    steps = max(
        2,
        int(math.ceil(max(data_a["total"], data_b["total"]) / SAMPLE_SPACING)),
    )
    points_a = []
    points_b = []
    for index in range(steps + 1):
        fraction = index / float(steps)
        point_a, _heading_a = interpolate_alignment_station(data_a, data_a["total"] * fraction)
        point_b, _heading_b = interpolate_alignment_station(data_b, data_b["total"] * fraction)
        points_a.append(point_a)
        points_b.append(point_b)
    return _create_plan_face(
        points_a + list(reversed(points_b)),
        "a formation gap-filling ribbon between adjacent tracks",
    )


def create_platform_plan_face(platform_geometry):
    if platform_geometry is None:
        return None
    return _create_plan_face(platform_geometry["boundary"], "the platform plan footprint")


def create_platform_envelope_face(platform_geometry, outer_margin):
    if platform_geometry is None:
        return None
    edge_a = list(platform_geometry["edge_a"])
    edge_b = list(platform_geometry["edge_b"])
    if len(edge_a) < 2 or len(edge_a) != len(edge_b):
        raise ValueError("The platform footprint is incomplete.")
    expanded_a = []
    expanded_b = []
    centres = [
        vector_xy(0.5 * (point_a.x + point_b.x), 0.5 * (point_a.y + point_b.y))
        for point_a, point_b in zip(edge_a, edge_b)
    ]
    for point_a, point_b in zip(edge_a, edge_b):
        width_x = point_b.x - point_a.x
        width_y = point_b.y - point_a.y
        width = math.hypot(width_x, width_y)
        if width <= GEOMETRY_TOLERANCE:
            raise ValueError("The platform footprint has no usable width.")
        unit_x = width_x / width
        unit_y = width_y / width
        expanded_a.append(vector_xy(point_a.x - outer_margin * unit_x, point_a.y - outer_margin * unit_y))
        expanded_b.append(vector_xy(point_b.x + outer_margin * unit_x, point_b.y + outer_margin * unit_y))
    if outer_margin > 0.0:
        start_dx = centres[1].x - centres[0].x
        start_dy = centres[1].y - centres[0].y
        start_length = max(GEOMETRY_TOLERANCE, math.hypot(start_dx, start_dy))
        finish_dx = centres[-1].x - centres[-2].x
        finish_dy = centres[-1].y - centres[-2].y
        finish_length = max(GEOMETRY_TOLERANCE, math.hypot(finish_dx, finish_dy))
        for collection in (expanded_a, expanded_b):
            collection[0] = vector_xy(
                collection[0].x - outer_margin * start_dx / start_length,
                collection[0].y - outer_margin * start_dy / start_length,
            )
            collection[-1] = vector_xy(
                collection[-1].x + outer_margin * finish_dx / finish_length,
                collection[-1].y + outer_margin * finish_dy / finish_length,
            )
    return _create_plan_face(
        expanded_a + list(reversed(expanded_b)),
        "the platform formation swept envelope",
    )


def _refine_shape(shape):
    try:
        refined = shape.removeSplitter()
        if refined is not None and not refined.isNull():
            return refined
    except Exception:
        pass
    return shape


def _fuse_shapes(shapes, description):
    usable = [shape for shape in shapes if shape is not None and not shape.isNull()]
    if not usable:
        raise ValueError("No geometry is available for {}.".format(description))
    result = usable[0]
    for shape in usable[1:]:
        result = result.fuse(shape)
        if result.isNull():
            raise ValueError("FreeCAD could not fuse {}.".format(description))
    return _refine_shape(result)


def _face_components(shape):
    return [face for face in list(getattr(shape, "Faces", [])) if not face.isNull()]


def _nearest_face_points(face_a, face_b):
    try:
        _distance, pairs, _info = face_a.distToShape(face_b)
        if pairs:
            return pairs[0][0], pairs[0][1]
    except Exception:
        pass
    box_a = face_a.BoundBox
    box_b = face_b.BoundBox
    return (
        vector_xy(0.5 * (box_a.XMin + box_a.XMax), 0.5 * (box_a.YMin + box_a.YMax)),
        vector_xy(0.5 * (box_b.XMin + box_b.XMax), 0.5 * (box_b.YMin + box_b.YMax)),
    )


def _make_rectangular_bridge(point_a, point_b, width):
    dx = point_b.x - point_a.x
    dy = point_b.y - point_a.y
    length = math.hypot(dx, dy)
    if length <= GEOMETRY_TOLERANCE:
        half = 0.5 * width
        return _create_plan_face(
            [
                vector_xy(point_a.x - half, point_a.y - half),
                vector_xy(point_a.x + half, point_a.y - half),
                vector_xy(point_a.x + half, point_a.y + half),
                vector_xy(point_a.x - half, point_a.y + half),
            ],
            "a minimum-neck formation connector",
        )
    tangent_x = dx / length
    tangent_y = dy / length
    normal_x = -tangent_y
    normal_y = tangent_x
    half = 0.5 * width
    start_x = point_a.x - half * tangent_x
    start_y = point_a.y - half * tangent_y
    finish_x = point_b.x + half * tangent_x
    finish_y = point_b.y + half * tangent_y
    return _create_plan_face(
        [
            vector_xy(start_x + half * normal_x, start_y + half * normal_y),
            vector_xy(finish_x + half * normal_x, finish_y + half * normal_y),
            vector_xy(finish_x - half * normal_x, finish_y - half * normal_y),
            vector_xy(start_x - half * normal_x, start_y - half * normal_y),
        ],
        "a minimum-neck formation connector",
    )


def _connect_plan_components(shape, minimum_neck_width):
    result = shape
    for _iteration in range(100):
        faces = _face_components(result)
        if len(faces) <= 1:
            return _refine_shape(result)
        base = faces[0]
        best = None
        for other in faces[1:]:
            point_a, point_b = _nearest_face_points(base, other)
            distance = _xy_distance(point_a, point_b)
            if best is None or distance < best[0]:
                best = (distance, point_a, point_b)
        if best is None:
            break
        bridge = _make_rectangular_bridge(best[1], best[2], minimum_neck_width)
        result = _refine_shape(result.fuse(bridge))
    raise ValueError("The formation-board swept envelope could not be joined into one continuous footprint.")


def _fill_enclosed_plan_gaps(shape):
    outer_faces = []
    for face in _face_components(shape):
        try:
            outer_faces.append(Part.Face(face.OuterWire))
        except Exception:
            outer_faces.append(face)
    return _fuse_shapes(outer_faces, "the filled formation-board footprint")


def _outline_shape_from_face(face_shape, lift=FORMATION_OUTLINE_LIFT):
    wires = []
    for face in _face_components(face_shape):
        wire = face.OuterWire.copy()
        if abs(lift) > GEOMETRY_TOLERANCE:
            wire.translate(App.Vector(0.0, 0.0, lift))
        wires.append(wire)
    if not wires:
        raise ValueError("The formation footprint has no closed perimeter wire.")
    return wires[0] if len(wires) == 1 else Part.makeCompound(wires)


def _protected_plan_face(template_plan_faces, platform_plan_face):
    shapes = list(template_plan_faces)
    if platform_plan_face is not None:
        shapes.append(platform_plan_face)
    if not shapes:
        return None
    return _fuse_shapes(shapes, "the protected track and platform footprints")


def create_formation_geometry(
    config,
    all_alignments,
    template_plan_faces,
    platform_geometry,
    platform_plan_face,
):
    if not config["enabled"]:
        return None
    selected_alignments = [
        alignment for alignment in all_alignments
        if alignment.get("create_template", False)
    ] if config["include_track_templates"] else []
    include_platform = bool(config["include_platform"] and platform_geometry is not None)
    if not selected_alignments and not include_platform:
        raise ValueError(
            "Formation-board output needs at least one selected track-template strip "
            "or an enabled platform footprint."
        )

    source_faces = []
    for alignment in selected_alignments:
        source_faces.append(create_alignment_envelope_face(alignment, config["outer_margin"]))

    if len(selected_alignments) > 1:
        ordered = sorted(
            selected_alignments,
            key=lambda alignment: alignment["points"][0].y,
        )
        for alignment_a, alignment_b in zip(ordered[:-1], ordered[1:]):
            source_faces.append(create_between_alignments_face(alignment_a, alignment_b))

    if include_platform:
        source_faces.append(create_platform_envelope_face(platform_geometry, config["outer_margin"]))

    footprint = _fuse_shapes(source_faces, "the formation-board swept envelope")
    footprint = _connect_plan_components(footprint, config["minimum_neck_width"])
    if config["fill_enclosed_gaps"]:
        footprint = _fill_enclosed_plan_gaps(footprint)
    if config["smooth_outline"]:
        footprint = _refine_shape(footprint)

    faces = _face_components(footprint)
    if len(faces) != 1:
        raise ValueError(
            "The formation-board swept envelope did not resolve to one continuous "
            "closed cutting footprint."
        )
    footprint = faces[0]
    try:
        if not footprint.isValid():
            raise ValueError("The formation-board cutting footprint is invalid.")
    except AttributeError:
        pass

    body = footprint.extrude(App.Vector(0.0, 0.0, -config["board_thickness"]))
    if body.isNull():
        raise ValueError("FreeCAD could not extrude the formation-board solid.")
    return {
        "face": footprint,
        "outline": _outline_shape_from_face(footprint),
        "body": body,
        "area": float(getattr(footprint, "Area", 0.0)),
        "protected_face": _protected_plan_face(template_plan_faces, platform_plan_face),
    }


def _point_distance_squared_xy(point_a, point_b):
    dx = float(point_b.x) - float(point_a.x)
    dy = float(point_b.y) - float(point_a.y)
    return dx * dx + dy * dy


def _nearest_ordered_reference_index(reference_points, point, start_index=0):
    if not reference_points:
        raise ValueError("The formation-board reference alignment has no points.")
    index = min(max(0, int(start_index)), len(reference_points) - 1)
    current_distance = _point_distance_squared_xy(reference_points[index], point)

    while index > 0:
        previous_distance = _point_distance_squared_xy(
            reference_points[index - 1], point
        )
        if previous_distance + GEOMETRY_TOLERANCE >= current_distance:
            break
        index -= 1
        current_distance = previous_distance

    while index + 1 < len(reference_points):
        next_distance = _point_distance_squared_xy(
            reference_points[index + 1], point
        )
        if next_distance + GEOMETRY_TOLERANCE >= current_distance:
            break
        index += 1
        current_distance = next_distance
    return index


def _project_formation_point_to_reference(
    reference_data,
    point,
    cursor_segment=0,
    minimum_station=0.0,
):
    points = reference_data["points"]
    stations = reference_data["stations"]
    if len(points) < 2:
        raise ValueError("The formation-board reference alignment is incomplete.")

    nearest_vertex = _nearest_ordered_reference_index(
        points,
        point,
        min(max(0, int(cursor_segment)), len(points) - 1),
    )
    segment_start = max(0, nearest_vertex - 3)
    segment_finish = min(len(points) - 2, nearest_vertex + 3)
    minimum_station = min(
        max(0.0, float(minimum_station)),
        float(reference_data["total"]),
    )

    best = None
    for segment_index in range(segment_start, segment_finish + 1):
        point_a = points[segment_index]
        point_b = points[segment_index + 1]
        station_a = float(stations[segment_index])
        station_b = float(stations[segment_index + 1])
        if station_b + GEOMETRY_TOLERANCE < minimum_station:
            continue

        dx = float(point_b.x) - float(point_a.x)
        dy = float(point_b.y) - float(point_a.y)
        length_squared = (dx * dx) + (dy * dy)
        if length_squared <= GEOMETRY_TOLERANCE:
            continue

        fraction = (
            ((float(point.x) - float(point_a.x)) * dx)
            + ((float(point.y) - float(point_a.y)) * dy)
        ) / length_squared
        fraction = min(max(fraction, 0.0), 1.0)
        if station_b > station_a + GEOMETRY_TOLERANCE:
            minimum_fraction = max(
                0.0,
                (minimum_station - station_a) / (station_b - station_a),
            )
            fraction = max(fraction, min(1.0, minimum_fraction))

        projected_x = float(point_a.x) + (fraction * dx)
        projected_y = float(point_a.y) + (fraction * dy)
        distance_squared = (
            ((float(point.x) - projected_x) ** 2)
            + ((float(point.y) - projected_y) ** 2)
        )
        station = station_a + (fraction * (station_b - station_a))
        candidate = (distance_squared, station, segment_index)
        if best is None or candidate[0] < best[0]:
            best = candidate

    if best is None:
        station = minimum_station
        segment_index = max(
            0,
            min(
                len(points) - 2,
                bisect.bisect_right(stations, station) - 1,
            ),
        )
    else:
        _distance_squared, station, segment_index = best

    reference_point, reference_heading = interpolate_alignment_station(
        reference_data, station
    )
    normal_x, normal_y = left_normal(reference_heading)
    signed_offset = dot_xy(
        float(point.x) - float(reference_point.x),
        float(point.y) - float(reference_point.y),
        normal_x,
        normal_y,
    )
    return float(station), float(signed_offset), int(segment_index)


def _formation_edge_station_samples(reference_data, edge_points):
    if len(edge_points) < 2:
        raise ValueError("A selected formation footprint edge is incomplete.")

    samples = []
    cursor_segment = 0
    minimum_station = 0.0
    for point in edge_points:
        station, signed_offset, cursor_segment = (
            _project_formation_point_to_reference(
                reference_data,
                point,
                cursor_segment,
                minimum_station,
            )
        )
        if samples and station <= samples[-1][0] + 1.0e-8:
            # Consecutive source points can project onto the same reference station.
            # Replace the duplicate rather than creating a zero-length interpolation span.
            samples[-1] = (max(station, samples[-1][0]), signed_offset)
        else:
            samples.append((station, signed_offset))
        minimum_station = max(minimum_station, station)

    if len(samples) < 2:
        raise ValueError(
            "A selected formation footprint edge could not be mapped along the route."
        )
    return samples


def _formation_offset_at_station(samples, station):
    sample_stations = [item[0] for item in samples]
    position = bisect.bisect_right(sample_stations, station) - 1
    position = max(0, min(position, len(samples) - 2))
    station_a, offset_a = samples[position]
    station_b, offset_b = samples[position + 1]
    span = station_b - station_a
    if span <= GEOMETRY_TOLERANCE:
        return float(offset_b)
    fraction = min(max((station - station_a) / span, 0.0), 1.0)
    return float(offset_a) + (fraction * (float(offset_b) - float(offset_a)))


def _accumulate_formation_path_extents(
    reference_stations,
    left_extents,
    right_extents,
    samples,
):
    first_station = float(samples[0][0])
    last_station = float(samples[-1][0])
    start_index = max(0, bisect.bisect_left(reference_stations, first_station))
    finish_index = min(
        len(reference_stations) - 1,
        bisect.bisect_right(reference_stations, last_station) - 1,
    )
    if finish_index < start_index:
        return

    for index in range(start_index, finish_index + 1):
        station = float(reference_stations[index])
        offset = _formation_offset_at_station(samples, station)
        previous_left = left_extents[index]
        previous_right = right_extents[index]
        left_extents[index] = (
            offset if previous_left is None else max(float(previous_left), offset)
        )
        right_extents[index] = (
            offset if previous_right is None else min(float(previous_right), offset)
        )


def _interpolate_formation_extents(values, start_index, finish_index):
    known = [
        index
        for index in range(start_index, finish_index + 1)
        if values[index] is not None
    ]
    if not known:
        raise ValueError("The formation-board envelope has no usable edge samples.")
    for first, second in zip(known[:-1], known[1:]):
        if second <= first + 1:
            continue
        first_value = float(values[first])
        second_value = float(values[second])
        span = float(second - first)
        for index in range(first + 1, second):
            fraction = (index - first) / span
            values[index] = first_value + fraction * (
                second_value - first_value
            )
    first_known = known[0]
    last_known = known[-1]
    for index in range(start_index, first_known):
        values[index] = values[first_known]
    for index in range(last_known + 1, finish_index + 1):
        values[index] = values[last_known]


def _broaden_formation_extent_transitions(
    values,
    stations,
    start_index,
    finish_index,
    maximum_slope,
    upper_envelope,
):
    maximum_slope = max(0.05, float(maximum_slope))
    broadened = list(values)

    for index in range(start_index + 1, finish_index + 1):
        distance = max(0.0, float(stations[index]) - float(stations[index - 1]))
        allowance = maximum_slope * distance
        if upper_envelope:
            broadened[index] = max(
                float(broadened[index]),
                float(broadened[index - 1]) - allowance,
            )
        else:
            broadened[index] = min(
                float(broadened[index]),
                float(broadened[index - 1]) + allowance,
            )

    for index in range(finish_index - 1, start_index - 1, -1):
        distance = max(0.0, float(stations[index + 1]) - float(stations[index]))
        allowance = maximum_slope * distance
        if upper_envelope:
            broadened[index] = max(
                float(broadened[index]),
                float(broadened[index + 1]) - allowance,
            )
        else:
            broadened[index] = min(
                float(broadened[index]),
                float(broadened[index + 1]) + allowance,
            )
    return broadened


def _simple_formation_swept_face(
    config,
    all_alignments,
    selected_alignments,
    platform_geometries,
):
    if not all_alignments:
        raise ValueError("Formation-board output needs a reference alignment.")
    reference = all_alignments[0]
    reference_data = alignment_station_data(reference)
    reference_points = reference_data["points"]
    reference_headings = reference_data["headings"]
    reference_stations = reference_data["stations"]
    if (
        len(reference_points) < 2
        or len(reference_points) != len(reference_headings)
    ):
        raise ValueError("The formation-board reference alignment is incomplete.")

    left_extents = [None] * len(reference_points)
    right_extents = [None] * len(reference_points)
    margin = max(0.0, float(config["outer_margin"]))
    # By default the outer margin also extends both exposed route ends. Connected
    # curve/straight boards can override either signed tangent shift internally so
    # their end caps meet at the exact shared tangent boundary without overlap.
    start_tangent_shift = float(
        config.get("_start_tangent_shift", -margin)
    )
    finish_tangent_shift = float(
        config.get("_finish_tangent_shift", margin)
    )

    def add_edge_path(edge_points):
        samples = _formation_edge_station_samples(reference_data, edge_points)
        _accumulate_formation_path_extents(
            reference_stations,
            left_extents,
            right_extents,
            samples,
        )

    for alignment in selected_alignments:
        points = list(alignment.get("points", []))
        headings = list(alignment.get("headings", []))
        if len(points) < 2 or len(points) != len(headings):
            raise ValueError(
                "A selected formation track alignment is incomplete."
            )
        half_width = 0.5 * float(alignment["width"])
        left_path = []
        right_path = []
        for point, heading in zip(points, headings):
            normal_x, normal_y = left_normal(heading)
            left_path.append(
                vector_xy(
                    point.x + half_width * normal_x,
                    point.y + half_width * normal_y,
                )
            )
            right_path.append(
                vector_xy(
                    point.x - half_width * normal_x,
                    point.y - half_width * normal_y,
                )
            )
        add_edge_path(left_path)
        add_edge_path(right_path)

    for platform_geometry in platform_geometries:
        if platform_geometry is None:
            continue
        for edge_name in ("edge_a", "edge_b"):
            add_edge_path(list(platform_geometry.get(edge_name, [])))

    active_indices = [
        index
        for index, (left_value, right_value) in enumerate(
            zip(left_extents, right_extents)
        )
        if left_value is not None or right_value is not None
    ]
    if not active_indices:
        raise ValueError(
            "Formation-board output has no usable track or platform footprint."
        )
    start_index = active_indices[0]
    finish_index = active_indices[-1]
    _interpolate_formation_extents(
        left_extents, start_index, finish_index
    )
    _interpolate_formation_extents(
        right_extents, start_index, finish_index
    )

    for index in range(start_index, finish_index + 1):
        left_extents[index] = float(left_extents[index]) + margin
        right_extents[index] = float(right_extents[index]) - margin

    # The board must support the platform, not copy every taper point. Limit the
    # longitudinal rate at which either board edge can move inwards. The two-pass
    # envelope widens the board only where needed and produces predictable run-outs
    # before and after platform ends without any face Boolean operations.
    maximum_transverse_slope = 0.5
    left_extents = _broaden_formation_extent_transitions(
        left_extents,
        reference_stations,
        start_index,
        finish_index,
        maximum_transverse_slope,
        True,
    )
    right_extents = _broaden_formation_extent_transitions(
        right_extents,
        reference_stations,
        start_index,
        finish_index,
        maximum_transverse_slope,
        False,
    )

    minimum_width = max(
        0.1, float(config.get("minimum_neck_width", 0.1))
    )
    left_edge = []
    right_edge = []
    for index in range(start_index, finish_index + 1):
        left_value = float(left_extents[index])
        right_value = float(right_extents[index])
        if left_value - right_value < minimum_width:
            midpoint = 0.5 * (left_value + right_value)
            left_value = midpoint + 0.5 * minimum_width
            right_value = midpoint - 0.5 * minimum_width

        point = reference_points[index]
        heading = reference_headings[index]
        tangent_shift = 0.0
        if index == start_index:
            tangent_shift = start_tangent_shift
        elif index == finish_index:
            tangent_shift = finish_tangent_shift
        base_x = float(point.x) + tangent_shift * math.cos(heading)
        base_y = float(point.y) + tangent_shift * math.sin(heading)
        normal_x, normal_y = left_normal(heading)
        left_edge.append(
            vector_xy(
                base_x + left_value * normal_x,
                base_y + left_value * normal_y,
            )
        )
        right_edge.append(
            vector_xy(
                base_x + right_value * normal_x,
                base_y + right_value * normal_y,
            )
        )

    # left_edge runs in the direction of travel and right_edge returns against it.
    # The first and last point pairs share one route station and tangent shift, so
    # both closing caps are straight and perpendicular to the route.
    return _create_plan_face(
        left_edge + list(reversed(right_edge)),
        "the continuous formation-board swept footprint",
    )

def create_formation_geometry_multi(
    config,
    all_alignments,
    template_plan_faces,
    platform_geometries,
    platform_plan_faces,
):
    if not config["enabled"]:
        return None
    selected_alignments = (
        [
            alignment
            for alignment in all_alignments
            if alignment.get("create_template", False)
        ]
        if config["include_track_templates"]
        else []
    )
    included_platforms = (
        [geometry for geometry in platform_geometries if geometry is not None]
        if config["include_platform"]
        else []
    )
    if not selected_alignments and not included_platforms:
        raise ValueError(
            "Formation-board output needs at least one selected track-template strip "
            "or an enabled platform footprint."
        )

    # One direct boundary and one extrusion: no Boolean union of overlapping
    # track and platform plan faces is used in the base formation-board path.
    footprint = _simple_formation_swept_face(
        config,
        all_alignments,
        selected_alignments,
        included_platforms,
    )
    try:
        if not footprint.isValid():
            raise ValueError("The formation-board cutting footprint is invalid.")
    except AttributeError:
        pass

    body = footprint.extrude(
        App.Vector(0.0, 0.0, -config["board_thickness"])
    )
    if body.isNull():
        raise ValueError("FreeCAD could not extrude the formation-board solid.")

    protected_shapes = [
        shape
        for shape in list(template_plan_faces) + list(platform_plan_faces)
        if shape is not None and not shape.isNull()
    ]
    return {
        "face": footprint,
        "outline": _outline_shape_from_face(footprint),
        "body": body,
        "area": float(getattr(footprint, "Area", 0.0)),
        "protected_face": protected_shapes,
    }


def extrude_plan_shape_down(shape, thickness):
    faces = _face_components(shape)
    if not faces:
        raise ValueError("A plan shape has no face to extrude.")
    solids = []
    for face in faces:
        solid = face.extrude(App.Vector(0.0, 0.0, -float(thickness)))
        if solid.isNull():
            raise ValueError("FreeCAD could not extrude a sectioned formation-board piece.")
        solids.append(solid)
    return solids[0] if len(solids) == 1 else Part.makeCompound(solids)


def calculate_section_plan(total_length, config):
    total_length = float(total_length)
    if total_length <= GEOMETRY_TOLERANCE:
        raise ValueError("The main alignment has no usable length for sectioning.")
    maximum = float(config["maximum_section_length"])
    enabled = bool(config["enabled"] and maximum > GEOMETRY_TOLERANCE)
    if not enabled or maximum >= total_length - GEOMETRY_TOLERANCE:
        return {"enabled": False, "boundaries": [0.0, total_length], "ranges": [(0.0, total_length)]}

    minimum = float(config["minimum_section_length"])
    if minimum > maximum + GEOMETRY_TOLERANCE:
        raise ValueError("Minimum permitted section length cannot exceed maximum section length.")
    count = int(math.ceil(total_length / maximum))
    if count > MAX_SECTION_COUNT:
        raise ValueError("The requested maximum section length would create more than {} pieces.".format(MAX_SECTION_COUNT))

    if config["balance_lengths"]:
        length = total_length / float(count)
        if count > 1 and length + GEOMETRY_TOLERANCE < minimum:
            raise ValueError(
                "Balanced section length {:.3f} mm is below the minimum permitted "
                "length of {:.3f} mm.".format(length, minimum)
            )
        boundaries = [total_length * index / float(count) for index in range(count + 1)]
    else:
        boundaries = [0.0]
        while boundaries[-1] + maximum < total_length - GEOMETRY_TOLERANCE:
            boundaries.append(boundaries[-1] + maximum)
        boundaries.append(total_length)
        if len(boundaries) > 2:
            final_length = boundaries[-1] - boundaries[-2]
            if final_length + GEOMETRY_TOLERANCE < minimum:
                combined = boundaries[-1] - boundaries[-3]
                replacement = 0.5 * combined
                if replacement + GEOMETRY_TOLERANCE < minimum or replacement > maximum + GEOMETRY_TOLERANCE:
                    raise ValueError(
                        "The final unbalanced section would be {:.3f} mm and cannot "
                        "be redistributed within the entered limits.".format(final_length)
                    )
                boundaries[-2] = boundaries[-3] + replacement

    ranges = list(zip(boundaries[:-1], boundaries[1:]))
    for start, finish in ranges:
        length = finish - start
        if len(ranges) > 1 and length + GEOMETRY_TOLERANCE < minimum:
            raise ValueError("A calculated section is shorter than the minimum permitted length.")
        if length > maximum + 1.0e-6:
            raise ValueError("A calculated section exceeds the maximum section length.")
    return {"enabled": True, "boundaries": boundaries, "ranges": ranges}


def _section_mask_half_width(shapes):
    boxes = [shape.BoundBox for shape in shapes if shape is not None and not shape.isNull()]
    if not boxes:
        return SECTION_MASK_MARGIN
    extent = max(max(box.XLength, box.YLength) for box in boxes)
    return max(SECTION_MASK_MARGIN, extent + SECTION_MASK_MARGIN)


def create_section_mask_face(
    main_alignment,
    start_station,
    finish_station,
    half_width,
    extend_start=False,
    extend_finish=False,
):
    data = alignment_station_data(main_alignment)
    length = finish_station - start_station
    steps = max(1, int(math.ceil(length / SAMPLE_SPACING)))
    left_points = []
    right_points = []
    sampled_headings = []
    for index in range(steps + 1):
        station = start_station + length * index / float(steps)
        point, heading = interpolate_alignment_station(data, station)
        sampled_headings.append(heading)
        normal_x, normal_y = left_normal(heading)
        left_points.append(vector_xy(point.x + half_width * normal_x, point.y + half_width * normal_y))
        right_points.append(vector_xy(point.x - half_width * normal_x, point.y - half_width * normal_y))
    if extend_start:
        heading = sampled_headings[0]
        extension = 2.0 * half_width
        left_points[0] = vector_xy(
            left_points[0].x - extension * math.cos(heading),
            left_points[0].y - extension * math.sin(heading),
        )
        right_points[0] = vector_xy(
            right_points[0].x - extension * math.cos(heading),
            right_points[0].y - extension * math.sin(heading),
        )
    if extend_finish:
        heading = sampled_headings[-1]
        extension = 2.0 * half_width
        left_points[-1] = vector_xy(
            left_points[-1].x + extension * math.cos(heading),
            left_points[-1].y + extension * math.sin(heading),
        )
        right_points[-1] = vector_xy(
            right_points[-1].x + extension * math.cos(heading),
            right_points[-1].y + extension * math.sin(heading),
        )
    return _create_plan_face(left_points + list(reversed(right_points)), "a shared section cutting mask")


def _source_bounds_face(source_shapes, padding):
    boxes = [shape.BoundBox for shape in source_shapes if shape is not None and not shape.isNull()]
    if not boxes:
        raise ValueError("No source geometry is available for section masks.")
    x_min = min(box.XMin for box in boxes) - padding
    x_max = max(box.XMax for box in boxes) + padding
    y_min = min(box.YMin for box in boxes) - padding
    y_max = max(box.YMax for box in boxes) + padding
    return _create_plan_face(
        [
            vector_xy(x_min, y_min),
            vector_xy(x_max, y_min),
            vector_xy(x_max, y_max),
            vector_xy(x_min, y_max),
        ],
        "the overall section-mask boundary",
    )


def _section_halfspace_face(point, heading, extent, forward):
    if forward:
        x_start, x_finish = -1.0e-5, extent
    else:
        x_start, x_finish = -extent, 1.0e-5
    return _oriented_rectangle(point, heading, x_start, x_finish, 2.0 * extent)


def create_section_masks(main_alignment, section_plan, source_shapes, z_min, z_max):
    boxes = [shape.BoundBox for shape in source_shapes if shape is not None and not shape.isNull()]
    if not boxes:
        raise ValueError("No source geometry is available for sectioning.")
    span_x = max(box.XMax for box in boxes) - min(box.XMin for box in boxes)
    span_y = max(box.YMax for box in boxes) - min(box.YMin for box in boxes)
    extent = max(SECTION_MASK_MARGIN, 4.0 * math.hypot(span_x, span_y) + SECTION_MASK_MARGIN)
    overall = _source_bounds_face(source_shapes, SECTION_MASK_MARGIN)
    data = alignment_station_data(main_alignment)
    masks = []
    range_count = len(section_plan["ranges"])
    for index, (start, finish) in enumerate(section_plan["ranges"]):
        face = overall.copy()
        if index > 0:
            start_point, start_heading = interpolate_alignment_station(data, start)
            face = face.common(_section_halfspace_face(start_point, start_heading, extent, True))
        if index < range_count - 1:
            finish_point, finish_heading = interpolate_alignment_station(data, finish)
            face = face.common(_section_halfspace_face(finish_point, finish_heading, extent, False))
        face = _refine_shape(face)
        if face.isNull() or not _face_components(face):
            raise ValueError(
                "A shared perpendicular section mask could not be created for Section {:02d}.".format(index + 1)
            )
        prism_face = face.copy()
        prism_face.translate(App.Vector(0.0, 0.0, z_min))
        prism = prism_face.extrude(App.Vector(0.0, 0.0, z_max - z_min))
        if prism.isNull():
            raise ValueError("FreeCAD could not create a section cutting prism.")
        masks.append({"start": start, "finish": finish, "face": face, "solid": prism})
    return masks


def _common_or_none(shape, cutter):
    if shape is None:
        return None
    result = shape.common(cutter)
    if result.isNull():
        return None
    try:
        if result.Volume <= GEOMETRY_TOLERANCE and result.Area <= GEOMETRY_TOLERANCE and result.Length <= GEOMETRY_TOLERANCE:
            return None
    except Exception:
        pass
    return _refine_shape(result)


def section_plan_face(face, masks):
    return [_common_or_none(face, mask["face"]) for mask in masks]


def section_solid_shape(shape, masks):
    return [_common_or_none(shape, mask["solid"]) for mask in masks]


def _shape_measure(shape):
    if shape is None or shape.isNull():
        return 0.0
    try:
        if shape.Volume > GEOMETRY_TOLERANCE:
            return float(shape.Volume)
    except Exception:
        pass
    try:
        if shape.Area > GEOMETRY_TOLERANCE:
            return float(shape.Area)
    except Exception:
        pass
    try:
        return float(shape.Length)
    except Exception:
        return 0.0


def validate_section_partition(original_shape, section_shapes, description, require_every_section=False):
    usable = [shape for shape in section_shapes if shape is not None and not shape.isNull()]
    if require_every_section and len(usable) != len(section_shapes):
        raise ValueError("One or more {} pieces are empty.".format(description))
    if not usable:
        raise ValueError("Sectioning produced no {} pieces.".format(description))
    try:
        original_volume = float(original_shape.Volume)
    except Exception:
        original_volume = 0.0
    solid_partition = original_volume > GEOMETRY_TOLERANCE

    def dimensional_measure(shape):
        if shape is None or shape.isNull():
            return 0.0
        if solid_partition:
            try:
                return float(shape.Volume)
            except Exception:
                return 0.0
        try:
            return float(shape.Area)
        except Exception:
            return 0.0

    def bound_boxes_may_overlap(shape_a, shape_b):
        box_a = shape_a.BoundBox
        box_b = shape_b.BoundBox
        if box_a.XMax < box_b.XMin - GEOMETRY_TOLERANCE or box_b.XMax < box_a.XMin - GEOMETRY_TOLERANCE:
            return False
        if box_a.YMax < box_b.YMin - GEOMETRY_TOLERANCE or box_b.YMax < box_a.YMin - GEOMETRY_TOLERANCE:
            return False
        if solid_partition:
            if box_a.ZMax < box_b.ZMin - GEOMETRY_TOLERANCE or box_b.ZMax < box_a.ZMin - GEOMETRY_TOLERANCE:
                return False
        return True

    original_measure = max(dimensional_measure(original_shape), 1.0)
    tolerance = max(1.0e-5, original_measure * 1.0e-7)

    # Every section is created with source.common(shared_mask), so each piece is
    # already clipped to the source. Check complete coverage with one Boolean cut
    # against a compound of all pieces instead of repeatedly cutting a progressively
    # fragmented remainder. This keeps the validation strict without the severe
    # OpenCascade cost seen when many curved sections are present.
    section_compound = usable[0] if len(usable) == 1 else Part.makeCompound(usable)
    missing = original_shape.cut(section_compound)
    missing_measure = dimensional_measure(missing)

    section_measure = sum(dimensional_measure(shape) for shape in usable)
    overlap_measure = 0.0
    for index, shape_a in enumerate(usable[:-1]):
        for shape_b in usable[index + 1:]:
            if not bound_boxes_may_overlap(shape_a, shape_b):
                continue
            overlap = shape_a.common(shape_b)
            measured_overlap = dimensional_measure(overlap)
            overlap_measure += measured_overlap
            if measured_overlap > tolerance:
                raise ValueError(
                    "Two {} pieces overlap by a measurable area or volume.".format(description)
                )

    reconstructed_measure = section_measure - overlap_measure
    measure_shortfall = max(0.0, original_measure - reconstructed_measure)
    measure_excess = max(0.0, reconstructed_measure - original_measure)
    if (
        missing_measure > tolerance
        or measure_shortfall > tolerance
        or measure_excess > tolerance
    ):
        raise ValueError(
            "Shared section masks do not reproduce the complete {} geometry. "
            "Missing measure {:.9g}; measure shortfall {:.9g}; measure excess {:.9g}; "
            "permitted tolerance {:.9g}. No existing generated objects have been removed.".format(
                description,
                missing_measure,
                measure_shortfall,
                measure_excess,
                tolerance,
            )
        )

def _oriented_rectangle(point, heading, x_start, x_finish, width):
    tangent_x = math.cos(heading)
    tangent_y = math.sin(heading)
    normal_x, normal_y = left_normal(heading)
    half = 0.5 * width
    return _create_plan_face(
        [
            vector_xy(point.x + x_start * tangent_x + half * normal_x, point.y + x_start * tangent_y + half * normal_y),
            vector_xy(point.x + x_finish * tangent_x + half * normal_x, point.y + x_finish * tangent_y + half * normal_y),
            vector_xy(point.x + x_finish * tangent_x - half * normal_x, point.y + x_finish * tangent_y - half * normal_y),
            vector_xy(point.x + x_start * tangent_x - half * normal_x, point.y + x_start * tangent_y - half * normal_y),
        ],
        "an oriented registration feature",
    )


def _circle_face(point, radius):
    edge = Part.makeCircle(radius, App.Vector(point.x, point.y, 0.0))
    wire = Part.Wire([edge])
    face = Part.Face(wire)
    if face.isNull():
        raise ValueError("FreeCAD could not create an alignment hole.")
    return face


def _candidate_inside_formation(candidate, formation_face):
    try:
        common = candidate.common(formation_face)
        return not common.isNull() and common.Area >= candidate.Area * 0.999
    except Exception:
        return False


def _candidate_clear_of_protected(candidate, protected_face):
    if protected_face is None:
        return True
    if isinstance(protected_face, (list, tuple)):
        for shape in protected_face:
            if not _candidate_clear_of_protected(candidate, shape):
                return False
        return True
    try:
        common = candidate.common(protected_face)
        return common.isNull() or common.Area <= 1.0e-5
    except Exception:
        return False


def _normal_offset_candidates(formation_face, feature_width):
    box = formation_face.BoundBox
    extent = math.hypot(box.XLength, box.YLength) + feature_width
    step = max(2.0, 0.75 * feature_width)
    count = max(1, int(math.ceil(extent / step)))
    values = [index * step for index in range(-count, count + 1)]
    return sorted(values, key=lambda value: (-abs(value), value))


def _offset_along_normal(point, heading, distance):
    normal_x, normal_y = left_normal(heading)
    return vector_xy(point.x + distance * normal_x, point.y + distance * normal_y)


def _find_joint_rectangles(
    formation_face,
    protected_face,
    point,
    heading,
    depth,
    width,
    clearance,
    count,
):
    found = []
    for normal_offset in _normal_offset_candidates(formation_face, width + 2.0 * clearance):
        if any(abs(normal_offset - used[0]) < 1.5 * width for used in found):
            continue
        centre = _offset_along_normal(point, heading, normal_offset)
        male = _oriented_rectangle(centre, heading, -0.25, depth, width)
        socket = _oriented_rectangle(
            centre,
            heading,
            -0.25,
            depth + clearance,
            width + 2.0 * clearance,
        )
        guard = _oriented_rectangle(
            centre,
            heading,
            -2.0,
            depth + clearance + 2.0,
            width + 2.0 * clearance + 4.0,
        )
        if not _candidate_inside_formation(guard, formation_face):
            continue
        if not _candidate_clear_of_protected(guard, protected_face):
            continue
        found.append((normal_offset, male, socket))
        if len(found) >= count:
            break
    return found


def _find_alignment_hole_pairs(
    formation_face,
    protected_face,
    point,
    heading,
    diameter,
    longitudinal_offset,
):
    tangent_x = math.cos(heading)
    tangent_y = math.sin(heading)
    radius = 0.5 * diameter
    found = []
    for normal_offset in _normal_offset_candidates(formation_face, diameter):
        if any(abs(normal_offset - used[0]) < 2.0 * diameter for used in found):
            continue
        centre = _offset_along_normal(point, heading, normal_offset)
        before = vector_xy(centre.x - longitudinal_offset * tangent_x, centre.y - longitudinal_offset * tangent_y)
        after = vector_xy(centre.x + longitudinal_offset * tangent_x, centre.y + longitudinal_offset * tangent_y)
        hole_before = _circle_face(before, radius)
        hole_after = _circle_face(after, radius)
        guard_radius = radius + max(2.0, 0.5 * diameter)
        guard_before = _circle_face(before, guard_radius)
        guard_after = _circle_face(after, guard_radius)
        if not _candidate_inside_formation(guard_before, formation_face):
            continue
        if not _candidate_inside_formation(guard_after, formation_face):
            continue
        if not _candidate_clear_of_protected(guard_before, protected_face):
            continue
        if not _candidate_clear_of_protected(guard_after, protected_face):
            continue
        found.append((normal_offset, hole_before, hole_after))
        if len(found) >= 2:
            break
    return found


def apply_registration_features(
    formation_section_faces,
    main_alignment,
    section_plan,
    formation_face,
    protected_face,
    config,
):
    joint_type = config["joint_type"]
    results = list(formation_section_faces)
    registration_shapes = []
    alignment_hole_shapes = []
    if joint_type == REGISTRATION_PLAIN or len(results) <= 1:
        return results, registration_shapes, alignment_hole_shapes

    data = alignment_station_data(main_alignment)
    for boundary_index, station in enumerate(section_plan["boundaries"][1:-1]):
        point, heading = interpolate_alignment_station(data, station)
        if joint_type == REGISTRATION_HOLES:
            pairs = _find_alignment_hole_pairs(
                formation_face,
                protected_face,
                point,
                heading,
                config["alignment_hole_diameter"],
                config["alignment_hole_offset"],
            )
            if not pairs:
                raise ValueError(
                    "No safe board material is available for alignment holes at section joint {:02d}. "
                    "Increase the formation margin, reduce the hole size, or use plain joints.".format(boundary_index + 1)
                )
            before_holes = [item[1] for item in pairs]
            after_holes = [item[2] for item in pairs]
            before_compound = _fuse_shapes(before_holes, "alignment holes before a section joint")
            after_compound = _fuse_shapes(after_holes, "alignment holes after a section joint")
            if results[boundary_index] is not None:
                results[boundary_index] = _refine_shape(results[boundary_index].cut(before_compound))
            if results[boundary_index + 1] is not None:
                results[boundary_index + 1] = _refine_shape(results[boundary_index + 1].cut(after_compound))
            alignment_hole_shapes.append(Part.makeCompound(
                [hole.OuterWire for hole in before_holes + after_holes]
            ))
        else:
            feature_count = 2 if joint_type == REGISTRATION_PINS else 1
            rectangles = _find_joint_rectangles(
                formation_face,
                protected_face,
                point,
                heading,
                config["joint_depth"],
                config["joint_width"],
                config["fit_clearance"],
                feature_count,
            )
            if not rectangles:
                raise ValueError(
                    "No safe board material is available for {} at section joint {:02d}. "
                    "Increase the formation margin, reduce the joint size, or use plain joints.".format(
                        joint_type.lower(), boundary_index + 1
                    )
                )
            male_shapes = [item[1] for item in rectangles]
            socket_shapes = [item[2] for item in rectangles]
            male = _fuse_shapes(male_shapes, "registration tongues or pins")
            socket = _fuse_shapes(socket_shapes, "registration grooves or sockets")
            if results[boundary_index] is not None:
                results[boundary_index] = _refine_shape(results[boundary_index].fuse(male))
            if results[boundary_index + 1] is not None:
                results[boundary_index + 1] = _refine_shape(results[boundary_index + 1].cut(socket))
            registration_shapes.append(Part.makeCompound(
                [shape.OuterWire for shape in male_shapes + socket_shapes]
            ))
    return results, registration_shapes, alignment_hole_shapes


def _lift_polyline(points, z_height):
    return Part.makePolygon([App.Vector(point.x, point.y, z_height) for point in points])


def create_track_engraving_shape(all_alignments):
    wires = [_lift_polyline(alignment["points"], ENGRAVING_LIFT) for alignment in all_alignments]
    return wires[0] if len(wires) == 1 else Part.makeCompound(wires)


def create_platform_engraving_shape(platform_geometry):
    if platform_geometry is None:
        return None
    wires = [
        _lift_polyline(platform_geometry["edge_a"], ENGRAVING_LIFT),
        _lift_polyline(platform_geometry["edge_b"], ENGRAVING_LIFT),
    ]
    return Part.makeCompound(wires)


def create_platforms_engraving_shape(platform_geometries):
    shapes = [
        create_platform_engraving_shape(geometry)
        for geometry in platform_geometries
        if geometry is not None
    ]
    return _compound_non_null(shapes)


_STROKE_DIGITS = {
    "0": ("a", "b", "c", "d", "e", "f"),
    "1": ("b", "c"),
    "2": ("a", "b", "g", "e", "d"),
    "3": ("a", "b", "c", "d", "g"),
    "4": ("f", "g", "b", "c"),
    "5": ("a", "f", "g", "c", "d"),
    "6": ("a", "f", "g", "e", "c", "d"),
    "7": ("a", "b", "c"),
    "8": ("a", "b", "c", "d", "e", "f", "g"),
    "9": ("a", "b", "c", "d", "f", "g"),
}
_STROKE_SEGMENTS = {
    "a": ((0.0, 1.0), (1.0, 1.0)),
    "b": ((1.0, 1.0), (1.0, 0.5)),
    "c": ((1.0, 0.5), (1.0, 0.0)),
    "d": ((0.0, 0.0), (1.0, 0.0)),
    "e": ((0.0, 0.5), (0.0, 0.0)),
    "f": ((0.0, 1.0), (0.0, 0.5)),
    "g": ((0.0, 0.5), (1.0, 0.5)),
}


def create_section_number_shape(number, origin, heading, height=8.0):
    text = "{:02d}".format(int(number))
    digit_width = 0.5 * height
    spacing = 0.18 * height
    tangent_x = math.cos(heading)
    tangent_y = math.sin(heading)
    normal_x, normal_y = left_normal(heading)
    total_width = len(text) * digit_width + (len(text) - 1) * spacing
    edges = []
    for digit_index, digit in enumerate(text):
        offset_x = -0.5 * total_width + digit_index * (digit_width + spacing)
        for segment in _STROKE_DIGITS.get(digit, ()):
            start, finish = _STROKE_SEGMENTS[segment]
            local_start_x = offset_x + start[0] * digit_width
            local_start_y = (start[1] - 0.5) * height
            local_finish_x = offset_x + finish[0] * digit_width
            local_finish_y = (finish[1] - 0.5) * height
            start_point = App.Vector(
                origin.x + local_start_x * tangent_x + local_start_y * normal_x,
                origin.y + local_start_x * tangent_y + local_start_y * normal_y,
                ENGRAVING_LIFT,
            )
            finish_point = App.Vector(
                origin.x + local_finish_x * tangent_x + local_finish_y * normal_x,
                origin.y + local_finish_x * tangent_y + local_finish_y * normal_y,
                ENGRAVING_LIFT,
            )
            edges.append(Part.makeLine(start_point, finish_point))
    return Part.makeCompound(edges)


def find_section_number_origin(formation_face, protected_face, main_alignment, start, finish):
    data = alignment_station_data(main_alignment)
    station = 0.5 * (start + finish)
    point, heading = interpolate_alignment_station(data, station)
    for normal_offset in _normal_offset_candidates(formation_face, 12.0):
        origin = _offset_along_normal(point, heading, normal_offset)
        candidate = _oriented_rectangle(origin, heading, -7.0, 7.0, 10.0)
        if _candidate_inside_formation(candidate, formation_face) and _candidate_clear_of_protected(candidate, protected_face):
            return origin, heading
    return point, heading

def alignment_station_at_cross_section(
    alignment,
    boundary_point,
    boundary_heading,
    target_fraction,
):
    """Return where an alignment crosses a shared section line."""
    data = alignment_station_data(alignment)
    tangent_x = math.cos(boundary_heading)
    tangent_y = math.sin(boundary_heading)
    distances = [
        ((point.x - boundary_point.x) * tangent_x)
        + ((point.y - boundary_point.y) * tangent_y)
        for point in data["points"]
    ]
    candidates = []
    tolerance = 1.0e-7
    for index in range(len(data["points"]) - 1):
        value_a = distances[index]
        value_b = distances[index + 1]
        station_a = data["stations"][index]
        station_b = data["stations"][index + 1]
        if abs(value_a) <= tolerance:
            candidates.append(station_a)
        denominator = value_b - value_a
        if abs(denominator) > tolerance:
            fraction = -value_a / denominator
            if -tolerance <= fraction <= 1.0 + tolerance:
                fraction = min(max(fraction, 0.0), 1.0)
                candidates.append(station_a + fraction * (station_b - station_a))
    if abs(distances[-1]) <= tolerance:
        candidates.append(data["stations"][-1])

    unique = []
    for value in sorted(candidates):
        if not unique or abs(value - unique[-1]) > 1.0e-5:
            unique.append(value)
    if not unique:
        nearest_index = min(range(len(distances)), key=lambda index: abs(distances[index]))
        if abs(distances[nearest_index]) <= 0.01:
            unique.append(data["stations"][nearest_index])
        else:
            raise ValueError(
                "A track centreline does not cross a shared section boundary. "
                "No existing generated objects have been removed."
            )
    target_station = min(max(float(target_fraction), 0.0), 1.0) * data["total"]
    return min(unique, key=lambda value: abs(value - target_station))


def calculate_template_section_stations(template_sources, main_alignment, section_plan):
    main_data = alignment_station_data(main_alignment)
    result = []
    for source in template_sources:
        boundaries = []
        for main_station in section_plan["boundaries"]:
            point, heading = interpolate_alignment_station(main_data, main_station)
            fraction = 0.0 if main_data["total"] <= GEOMETRY_TOLERANCE else main_station / main_data["total"]
            boundaries.append(
                alignment_station_at_cross_section(
                    source["alignment"],
                    point,
                    heading,
                    fraction,
                )
            )
        boundaries[0] = 0.0
        boundaries[-1] = alignment_station_data(source["alignment"])["total"]
        for start, finish in zip(boundaries[:-1], boundaries[1:]):
            if finish <= start + GEOMETRY_TOLERANCE:
                raise ValueError(
                    "Shared section boundaries are not in travel order on '{}'.".format(
                        source["alignment"]["name"]
                    )
                )
        result.append(boundaries)
    return result


def _extrude_template_feature(
    face,
    template_thickness=TEMPLATE_THICKNESS,
    lower=-0.20,
):
    thickness = max(float(template_thickness), GEOMETRY_TOLERANCE)
    upper = thickness + 0.20
    copy = face.copy()
    copy.translate(App.Vector(0.0, 0.0, lower))
    solid = copy.extrude(App.Vector(0.0, 0.0, upper - lower))
    if solid.isNull():
        raise ValueError("FreeCAD could not create a track-template feature cutter.")
    return solid


def _rounded_template_tab_face(point, heading, depth, width):
    radius = 0.5 * width
    if depth <= radius + 0.25:
        raise ValueError(
            "Pin depth must exceed half the pin diameter by at least 0.25 mm."
        )
    tangent_x = math.cos(heading)
    tangent_y = math.sin(heading)
    circle_offset = depth - radius
    centre = vector_xy(
        point.x + circle_offset * tangent_x,
        point.y + circle_offset * tangent_y,
    )
    rectangle = _oriented_rectangle(point, heading, -0.25, circle_offset, width)
    circle = _circle_face(centre, radius)
    return _fuse_shapes([rectangle, circle], "a rounded track-template pin")


def _template_joint_faces(point, heading, track_width, config):
    joint_type = config["joint_type"]
    depth = float(config["joint_depth"])
    width = float(config["joint_width"])
    clearance = float(config["fit_clearance"])
    edge_margin = 1.0
    usable_width = track_width - 2.0 * edge_margin
    if width + 2.0 * clearance > usable_width + GEOMETRY_TOLERANCE:
        raise ValueError(
            "Template joint width {:.3f} mm plus clearance does not fit within a "
            "{:.3f} mm track strip while retaining 1 mm side margins.".format(
                width, track_width
            )
        )

    if joint_type == TEMPLATE_JOINT_TONGUE:
        male_faces = [_oriented_rectangle(point, heading, -0.25, depth, width)]
        socket_faces = [
            _oriented_rectangle(
                point,
                heading,
                -0.50,
                depth + clearance,
                width + 2.0 * clearance,
            )
        ]
        return male_faces, socket_faces

    if joint_type == TEMPLATE_JOINT_PINS:
        pin_width = width
        socket_width = width + 2.0 * clearance
        maximum_offset = 0.5 * track_width - edge_margin - 0.5 * socket_width
        minimum_offset = 0.75 * socket_width
        if maximum_offset + GEOMETRY_TOLERANCE < minimum_offset:
            raise ValueError(
                "Two {:.3f} mm template pins do not fit safely across a {:.3f} mm "
                "track strip. Reduce the pin diameter or use a tongue-and-socket joint.".format(
                    width, track_width
                )
            )
        offset = min(0.25 * track_width, maximum_offset)
        offset = max(offset, minimum_offset)
        male_faces = []
        socket_faces = []
        for normal_offset in (-offset, offset):
            centre = _offset_along_normal(point, heading, normal_offset)
            male_faces.append(
                _rounded_template_tab_face(centre, heading, depth, pin_width)
            )
            socket_faces.append(
                _rounded_template_tab_face(
                    centre,
                    heading,
                    depth + clearance,
                    socket_width,
                )
            )
        return male_faces, socket_faces

    return [], []


def apply_track_template_joints(
    section_shapes_by_track,
    template_sources,
    main_alignment,
    section_plan,
    template_section_stations,
    config,
):
    results = [list(items) for items in section_shapes_by_track]
    profile_shapes = []
    if config["joint_type"] == TEMPLATE_JOINT_PLAIN or len(section_plan["ranges"]) <= 1:
        return results, profile_shapes

    main_data = alignment_station_data(main_alignment)
    internal_boundaries = section_plan["boundaries"][1:-1]
    for boundary_index, main_station in enumerate(internal_boundaries):
        _main_point, main_heading = interpolate_alignment_station(main_data, main_station)
        boundary_profiles = []
        for track_index, source in enumerate(template_sources):
            track_data = alignment_station_data(source["alignment"])
            track_station = template_section_stations[track_index][boundary_index + 1]
            point, _track_heading = interpolate_alignment_station(track_data, track_station)
            male_faces, socket_faces = _template_joint_faces(
                point,
                main_heading,
                float(source["alignment"]["width"]),
                config,
            )
            for candidate in male_faces + socket_faces:
                if not _candidate_inside_formation(candidate, source["plan_face"]):
                    raise ValueError(
                        "The requested {} does not remain within the '{}' template strip "
                        "at joint {:02d}. Reduce its depth or width.".format(
                            config["joint_type"].lower(),
                            source["alignment"]["name"],
                            boundary_index + 1,
                        )
                    )
            male_face = _fuse_shapes(male_faces, "track-template joint tongues or pins")
            socket_face = _fuse_shapes(socket_faces, "track-template joint sockets")
            thickness = float(
                source["alignment"].get("template_thickness", TEMPLATE_THICKNESS)
            )
            male_solid = _extrude_template_feature(male_face, thickness)
            socket_solid = _extrude_template_feature(socket_face, thickness)
            before = results[track_index][boundary_index]
            after = results[track_index][boundary_index + 1]
            if before is None or after is None:
                raise ValueError(
                    "A track-template joint cannot be applied because a section piece is missing."
                )
            before = _refine_shape(before.fuse(male_solid))
            after = _refine_shape(after.cut(socket_solid))
            if before.isNull() or after.isNull():
                raise ValueError("FreeCAD could not create a matching track-template joint.")
            results[track_index][boundary_index] = before
            results[track_index][boundary_index + 1] = after
            boundary_profiles.extend(
                [face.OuterWire for face in male_faces + socket_faces]
            )
        profile_shapes.append(Part.makeCompound(boundary_profiles))
    return results, profile_shapes


def create_track_template_fixing_holes(
    section_shapes_by_track,
    template_sources,
    template_section_stations,
    config,
):
    results = [list(items) for items in section_shapes_by_track]
    section_profiles = [[] for _item in range(len(results[0]) if results else 0)]
    hole_faces = []
    hole_count = int(config["holes_per_section"])
    radius = 0.5 * float(config["hole_diameter"])
    joint_guard = 0.0
    if config["joint_type"] != TEMPLATE_JOINT_PLAIN:
        joint_guard = (
            float(config["joint_depth"])
            + float(config["fit_clearance"])
            + radius
            + 1.0
        )
    end_clearance = max(float(config["minimum_end_clearance"]), joint_guard)

    for track_index, source in enumerate(template_sources):
        track_width = float(source["alignment"]["width"])
        thickness = float(
            source["alignment"].get("template_thickness", TEMPLATE_THICKNESS)
        )
        if config["hole_diameter"] + 2.0 > track_width + GEOMETRY_TOLERANCE:
            raise ValueError(
                "A {:.3f} mm fixing hole does not fit safely within the {:.3f} mm '{}' strip.".format(
                    config["hole_diameter"],
                    track_width,
                    source["alignment"]["name"],
                )
            )
        data = alignment_station_data(source["alignment"])
        boundaries = template_section_stations[track_index]
        for section_index, (start, finish) in enumerate(zip(boundaries[:-1], boundaries[1:])):
            usable_start = start + end_clearance
            usable_finish = finish - end_clearance
            usable_length = usable_finish - usable_start
            if usable_length <= GEOMETRY_TOLERANCE:
                raise ValueError(
                    "Section {:02d} of '{}' is too short for {} fixing hole{} with "
                    "the required {:.3f} mm end clearance.".format(
                        section_index + 1,
                        source["alignment"]["name"],
                        hole_count,
                        "" if hole_count == 1 else "s",
                        end_clearance,
                    )
                )
            for hole_index in range(hole_count):
                fraction = (hole_index + 0.5) / float(hole_count)
                station = usable_start + fraction * usable_length
                point, _heading = interpolate_alignment_station(data, station)
                hole_face = _circle_face(point, radius)
                if not _candidate_inside_formation(hole_face, source["plan_face"]):
                    raise ValueError(
                        "A fixing hole leaves the '{}' template strip in Section {:02d}.".format(
                            source["alignment"]["name"], section_index + 1
                        )
                    )
                cutter = _extrude_template_feature(hole_face, thickness)
                shape = results[track_index][section_index]
                if shape is None:
                    raise ValueError("A fixing hole cannot be applied to a missing template section.")
                shape = _refine_shape(shape.cut(cutter))
                if shape.isNull():
                    raise ValueError("FreeCAD could not cut a centreline fixing hole.")
                results[track_index][section_index] = shape
                hole_faces.append(hole_face)
                wire = hole_face.OuterWire.copy()
                wire.translate(App.Vector(0.0, 0.0, thickness + 0.06))
                section_profiles[section_index].append(wire)

    profile_shapes = [
        Part.makeCompound(wires) if wires else None
        for wires in section_profiles
    ]
    return results, profile_shapes, hole_faces, end_clearance


def prepare_straight_route_production(
    route,
    formation_config,
    section_config,
    registration_config,
    template_assembly_config,
):
    alignments = list(route.get("alignments", []))
    if not alignments:
        raise ValueError(
            "Straight route '{}' has no usable alignments.".format(
                route.get("name", "Unnamed straight")
            )
        )
    reference_alignment = alignments[0]
    template_sources = []
    template_plan_faces = []
    track_protection_faces = []
    template_solids = []
    for alignment_index, alignment in enumerate(alignments):
        plan_face = create_template_plan_face(
            alignment["points"],
            alignment["headings"],
            alignment["width"],
        )
        track_protection_faces.append(plan_face)
        if not alignment.get("create_template", False):
            continue
        solid = create_template_shape(
            alignment["points"],
            alignment["headings"],
            alignment["width"],
            alignment.get("template_thickness", TEMPLATE_THICKNESS),
        )
        template_solids.append(solid)
        template_plan_faces.append(plan_face)
        template_sources.append({
            "alignment": alignment,
            "solid": solid,
            "plan_face": plan_face,
            "track_number": alignment_index + 1,
        })

    compound_template = None
    if template_solids:
        compound_template = (
            template_solids[0]
            if len(template_solids) == 1
            else Part.makeCompound(template_solids)
        )

    route_formation_config = clone_formation_config(formation_config)
    route_formation_config["include_platform"] = False
    margin = float(route_formation_config.get("outer_margin", 0.0))
    connection_mode = route.get(
        "connection_mode", STRAIGHT_CONNECTION_INDEPENDENT
    )
    if connection_mode == STRAIGHT_CONNECTION_CURVE_ENTRANCE:
        # The entrance straight travels towards the curve. Keep the free-start
        # margin, but end the board exactly at the shared curve tangent.
        route_formation_config["_start_tangent_shift"] = -margin
        route_formation_config["_finish_tangent_shift"] = 0.0
    elif connection_mode == STRAIGHT_CONNECTION_CURVE_EXIT:
        # The exit straight travels away from the curve. Start exactly at the
        # shared tangent and retain the configured margin at the exposed end.
        route_formation_config["_start_tangent_shift"] = 0.0
        route_formation_config["_finish_tangent_shift"] = margin
    formation_geometry = None
    if (
        route_formation_config["enabled"]
        and route_formation_config["include_track_templates"]
        and template_sources
    ):
        formation_geometry = create_formation_geometry_multi(
            route_formation_config,
            alignments,
            track_protection_faces,
            [],
            [],
        )

    section_plan = calculate_section_plan(
        reference_alignment["total_length"], section_config
    )
    section_track_templates = bool(
        section_plan["enabled"]
        and section_config["section_track_templates"]
        and template_sources
    )
    section_formation = bool(
        section_plan["enabled"]
        and section_config["section_formation"]
        and formation_geometry is not None
    )
    section_active = bool(section_track_templates or section_formation)
    template_assembly_active = bool(
        section_track_templates and template_assembly_config["enabled"]
    )

    section_masks = []
    template_sections_by_track = []
    template_sections = []
    template_section_stations = []
    template_joint_shapes = []
    template_hole_profile_shapes = []
    template_hole_faces = []
    formation_matching_hole_shape = None
    effective_template_hole_clearance = 0.0
    formation_section_faces = []
    formation_section_outlines = []
    formation_section_solids = []
    registration_shapes = []
    alignment_hole_shapes = []
    section_number_shapes = []

    if section_active:
        source_shapes = []
        if compound_template is not None:
            source_shapes.append(compound_template)
        if formation_geometry is not None:
            source_shapes.append(formation_geometry["body"])
        board_depth = (
            route_formation_config["board_thickness"]
            if formation_geometry is not None
            else 0.0
        )
        z_min = -max(board_depth, 1.0) - 10.0
        z_max = max(
            [
                float(item["alignment"].get("template_thickness", TEMPLATE_THICKNESS))
                for item in template_sources
            ]
            or [TEMPLATE_THICKNESS]
        ) + 10.0
        section_masks = create_section_masks(
            reference_alignment,
            section_plan,
            source_shapes,
            z_min,
            z_max,
        )

        if section_track_templates:
            for source in template_sources:
                pieces = section_solid_shape(source["solid"], section_masks)
                validate_section_partition(
                    source["solid"],
                    pieces,
                    "'{}' straight track-template".format(
                        source["alignment"]["name"]
                    ),
                    require_every_section=True,
                )
                template_sections_by_track.append(pieces)
            template_section_stations = calculate_template_section_stations(
                template_sources,
                reference_alignment,
                section_plan,
            )
            if template_assembly_active:
                (
                    template_sections_by_track,
                    template_joint_shapes,
                ) = apply_track_template_joints(
                    template_sections_by_track,
                    template_sources,
                    reference_alignment,
                    section_plan,
                    template_section_stations,
                    template_assembly_config,
                )
                if template_assembly_config["fixing_holes_enabled"]:
                    (
                        template_sections_by_track,
                        template_hole_profile_shapes,
                        template_hole_faces,
                        effective_template_hole_clearance,
                    ) = create_track_template_fixing_holes(
                        template_sections_by_track,
                        template_sources,
                        template_section_stations,
                        template_assembly_config,
                    )
                    if template_assembly_config["matching_formation_holes"]:
                        if formation_geometry is None:
                            raise ValueError(
                                "Straight route '{}' needs a straight formation-board extension "
                                "before matching fixing holes can be created. Enable formation-board "
                                "output and include track-template strips.".format(route["name"])
                            )
                        (
                            formation_geometry,
                            formation_matching_hole_shape,
                        ) = cut_formation_matching_holes(
                            formation_geometry,
                            template_hole_faces,
                            route_formation_config["board_thickness"],
                        )
            template_sections = combine_track_template_sections(
                template_sections_by_track
            )
            if any(shape is None for shape in template_sections):
                raise ValueError(
                    "A combined straight track-template section is missing on '{}'.".format(
                        route["name"]
                    )
                )

        if section_formation:
            formation_section_faces = section_plan_face(
                formation_geometry["face"], section_masks
            )
            validate_section_partition(
                formation_geometry["face"],
                formation_section_faces,
                "'{}' straight formation-board".format(route["name"]),
                require_every_section=True,
            )
            (
                formation_section_faces,
                registration_shapes,
                alignment_hole_shapes,
            ) = apply_registration_features(
                formation_section_faces,
                reference_alignment,
                section_plan,
                formation_geometry["face"],
                formation_geometry["protected_face"],
                registration_config,
            )
            for face_shape in formation_section_faces:
                if face_shape is None:
                    formation_section_outlines.append(None)
                    formation_section_solids.append(None)
                    continue
                formation_section_outlines.append(
                    _outline_shape_from_face(face_shape)
                )
                formation_section_solids.append(
                    extrude_plan_shape_down(
                        face_shape,
                        route_formation_config["board_thickness"],
                    )
                )

        if section_config["number_in_travel_order"]:
            data = alignment_station_data(reference_alignment)
            for index, (start_station, finish_station) in enumerate(
                section_plan["ranges"]
            ):
                if formation_geometry is not None:
                    placement_face = formation_geometry["face"]
                    if (
                        section_formation
                        and index < len(formation_section_faces)
                        and formation_section_faces[index] is not None
                    ):
                        placement_face = formation_section_faces[index]
                    origin, heading = find_section_number_origin(
                        placement_face,
                        formation_geometry["protected_face"],
                        reference_alignment,
                        start_station,
                        finish_station,
                    )
                else:
                    origin, heading = interpolate_alignment_station(
                        data, 0.5 * (start_station + finish_station)
                    )
                section_number_shapes.append(
                    create_section_number_shape(index + 1, origin, heading)
                )

    preserve_unsplit = bool(
        section_config["preserve_unsplit"] or not section_plan["enabled"]
    )
    create_unsplit_template = bool(
        compound_template is not None
        and (preserve_unsplit or not section_track_templates)
    )
    create_unsplit_formation = bool(
        formation_geometry is not None
        and (preserve_unsplit or not section_formation)
    )

    result = {
        "route": route,
        "route_id": route["route_id"],
        "route_name": route["name"],
        "reference_alignment": reference_alignment,
        "alignments": alignments,
        "template_sources": template_sources,
        "template_plan_faces": template_plan_faces,
        "track_protection_faces": track_protection_faces,
        "compound_template": compound_template,
        "formation_config": route_formation_config,
        "formation_geometry": formation_geometry,
        "section_plan": section_plan,
        "section_active": section_active,
        "section_track_templates": section_track_templates,
        "section_formation": section_formation,
        "template_assembly_active": template_assembly_active,
        "section_masks": section_masks,
        "template_sections_by_track": template_sections_by_track,
        "template_sections": template_sections,
        "template_section_stations": template_section_stations,
        "template_joint_shapes": template_joint_shapes,
        "template_hole_profile_shapes": template_hole_profile_shapes,
        "template_hole_faces": template_hole_faces,
        "formation_matching_hole_shape": formation_matching_hole_shape,
        "effective_template_hole_clearance": effective_template_hole_clearance,
        "formation_section_faces": formation_section_faces,
        "formation_section_outlines": formation_section_outlines,
        "formation_section_solids": formation_section_solids,
        "registration_shapes": registration_shapes,
        "alignment_hole_shapes": alignment_hole_shapes,
        "section_number_shapes": section_number_shapes,
        "create_unsplit_template": create_unsplit_template,
        "create_unsplit_formation": create_unsplit_formation,
    }
    route["section_count"] = (
        len(section_plan["ranges"]) if section_active else 1
    )
    route["formation_enabled"] = formation_geometry is not None
    route["template_assembly_active"] = template_assembly_active
    return result


def formation_config_for_curve_connections(formation_config, straight_routes):
    """Return curve-board end-cap settings for any connected straight routes."""
    result = clone_formation_config(formation_config)
    margin = float(result.get("outer_margin", 0.0))
    has_entrance = any(
        route.get("connection_mode") == STRAIGHT_CONNECTION_CURVE_ENTRANCE
        for route in straight_routes
    )
    has_exit = any(
        route.get("connection_mode") == STRAIGHT_CONNECTION_CURVE_EXIT
        for route in straight_routes
    )
    result["_start_tangent_shift"] = 0.0 if has_entrance else -margin
    result["_finish_tangent_shift"] = 0.0 if has_exit else margin
    return result


def prepare_straight_routes_production(
    straight_routes,
    formation_config,
    section_config,
    registration_config,
    template_assembly_config,
):
    return [
        prepare_straight_route_production(
            route,
            formation_config,
            section_config,
            registration_config,
            template_assembly_config,
        )
        for route in straight_routes
    ]


def combine_track_template_sections(section_shapes_by_track):
    if not section_shapes_by_track:
        return []
    section_count = len(section_shapes_by_track[0])
    combined = []
    for section_index in range(section_count):
        pieces = [
            track_sections[section_index]
            for track_sections in section_shapes_by_track
            if section_index < len(track_sections)
            and track_sections[section_index] is not None
        ]
        if not pieces:
            combined.append(None)
        elif len(pieces) == 1:
            combined.append(pieces[0])
        else:
            combined.append(Part.makeCompound(pieces))
    return combined


def cut_formation_matching_holes(formation_geometry, hole_faces, board_thickness):
    if formation_geometry is None:
        raise ValueError(
            "Matching formation-board holes require formation-board output to be enabled."
        )
    face = formation_geometry["face"].copy()
    body = formation_geometry["body"].copy()
    profile_wires = []
    for hole_face in hole_faces:
        if not _candidate_inside_formation(hole_face, formation_geometry["face"]):
            raise ValueError(
                "A matching fixing hole lies outside the formation board. Include the "
                "track-template strips in the swept envelope or increase its margin."
            )
        face = _refine_shape(face.cut(hole_face))
        cutter_face = hole_face.copy()
        cutter_face.translate(App.Vector(0.0, 0.0, -float(board_thickness) - 0.20))
        cutter = cutter_face.extrude(
            App.Vector(0.0, 0.0, float(board_thickness) + 0.40)
        )
        body = _refine_shape(body.cut(cutter))
        wire = hole_face.OuterWire.copy()
        wire.translate(App.Vector(0.0, 0.0, FORMATION_OUTLINE_LIFT + 0.02))
        profile_wires.append(wire)
    if face.isNull() or body.isNull():
        raise ValueError("FreeCAD could not cut matching holes through the formation board.")
    updated = dict(formation_geometry)
    updated["face"] = face
    updated["body"] = body
    updated["area"] = float(getattr(face, "Area", 0.0))
    profiles = Part.makeCompound(profile_wires) if profile_wires else None
    return updated, profiles


def tag_export_metadata(
    obj,
    subtype,
    category,
    track_number=0,
    platform_number=0,
    platform_name="",
    section_number=0,
    travel_order_number=0,
    section_length=0.0,
    feature_number=0,
):
    properties = [
        ensure_property(obj, "App::PropertyString", "ExportSubtype", "Production export", "Specific production-export role"),
        ensure_property(obj, "App::PropertyString", "ExportCategory", "Production export", "Cutting, hole, joint, engraving or solid category"),
        ensure_property(obj, "App::PropertyInteger", "TrackNumber", "Production export", "One-based generated track number; zero means not applicable"),
        ensure_property(obj, "App::PropertyInteger", "PlatformNumber", "Production export", "One-based platform-manager number; zero means not applicable"),
        ensure_property(obj, "App::PropertyString", "PlatformName", "Production export", "Platform name used in generated objects and filenames"),
        ensure_property(obj, "App::PropertyInteger", "SectionNumber", "Production export", "One-based travel-order section number; zero means not applicable"),
        ensure_property(obj, "App::PropertyInteger", "TravelOrderNumber", "Production export", "One-based travel-order number; zero means not applicable"),
        ensure_property(obj, "App::PropertyLength", "SectionLength", "Production export", "Section length where available"),
        ensure_property(obj, "App::PropertyInteger", "FeatureNumber", "Production export", "One-based feature number within an output role; zero means not applicable"),
    ]
    obj.ExportSubtype = str(subtype)
    obj.ExportCategory = str(category)
    obj.TrackNumber = int(track_number or 0)
    obj.PlatformNumber = int(platform_number or 0)
    obj.PlatformName = str(platform_name or "")
    obj.SectionNumber = int(section_number or 0)
    obj.TravelOrderNumber = int(travel_order_number or 0)
    obj.SectionLength = max(0.0, float(section_length or 0.0))
    obj.FeatureNumber = int(feature_number or 0)
    set_read_only(obj, properties)


def safe_filename_component(value, fallback="Item"):
    cleaned = re.sub(r"[^A-Za-z0-9._-]+", "_", str(value).strip())
    cleaned = re.sub(r"_+", "_", cleaned).strip("._-")
    return cleaned or fallback


def export_set_filename_token(set_id):
    match = re.search(r"([0-9]+)$", str(set_id))
    if match:
        return "Set_{:03d}".format(int(match.group(1)))
    return "Set_{}".format(safe_filename_component(set_id, "001"))


def _other_engraving_filename_descriptor(record):
    """Return a stable filename token for the two established composite engraving records."""
    source_name = str(record.get("source_name") or "").strip().lower()
    source_label = str(record.get("source_label") or "").strip().lower()
    identity_text = "{} {}".format(source_name, source_label)
    compact_identity = re.sub(r"[^a-z0-9]+", "", identity_text)

    if (
        TRACK_ENGRAVING_NAME.lower() in compact_identity
        or "trackcentrelineengraving" in compact_identity
    ):
        # Preserve the established first-item filename for track-centreline engraving.
        return "Engraving_Geometry"
    if (
        PLATFORM_ENGRAVING_NAME.lower() in compact_identity
        or "platformedgeengraving" in compact_identity
    ):
        # The platform engraving previously collided with the track engraving and
        # was only distinguished later by an allocator-generated Item_02 suffix.
        return "Platform_Edge_Engraving"
    return EXPORT_SUBTYPE_FILENAMES.get("OtherEngraving", "Engraving_Geometry")


def record_filename_stem(record, config, set_id):
    route_name = str(record.get("route_name") or "").strip()
    if route_name:
        parts = [
            "Straight",
            safe_filename_component(route_name, "Route"),
            export_set_filename_token(set_id),
        ]
    else:
        parts = ["Curve", export_set_filename_token(set_id)]
    track_number = int(record.get("track_number") or 0)
    platform_number = int(record.get("platform_number") or 0)
    platform_name = str(record.get("platform_name") or "").strip()
    section_number = int(record.get("section_number") or 0)
    feature_number = int(record.get("feature_number") or 0)
    subtype = str(record.get("subtype", "Output"))

    if config.get("include_track_number", True) and track_number > 0:
        parts.extend(["Track", "{:02d}".format(track_number)])

    if platform_number > 0:
        parts.extend(["Platform", "{:02d}".format(platform_number)])
        if platform_name:
            parts.append(safe_filename_component(platform_name, "Platform"))

    if config.get("include_object_role", True):
        if platform_number > 0:
            descriptor = {
                "PlatformBody": "Body",
                "PlatformSection": "Body",
                "PlatformSectionOutline": "Plan_Outline",
                "PlatformPlanOutline": "Plan_Outline",
                "PlatformEdge": "Edge",
            }.get(
                subtype,
                EXPORT_SUBTYPE_FILENAMES.get(
                    subtype,
                    safe_filename_component(record.get("role", subtype), "Output"),
                ),
            )
        else:
            if subtype == "OtherEngraving":
                descriptor = _other_engraving_filename_descriptor(record)
            else:
                descriptor = EXPORT_SUBTYPE_FILENAMES.get(
                    subtype,
                    safe_filename_component(record.get("role", subtype), "Output"),
                )
    else:
        descriptor = safe_filename_component(
            record.get("source_label") or record.get("source_name") or subtype,
            "Output",
        )
        descriptor = re.sub(r"_?SET[-_ ]?[0-9]+_?", "_", descriptor, flags=re.I)
        descriptor = descriptor.strip("_") or "Output"
    parts.append(descriptor)

    if feature_number > 0:
        parts.append("{:02d}".format(feature_number))
    if config.get("include_section_number", True) and section_number > 0:
        parts.extend(["Section", "{:02d}".format(section_number)])
    return safe_filename_component(
        "_".join(parts),
        "Straight_Export" if route_name else "Curve_Export",
    )


def combined_filename_stem(category, set_id):
    descriptor = EXPORT_CATEGORY_COMBINED_NAMES.get(category, "Combined_Output")
    return safe_filename_component(
        "Curve_{}_{}".format(export_set_filename_token(set_id), descriptor),
        "Curve_Combined_Output",
    )


def resolve_revision_path(path, overwrite, reserved_paths=None):
    reserved = set(reserved_paths or [])
    absolute = os.path.abspath(path)
    if absolute in reserved:
        raise ValueError("Two export tasks resolved to the same filename: {}".format(absolute))
    if overwrite or not os.path.exists(absolute):
        return absolute
    stem, extension = os.path.splitext(absolute)
    revision = 2
    while True:
        candidate = "{}_Rev_{:02d}{}".format(stem, revision, extension)
        if candidate not in reserved and not os.path.exists(candidate):
            return candidate
        revision += 1



def allocate_export_path(desired_path, overwrite, reserved_paths, desired_counts):
    absolute_desired = os.path.abspath(desired_path)
    count = int(desired_counts.get(absolute_desired, 0)) + 1
    desired_counts[absolute_desired] = count
    candidate = absolute_desired
    if count > 1:
        stem, extension = os.path.splitext(absolute_desired)
        candidate = "{}_Item_{:02d}{}".format(stem, count, extension)
    return resolve_revision_path(candidate, overwrite, reserved_paths)


def _nearest_existing_directory(path):
    candidate = os.path.abspath(path)
    while not os.path.exists(candidate):
        parent = os.path.dirname(candidate)
        if parent == candidate:
            break
        candidate = parent
    return candidate if os.path.isdir(candidate) else ""


def validate_production_export_request(config, capabilities):
    if not config.get("enabled", False):
        return ""
    directory_text = str(config.get("output_directory", "")).strip()
    if not directory_text:
        raise ValueError("Choose an output directory for production export.")
    directory = os.path.abspath(os.path.expanduser(directory_text))
    if os.path.exists(directory) and not os.path.isdir(directory):
        raise ValueError(
            "The production export path exists but is not a directory: {}".format(
                directory
            )
        )
    existing_directory = (
        directory if os.path.isdir(directory)
        else _nearest_existing_directory(os.path.dirname(directory))
    )
    if not existing_directory:
        raise ValueError(
            "No existing parent directory is available for the production export path: {}".format(
                directory
            )
        )
    if not os.access(existing_directory, os.W_OK):
        raise ValueError(
            "The production export directory or its nearest existing parent is not writable: {}".format(
                existing_directory
            )
        )

    selected_formats = [
        key for key, selected in config.get("formats", {}).items() if selected
    ]
    if not selected_formats:
        raise ValueError("Select at least one available production export format.")
    unavailable = [
        EXPORT_FORMAT_LABELS.get(key, key.upper())
        for key in selected_formats
        if not capabilities.get(key, {}).get("available", False)
    ]
    if unavailable:
        raise ValueError(
            "The following selected exporters are unavailable in this FreeCAD installation: {}.".format(
                ", ".join(unavailable)
            )
        )
    if not any(config.get("selections", {}).values()):
        raise ValueError("Select at least one production output group.")
    config["output_directory"] = directory
    config["include_set_identifier"] = True
    config["current_template_set_only"] = True
    return directory


def ensure_production_export_directory(config):
    directory_text = str(config.get("output_directory") or "").strip()
    if not directory_text:
        raise ValueError("Choose an output directory for production export.")
    directory = os.path.abspath(os.path.expanduser(directory_text))
    if os.path.exists(directory) and not os.path.isdir(directory):
        raise ValueError(
            "The production export path exists but is not a directory: {}".format(
                directory
            )
        )
    if not os.path.isdir(directory):
        try:
            os.makedirs(directory)
        except Exception as error:
            raise ValueError(
                "The production export directory could not be created '{}': {}".format(
                    directory, error
                )
            )
    if not os.access(directory, os.W_OK):
        raise ValueError(
            "The production export directory is not writable: {}".format(directory)
        )
    config["output_directory"] = directory
    return directory


def _shape_is_null(shape):
    if shape is None:
        return True
    try:
        return bool(shape.isNull())
    except Exception:
        return False


def _shape_vertices(shape):
    try:
        return list(shape.Vertexes)
    except Exception:
        return []


def shape_is_planar_xy(shape, tolerance=0.001):
    vertices = _shape_vertices(shape)
    if not vertices:
        return False
    z_values = [float(vertex.Point.z) for vertex in vertices]
    return max(z_values) - min(z_values) <= float(tolerance)


def flatten_shape_to_xy(shape):
    if not shape_is_planar_xy(shape):
        raise ValueError("The selected 2D export geometry is not planar in XY.")
    copy = shape.copy()
    vertices = _shape_vertices(copy)
    z_value = float(vertices[0].Point.z) if vertices else 0.0
    if abs(z_value) > GEOMETRY_TOLERANCE:
        copy.translate(App.Vector(0.0, 0.0, -z_value))
    return copy


def shape_has_solid_geometry(shape):
    if _shape_is_null(shape):
        return False
    try:
        return len(shape.Solids) > 0
    except Exception:
        return False


def shape_has_edges(shape):
    if _shape_is_null(shape):
        return False
    try:
        return len(shape.Edges) > 0
    except Exception:
        return False


def shape_has_closed_profiles(shape):
    try:
        wires = list(shape.Wires)
    except Exception:
        wires = []
    if wires:
        for wire in wires:
            try:
                if not wire.isClosed():
                    return False
            except Exception:
                return False
        return True
    try:
        edges = list(shape.Edges)
    except Exception:
        edges = []
    if not edges:
        return False
    for edge in edges:
        try:
            if not edge.isClosed():
                return False
        except Exception:
            return False
    return True


def _horizontal_face_z(face, tolerance=0.001):
    vertices = _shape_vertices(face)
    if not vertices:
        return None
    z_values = [float(vertex.Point.z) for vertex in vertices]
    if max(z_values) - min(z_values) > tolerance:
        return None
    return sum(z_values) / float(len(z_values))


def plan_profile_from_shape(shape):
    if _shape_is_null(shape):
        return None
    if not shape_has_solid_geometry(shape):
        if shape_is_planar_xy(shape):
            try:
                wires = [wire.copy() for wire in shape.Wires]
            except Exception:
                wires = []
            if wires:
                return wires[0] if len(wires) == 1 else Part.makeCompound(wires)
            return shape.copy()
        return None

    horizontal = []
    try:
        faces = list(shape.Faces)
    except Exception:
        faces = []
    for face in faces:
        z_value = _horizontal_face_z(face)
        if z_value is not None and float(getattr(face, "Area", 0.0)) > GEOMETRY_TOLERANCE:
            horizontal.append((z_value, face))
    if not horizontal:
        return None
    top_z = max(item[0] for item in horizontal)
    wires = []
    for z_value, face in horizontal:
        if abs(z_value - top_z) > 0.001:
            continue
        try:
            wires.extend([wire.copy() for wire in face.Wires])
        except Exception:
            pass
    if not wires:
        return None
    profile = wires[0] if len(wires) == 1 else Part.makeCompound(wires)
    return flatten_shape_to_xy(profile)


def _compound_non_null(shapes):
    valid = [shape for shape in shapes if not _shape_is_null(shape)]
    if not valid:
        return None
    if len(valid) == 1:
        return valid[0].copy()
    return Part.makeCompound([shape.copy() for shape in valid])


def make_export_record(
    shape,
    source_name,
    source_label,
    role,
    subtype,
    category,
    selection_key,
    track_number=0,
    section_number=0,
    travel_order_number=0,
    feature_number=0,
    section_length=0.0,
    platform_number=0,
    platform_name="",
    platform_height=0.0,
    route_id="",
    route_name="",
    template_thickness=TEMPLATE_THICKNESS,
    track_name="",
):
    return {
        "shape": shape,
        "source_name": str(source_name),
        "source_label": str(source_label),
        "role": str(role),
        "subtype": str(subtype),
        "category": str(category),
        "selection_key": str(selection_key),
        "track_number": int(track_number or 0),
        "track_name": str(track_name or ""),
        "platform_number": int(platform_number or 0),
        "platform_name": str(platform_name or ""),
        "platform_height": max(0.0, float(platform_height or 0.0)),
        "section_number": int(section_number or 0),
        "travel_order_number": int(travel_order_number or 0),
        "feature_number": int(feature_number or 0),
        "section_length": max(0.0, float(section_length or 0.0)),
        "route_id": str(route_id or ""),
        "route_name": str(route_name or ""),
        "template_thickness": max(
            GEOMETRY_TOLERANCE, float(template_thickness or TEMPLATE_THICKNESS)
        ),
    }


def _record_selected(config, key):
    return bool(config.get("selections", {}).get(key, False))


def build_production_export_records(
    config,
    all_alignments,
    template_sources,
    compound_template,
    template_plan_faces,
    template_sections_by_track,
    template_section_stations,
    template_hole_faces,
    template_joint_shapes,
    platform_config,
    platform_geometry,
    platform_shapes,
    platform_plan_face,
    platform_sections,
    platform_section_plan_faces,
    formation_config,
    formation_geometry,
    formation_section_outlines,
    formation_section_solids,
    registration_shapes,
    alignment_hole_shapes,
    formation_matching_hole_shape,
    section_number_shapes,
    section_plan,
    track_engraving_shape,
    platform_engraving_shape,
    create_unsplit_template,
    create_unsplit_platform,
    create_unsplit_formation,
    template_assembly_config,
):
    records = []
    ranges = section_plan.get("ranges", []) if section_plan else []

    def main_section_length(section_index):
        if 0 <= section_index < len(ranges):
            start, finish = ranges[section_index]
            return max(0.0, float(finish) - float(start))
        return 0.0

    if create_unsplit_template and _record_selected(config, "track_template_compound_2d"):
        profiles = [_outline_shape_from_face(face) for face in template_plan_faces]
        records.append(make_export_record(
            _compound_non_null(profiles), TEMPLATE_NAME, "Multi-Track Curve Template",
            "Template", "TrackTemplateCompound", EXPORT_CATEGORY_CUTTING,
            "track_template_compound_2d",
        ))
    if create_unsplit_template and _record_selected(config, "track_template_compound_3d"):
        records.append(make_export_record(
            compound_template, TEMPLATE_NAME, "Multi-Track Curve Template",
            "Template", "TrackTemplateCompound", EXPORT_CATEGORY_SOLID,
            "track_template_compound_3d",
        ))

    for source_index, source in enumerate(template_sources):
        track_number = int(source.get("track_number", source_index + 1))
        track_name = str(source["alignment"]["name"])
        pieces = (
            template_sections_by_track[source_index]
            if source_index < len(template_sections_by_track)
            else []
        )
        boundaries = (
            template_section_stations[source_index]
            if source_index < len(template_section_stations)
            else []
        )
        for section_index, piece in enumerate(pieces):
            if piece is None:
                continue
            section_number = section_index + 1
            section_length = (
                boundaries[section_index + 1] - boundaries[section_index]
                if section_index + 1 < len(boundaries)
                else main_section_length(section_index)
            )
            source_name = "{}{:02d}_Track_{:02d}".format(
                TEMPLATE_SECTION_PREFIX, section_number, track_number
            )
            source_label = "Section {:02d} - {} Template".format(
                section_number, track_name
            )
            if _record_selected(config, "track_template_sections_2d"):
                records.append(make_export_record(
                    plan_profile_from_shape(piece), source_name, source_label,
                    "TrackTemplateSection", "TrackTemplateSection",
                    EXPORT_CATEGORY_CUTTING, "track_template_sections_2d",
                    track_number, section_number, section_number, 0, section_length,
                ))
            if _record_selected(config, "track_template_sections_3d"):
                records.append(make_export_record(
                    piece, source_name, source_label,
                    "TrackTemplateSection", "TrackTemplateSection",
                    EXPORT_CATEGORY_SOLID, "track_template_sections_3d",
                    track_number, section_number, section_number, 0, section_length,
                ))

    if _record_selected(config, "track_template_fixing_holes") and template_hole_faces:
        hole_count = int(template_assembly_config.get("holes_per_section", 0))
        section_count = len(ranges)
        offset = 0
        for source_index, source in enumerate(template_sources):
            track_number = int(source.get("track_number", source_index + 1))
            for section_index in range(section_count):
                faces = template_hole_faces[offset:offset + hole_count]
                offset += hole_count
                wires = []
                for face in faces:
                    try:
                        wires.append(face.OuterWire.copy())
                    except Exception:
                        pass
                if not wires:
                    continue
                shape = wires[0] if len(wires) == 1 else Part.makeCompound(wires)
                section_number = section_index + 1
                records.append(make_export_record(
                    shape,
                    "{}{:02d}_Track_{:02d}".format(
                        TRACK_TEMPLATE_HOLE_PREFIX, section_number, track_number
                    ),
                    "Section {:02d} - Track {:02d} Fixing Holes".format(
                        section_number, track_number
                    ),
                    "TrackTemplateFixingHole", "TrackTemplateFixingHole",
                    EXPORT_CATEGORY_HOLES, "track_template_fixing_holes",
                    track_number, section_number, section_number, 0,
                    main_section_length(section_index),
                ))

    if _record_selected(config, "track_template_joints"):
        for index, shape in enumerate(template_joint_shapes):
            records.append(make_export_record(
                shape, "{}{:02d}".format(TRACK_TEMPLATE_JOINT_PREFIX, index + 1),
                "Track Template Joint {:02d}".format(index + 1),
                "TrackTemplateJoint", "TrackTemplateJoint",
                EXPORT_CATEGORY_JOINTS, "track_template_joints",
                0, 0, index + 1, index + 1, 0.0,
            ))

    if _record_selected(config, "track_centrelines"):
        for index, alignment in enumerate(all_alignments):
            if not alignment.get("show_centreline", False):
                continue
            track_number = index + 1
            records.append(make_export_record(
                create_centreline_wire(alignment["points"]),
                "{}{:02d}".format(CENTRELINE_PREFIX, index),
                "{} Centreline".format(alignment["name"]),
                "Centreline", "TrackCentreline", EXPORT_CATEGORY_ENGRAVING,
                "track_centrelines", track_number,
            ))

    if platform_geometry is not None:
        if _record_selected(config, "platform_plan_outline") and platform_plan_face is not None:
            records.append(make_export_record(
                _outline_shape_from_face(platform_plan_face),
                PLATFORM_PLAN_OUTLINE_EXPORT_NAME,
                "{} Plan Outline".format(platform_config["name"]),
                "PlatformOutline", "PlatformPlanOutline", EXPORT_CATEGORY_CUTTING,
                "platform_plan_outline",
            ))
        if _record_selected(config, "platform_edges") and platform_shapes is not None:
            platform_edge_points = (
                platform_geometry["edge_a"],
                platform_geometry["edge_b"],
            )
            for edge_index, _display_edge_shape in enumerate(
                platform_shapes.get("edge_shapes", [])
            ):
                edge_shape = create_plan_polyline(
                    platform_edge_points[edge_index],
                    "the platform-edge export polyline",
                )
                records.append(make_export_record(
                    edge_shape,
                    "{}{:02d}".format(PLATFORM_EDGE_PREFIX, edge_index),
                    "{} Platform Edge {}".format(platform_config["name"], edge_index + 1),
                    "PlatformEdge", "PlatformEdge", EXPORT_CATEGORY_ENGRAVING,
                    "platform_edges", 0, 0, 0, edge_index + 1,
                ))
        if (
            create_unsplit_platform
            and platform_shapes is not None
            and platform_shapes.get("body_is_solid", False)
            and _record_selected(config, "platform_body")
        ):
            records.append(make_export_record(
                platform_shapes.get("body_shape"), PLATFORM_BODY_NAME, platform_config["name"],
                "PlatformBody", "PlatformBody", EXPORT_CATEGORY_SOLID,
                "platform_body",
            ))
        if _record_selected(config, "platform_sections_2d"):
            for section_index, face in enumerate(platform_section_plan_faces):
                if face is None:
                    continue
                section_number = section_index + 1
                records.append(make_export_record(
                    _outline_shape_from_face(face),
                    "{}{:02d}_Profile".format(PLATFORM_SECTION_PREFIX, section_number),
                    "Section {:02d} - Platform Outline".format(section_number),
                    "PlatformSection", "PlatformSection", EXPORT_CATEGORY_CUTTING,
                    "platform_sections_2d", 0, section_number, section_number, 0,
                    main_section_length(section_index),
                ))
        if _record_selected(config, "platform_sections_3d"):
            for section_index, shape in enumerate(platform_sections):
                if shape is None or not shape_has_solid_geometry(shape):
                    continue
                section_number = section_index + 1
                records.append(make_export_record(
                    shape,
                    "{}{:02d}".format(PLATFORM_SECTION_PREFIX, section_number),
                    "Section {:02d} - Platform".format(section_number),
                    "PlatformSection", "PlatformSection", EXPORT_CATEGORY_SOLID,
                    "platform_sections_3d", 0, section_number, section_number, 0,
                    main_section_length(section_index),
                ))

    if formation_geometry is not None:
        formation_output = str(formation_config.get("output_type", FORMATION_BOTH))
        formation_has_outline = formation_output in (
            FORMATION_OUTLINE_ONLY,
            FORMATION_BOTH,
        )
        formation_has_solid = formation_output in (
            FORMATION_SOLID_ONLY,
            FORMATION_BOTH,
        )
        if (
            create_unsplit_formation
            and formation_has_outline
            and _record_selected(config, "formation_perimeter")
        ):
            records.append(make_export_record(
                formation_geometry.get("outline"), FORMATION_OUTLINE_NAME,
                "Formation Board Perimeter", "FormationOutline", "FormationPerimeter",
                EXPORT_CATEGORY_CUTTING, "formation_perimeter",
            ))
        if (
            create_unsplit_formation
            and formation_has_solid
            and _record_selected(config, "formation_body")
        ):
            records.append(make_export_record(
                formation_geometry.get("body"), FORMATION_BODY_NAME,
                "Formation Board", "FormationBody", "FormationBody",
                EXPORT_CATEGORY_SOLID, "formation_body",
            ))
        if formation_has_outline and _record_selected(config, "formation_sections_2d"):
            for section_index, shape in enumerate(formation_section_outlines):
                if shape is None:
                    continue
                section_number = section_index + 1
                records.append(make_export_record(
                    shape,
                    "{}{:02d}_Profile".format(FORMATION_SECTION_PREFIX, section_number),
                    "Section {:02d} - Formation Perimeter".format(section_number),
                    "FormationSection", "FormationSectionPerimeter",
                    EXPORT_CATEGORY_CUTTING, "formation_sections_2d",
                    0, section_number, section_number, 0,
                    main_section_length(section_index),
                ))
        if formation_has_solid and _record_selected(config, "formation_sections_3d"):
            for section_index, shape in enumerate(formation_section_solids):
                if shape is None:
                    continue
                section_number = section_index + 1
                records.append(make_export_record(
                    shape,
                    "{}{:02d}_Body".format(FORMATION_SECTION_PREFIX, section_number),
                    "Section {:02d} - Formation Board".format(section_number),
                    "FormationSection", "FormationSectionBody",
                    EXPORT_CATEGORY_SOLID, "formation_sections_3d",
                    0, section_number, section_number, 0,
                    main_section_length(section_index),
                ))

    if _record_selected(config, "registration_joints"):
        for index, shape in enumerate(registration_shapes):
            records.append(make_export_record(
                shape, "{}{:02d}".format(REGISTRATION_PREFIX, index + 1),
                "Formation Registration Joint {:02d}".format(index + 1),
                "RegistrationFeature", "RegistrationJoint",
                EXPORT_CATEGORY_JOINTS, "registration_joints",
                0, 0, index + 1, index + 1, 0.0,
            ))
    if _record_selected(config, "registration_holes"):
        for index, shape in enumerate(alignment_hole_shapes):
            records.append(make_export_record(
                shape, "{}{:02d}".format(ALIGNMENT_HOLE_PREFIX, index + 1),
                "Registration Holes {:02d}".format(index + 1),
                "AlignmentHole", "RegistrationHole", EXPORT_CATEGORY_HOLES,
                "registration_holes", 0, 0, index + 1, index + 1, 0.0,
            ))
    if (
        _record_selected(config, "formation_matching_holes")
        and formation_matching_hole_shape is not None
    ):
        records.append(make_export_record(
            formation_matching_hole_shape, FORMATION_MATCHING_HOLES_NAME,
            "Formation Board Matching Fixing Holes", "FormationMatchingHole",
            "FormationMatchingFixingHole", EXPORT_CATEGORY_HOLES,
            "formation_matching_holes",
        ))

    if _record_selected(config, "section_numbers"):
        for section_index, shape in enumerate(section_number_shapes):
            section_number = section_index + 1
            records.append(make_export_record(
                shape, "{}{:02d}".format(SECTION_ENGRAVING_PREFIX, section_number),
                "Section {:02d} Number Engraving".format(section_number),
                "EngravingGeometry", "SectionNumberEngraving",
                EXPORT_CATEGORY_ENGRAVING, "section_numbers",
                0, section_number, section_number, 0,
                main_section_length(section_index),
            ))

    if _record_selected(config, "other_engraving"):
        if track_engraving_shape is not None:
            records.append(make_export_record(
                track_engraving_shape, TRACK_ENGRAVING_NAME,
                "Track Centreline Engraving", "EngravingGeometry",
                "OtherEngraving", EXPORT_CATEGORY_ENGRAVING,
                "other_engraving",
            ))
        if platform_engraving_shape is not None:
            records.append(make_export_record(
                platform_engraving_shape, PLATFORM_ENGRAVING_NAME,
                "Platform Edge Engraving", "EngravingGeometry",
                "OtherEngraving", EXPORT_CATEGORY_ENGRAVING,
                "other_engraving",
            ))
    return records


def build_production_export_records_multi(
    config,
    all_alignments,
    template_sources,
    compound_template,
    template_plan_faces,
    template_sections_by_track,
    template_section_stations,
    template_hole_faces,
    template_joint_shapes,
    platform_results,
    formation_config,
    formation_geometry,
    formation_section_outlines,
    formation_section_solids,
    registration_shapes,
    alignment_hole_shapes,
    formation_matching_hole_shape,
    section_number_shapes,
    section_plan,
    track_engraving_shape,
    platform_engraving_shape,
    create_unsplit_template,
    create_unsplit_formation,
    template_assembly_config,
):
    records = build_production_export_records(
        config,
        all_alignments,
        template_sources,
        compound_template,
        template_plan_faces,
        template_sections_by_track,
        template_section_stations,
        template_hole_faces,
        template_joint_shapes,
        default_platform_config(),
        None,
        None,
        None,
        [],
        [],
        formation_config,
        formation_geometry,
        formation_section_outlines,
        formation_section_solids,
        registration_shapes,
        alignment_hole_shapes,
        formation_matching_hole_shape,
        section_number_shapes,
        section_plan,
        track_engraving_shape,
        platform_engraving_shape,
        create_unsplit_template,
        False,
        create_unsplit_formation,
        template_assembly_config,
    )
    ranges = section_plan.get("ranges", []) if section_plan else []

    def main_section_length(section_index):
        if 0 <= section_index < len(ranges):
            start, finish = ranges[section_index]
            return max(0.0, float(finish) - float(start))
        return 0.0

    for result in platform_results:
        platform_number = int(result["platform_number"])
        platform_config = result["config"]
        platform_name = str(platform_config["name"])
        platform_height = float(platform_config.get("platform_height", 0.0))
        platform_geometry = result.get("geometry")
        platform_shapes = result.get("shapes")
        platform_plan_face = result.get("plan_face")
        platform_sections = result.get("sections", [])
        platform_section_plan_faces = result.get("section_plan_faces", [])
        create_unsplit_platform = bool(result.get("create_unsplit", False))

        if platform_geometry is None:
            continue
        if (
            _record_selected(config, "platform_plan_outline")
            and platform_plan_face is not None
        ):
            records.append(make_export_record(
                _outline_shape_from_face(platform_plan_face),
                "{}{:02d}".format(
                    PLATFORM_PLAN_OUTLINE_EXPORT_NAME, platform_number
                ),
                "{} Plan Outline".format(platform_name),
                "PlatformOutline",
                "PlatformPlanOutline",
                EXPORT_CATEGORY_CUTTING,
                "platform_plan_outline",
                platform_number=platform_number,
                platform_name=platform_name,
                platform_height=platform_height,
            ))
        if (
            _record_selected(config, "platform_edges")
            and platform_shapes is not None
        ):
            platform_edge_points = (
                platform_geometry["edge_a"],
                platform_geometry["edge_b"],
            )
            for edge_index, _display_edge_shape in enumerate(
                platform_shapes.get("edge_shapes", [])
            ):
                edge_shape = create_plan_polyline(
                    platform_edge_points[edge_index],
                    "the platform-edge export polyline",
                )
                records.append(make_export_record(
                    edge_shape,
                    "{}{:02d}_{:02d}".format(
                        PLATFORM_EDGE_PREFIX,
                        platform_number,
                        edge_index + 1,
                    ),
                    "{} Platform Edge {}".format(
                        platform_name, edge_index + 1
                    ),
                    "PlatformEdge",
                    "PlatformEdge",
                    EXPORT_CATEGORY_ENGRAVING,
                    "platform_edges",
                    feature_number=edge_index + 1,
                    platform_number=platform_number,
                    platform_name=platform_name,
                    platform_height=platform_height,
                ))
        if (
            create_unsplit_platform
            and platform_shapes is not None
            and platform_shapes.get("body_is_solid", False)
            and _record_selected(config, "platform_body")
        ):
            records.append(make_export_record(
                platform_shapes.get("body_shape"),
                "{}{:02d}".format(PLATFORM_BODY_NAME, platform_number),
                platform_name,
                "PlatformBody",
                "PlatformBody",
                EXPORT_CATEGORY_SOLID,
                "platform_body",
                platform_number=platform_number,
                platform_name=platform_name,
                platform_height=platform_height,
            ))
        if _record_selected(config, "platform_sections_2d"):
            for section_index, face in enumerate(platform_section_plan_faces):
                if face is None:
                    continue
                section_number = section_index + 1
                records.append(make_export_record(
                    _outline_shape_from_face(face),
                    "{}P{:02d}_S{:02d}_Profile".format(
                        PLATFORM_SECTION_PREFIX,
                        platform_number,
                        section_number,
                    ),
                    "Section {:02d} - {} Outline".format(
                        section_number, platform_name
                    ),
                    "PlatformSection",
                    "PlatformSectionOutline",
                    EXPORT_CATEGORY_CUTTING,
                    "platform_sections_2d",
                    section_number=section_number,
                    travel_order_number=section_number,
                    section_length=main_section_length(section_index),
                    platform_number=platform_number,
                    platform_name=platform_name,
                    platform_height=platform_height,
                ))
        if _record_selected(config, "platform_sections_3d"):
            for section_index, shape in enumerate(platform_sections):
                if shape is None or not shape_has_solid_geometry(shape):
                    continue
                section_number = section_index + 1
                records.append(make_export_record(
                    shape,
                    "{}P{:02d}_S{:02d}".format(
                        PLATFORM_SECTION_PREFIX,
                        platform_number,
                        section_number,
                    ),
                    "Section {:02d} - {}".format(
                        section_number, platform_name
                    ),
                    "PlatformSection",
                    "PlatformSection",
                    EXPORT_CATEGORY_SOLID,
                    "platform_sections_3d",
                    section_number=section_number,
                    travel_order_number=section_number,
                    section_length=main_section_length(section_index),
                    platform_number=platform_number,
                    platform_name=platform_name,
                    platform_height=platform_height,
                ))
    return records



def build_straight_production_export_records(
    config,
    straight_bundles,
    template_assembly_config,
):
    records = []
    for route_index, bundle in enumerate(straight_bundles):
        route = bundle["route"]
        route_id = bundle["route_id"]
        route_name = bundle["route_name"]
        route_token = "R{:02d}".format(route_index + 1)
        ranges = bundle["section_plan"].get("ranges", [])

        def section_length(section_index):
            if 0 <= section_index < len(ranges):
                start, finish = ranges[section_index]
                return max(0.0, float(finish) - float(start))
            return 0.0

        sources = bundle["template_sources"]
        if (
            bundle["create_unsplit_template"]
            and sources
            and _record_selected(config, "track_template_compound_2d")
        ):
            profiles = [
                _outline_shape_from_face(source["plan_face"])
                for source in sources
            ]
            records.append(make_export_record(
                _compound_non_null(profiles),
                "{}{}_Profile".format(STRAIGHT_TEMPLATE_PREFIX, route_token),
                "{} Multi-Track Straight Template".format(route_name),
                "StraightTrackTemplate",
                "TrackTemplateCompound",
                EXPORT_CATEGORY_CUTTING,
                "track_template_compound_2d",
                route_id=route_id,
                route_name=route_name,
                template_thickness=max(
                    float(source["alignment"].get("template_thickness", TEMPLATE_THICKNESS))
                    for source in sources
                ),
            ))
        if (
            bundle["create_unsplit_template"]
            and bundle["compound_template"] is not None
            and _record_selected(config, "track_template_compound_3d")
        ):
            records.append(make_export_record(
                bundle["compound_template"],
                "{}{}".format(STRAIGHT_TEMPLATE_PREFIX, route_token),
                "{} Multi-Track Straight Template".format(route_name),
                "StraightTrackTemplate",
                "TrackTemplateCompound",
                EXPORT_CATEGORY_SOLID,
                "track_template_compound_3d",
                route_id=route_id,
                route_name=route_name,
                template_thickness=max(
                    float(source["alignment"].get("template_thickness", TEMPLATE_THICKNESS))
                    for source in sources
                ),
            ))

        for source_index, source in enumerate(sources):
            track_number = int(source.get("track_number", source_index + 1))
            thickness = float(
                source["alignment"].get("template_thickness", TEMPLATE_THICKNESS)
            )
            pieces = (
                bundle["template_sections_by_track"][source_index]
                if source_index < len(bundle["template_sections_by_track"])
                else []
            )
            boundaries = (
                bundle["template_section_stations"][source_index]
                if source_index < len(bundle["template_section_stations"])
                else []
            )
            for section_index, piece in enumerate(pieces):
                if piece is None:
                    continue
                local_section = section_index + 1
                measured_length = (
                    boundaries[section_index + 1] - boundaries[section_index]
                    if section_index + 1 < len(boundaries)
                    else section_length(section_index)
                )
                source_name = "{}{}_S{:02d}_T{:02d}".format(
                    STRAIGHT_TEMPLATE_SECTION_PREFIX,
                    route_token,
                    local_section,
                    track_number,
                )
                source_label = "{} - Section {:02d} - Track {:02d}".format(
                    route_name, local_section, track_number
                )
                if _record_selected(config, "track_template_sections_2d"):
                    records.append(make_export_record(
                        plan_profile_from_shape(piece), source_name, source_label,
                        "StraightTrackTemplateSection", "TrackTemplateSection",
                        EXPORT_CATEGORY_CUTTING, "track_template_sections_2d",
                        track_number, local_section, local_section, 0,
                        measured_length, route_id=route_id, route_name=route_name,
                        template_thickness=thickness,
                    ))
                if _record_selected(config, "track_template_sections_3d"):
                    records.append(make_export_record(
                        piece, source_name, source_label,
                        "StraightTrackTemplateSection", "TrackTemplateSection",
                        EXPORT_CATEGORY_SOLID, "track_template_sections_3d",
                        track_number, local_section, local_section, 0,
                        measured_length, route_id=route_id, route_name=route_name,
                        template_thickness=thickness,
                    ))

        if (
            _record_selected(config, "track_template_fixing_holes")
            and bundle["template_hole_faces"]
        ):
            hole_count = int(template_assembly_config.get("holes_per_section", 0))
            section_count = len(ranges)
            offset = 0
            for source_index, source in enumerate(sources):
                track_number = int(source.get("track_number", source_index + 1))
                thickness = float(
                    source["alignment"].get("template_thickness", TEMPLATE_THICKNESS)
                )
                for section_index in range(section_count):
                    faces = bundle["template_hole_faces"][offset:offset + hole_count]
                    offset += hole_count
                    wires = []
                    for face in faces:
                        try:
                            wires.append(face.OuterWire.copy())
                        except Exception:
                            pass
                    if not wires:
                        continue
                    shape = wires[0] if len(wires) == 1 else Part.makeCompound(wires)
                    local_section = section_index + 1
                    records.append(make_export_record(
                        shape,
                        "{}{}_S{:02d}_T{:02d}".format(
                            STRAIGHT_TEMPLATE_HOLE_PREFIX,
                            route_token,
                            local_section,
                            track_number,
                        ),
                        "{} - Section {:02d} - Track {:02d} Fixing Holes".format(
                            route_name, local_section, track_number
                        ),
                        "StraightTrackTemplateFixingHole",
                        "TrackTemplateFixingHole",
                        EXPORT_CATEGORY_HOLES,
                        "track_template_fixing_holes",
                        track_number,
                        local_section,
                        local_section,
                        0,
                        section_length(section_index),
                        route_id=route_id,
                        route_name=route_name,
                        template_thickness=thickness,
                    ))

        if _record_selected(config, "track_template_joints"):
            for index, shape in enumerate(bundle["template_joint_shapes"]):
                records.append(make_export_record(
                    shape,
                    "{}{}_J{:02d}".format(
                        STRAIGHT_TEMPLATE_JOINT_PREFIX, route_token, index + 1
                    ),
                    "{} - Track Template Joint {:02d}".format(
                        route_name, index + 1
                    ),
                    "StraightTrackTemplateJoint",
                    "TrackTemplateJoint",
                    EXPORT_CATEGORY_JOINTS,
                    "track_template_joints",
                    travel_order_number=index + 1,
                    feature_number=index + 1,
                    route_id=route_id,
                    route_name=route_name,
                ))

        if _record_selected(config, "track_centrelines"):
            for alignment_index, alignment in enumerate(bundle["alignments"]):
                if not alignment.get("show_centreline", False):
                    continue
                thickness = float(
                    alignment.get("template_thickness", TEMPLATE_THICKNESS)
                )
                records.append(make_export_record(
                    create_centreline_wire(alignment["points"], thickness),
                    "{}{}_T{:02d}".format(
                        STRAIGHT_CENTRELINE_PREFIX,
                        route_token,
                        alignment_index + 1,
                    ),
                    "{} Centreline".format(alignment["name"]),
                    "StraightTrackCentreline",
                    "TrackCentreline",
                    EXPORT_CATEGORY_ENGRAVING,
                    "track_centrelines",
                    track_number=alignment_index + 1,
                    route_id=route_id,
                    route_name=route_name,
                    template_thickness=thickness,
                ))

        formation_geometry = bundle["formation_geometry"]
        formation_config = bundle["formation_config"]
        if formation_geometry is not None:
            formation_output = formation_config["output_type"]
            has_outline = formation_output in (FORMATION_OUTLINE_ONLY, FORMATION_BOTH)
            has_solid = formation_output in (FORMATION_SOLID_ONLY, FORMATION_BOTH)
            if (
                bundle["create_unsplit_formation"]
                and has_outline
                and _record_selected(config, "formation_perimeter")
            ):
                records.append(make_export_record(
                    formation_geometry["outline"],
                    "{}{}".format(STRAIGHT_FORMATION_OUTLINE_PREFIX, route_token),
                    "{} Formation Board Perimeter".format(route_name),
                    "StraightFormationOutline", "FormationPerimeter",
                    EXPORT_CATEGORY_CUTTING, "formation_perimeter",
                    route_id=route_id, route_name=route_name,
                ))
            if (
                bundle["create_unsplit_formation"]
                and has_solid
                and _record_selected(config, "formation_body")
            ):
                records.append(make_export_record(
                    formation_geometry["body"],
                    "{}{}".format(STRAIGHT_FORMATION_BODY_PREFIX, route_token),
                    "{} Formation Board".format(route_name),
                    "StraightFormationBody", "FormationBody",
                    EXPORT_CATEGORY_SOLID, "formation_body",
                    route_id=route_id, route_name=route_name,
                ))
            if has_outline and _record_selected(config, "formation_sections_2d"):
                for section_index, shape in enumerate(
                    bundle["formation_section_outlines"]
                ):
                    if shape is None:
                        continue
                    local_section = section_index + 1
                    records.append(make_export_record(
                        shape,
                        "{}{}_S{:02d}_Profile".format(
                            STRAIGHT_FORMATION_SECTION_PREFIX,
                            route_token,
                            local_section,
                        ),
                        "{} - Section {:02d} Formation Perimeter".format(
                            route_name, local_section
                        ),
                        "StraightFormationSection", "FormationSectionPerimeter",
                        EXPORT_CATEGORY_CUTTING, "formation_sections_2d",
                        section_number=local_section,
                        travel_order_number=local_section,
                        section_length=section_length(section_index),
                        route_id=route_id, route_name=route_name,
                    ))
            if has_solid and _record_selected(config, "formation_sections_3d"):
                for section_index, shape in enumerate(
                    bundle["formation_section_solids"]
                ):
                    if shape is None:
                        continue
                    local_section = section_index + 1
                    records.append(make_export_record(
                        shape,
                        "{}{}_S{:02d}_Body".format(
                            STRAIGHT_FORMATION_SECTION_PREFIX,
                            route_token,
                            local_section,
                        ),
                        "{} - Section {:02d} Formation Board".format(
                            route_name, local_section
                        ),
                        "StraightFormationSection", "FormationSectionBody",
                        EXPORT_CATEGORY_SOLID, "formation_sections_3d",
                        section_number=local_section,
                        travel_order_number=local_section,
                        section_length=section_length(section_index),
                        route_id=route_id, route_name=route_name,
                    ))

        if _record_selected(config, "registration_joints"):
            for index, shape in enumerate(bundle["registration_shapes"]):
                records.append(make_export_record(
                    shape,
                    "{}{}_J{:02d}".format(
                        STRAIGHT_REGISTRATION_PREFIX, route_token, index + 1
                    ),
                    "{} Formation Registration Joint {:02d}".format(
                        route_name, index + 1
                    ),
                    "StraightRegistrationFeature", "RegistrationJoint",
                    EXPORT_CATEGORY_JOINTS, "registration_joints",
                    travel_order_number=index + 1,
                    feature_number=index + 1,
                    route_id=route_id, route_name=route_name,
                ))
        if _record_selected(config, "registration_holes"):
            for index, shape in enumerate(bundle["alignment_hole_shapes"]):
                records.append(make_export_record(
                    shape,
                    "{}{}_J{:02d}".format(
                        STRAIGHT_ALIGNMENT_HOLE_PREFIX, route_token, index + 1
                    ),
                    "{} Registration Holes {:02d}".format(route_name, index + 1),
                    "StraightAlignmentHole", "RegistrationHole",
                    EXPORT_CATEGORY_HOLES, "registration_holes",
                    travel_order_number=index + 1,
                    feature_number=index + 1,
                    route_id=route_id, route_name=route_name,
                ))
        if (
            _record_selected(config, "formation_matching_holes")
            and bundle["formation_matching_hole_shape"] is not None
        ):
            records.append(make_export_record(
                bundle["formation_matching_hole_shape"],
                "{}{}".format(
                    STRAIGHT_FORMATION_MATCHING_HOLES_PREFIX, route_token
                ),
                "{} Formation Board Matching Fixing Holes".format(route_name),
                "StraightFormationMatchingHole",
                "FormationMatchingFixingHole",
                EXPORT_CATEGORY_HOLES,
                "formation_matching_holes",
                route_id=route_id,
                route_name=route_name,
            ))

        if _record_selected(config, "section_numbers"):
            for section_index, shape in enumerate(bundle["section_number_shapes"]):
                local_section = section_index + 1
                records.append(make_export_record(
                    shape,
                    "{}{}_S{:02d}".format(
                        STRAIGHT_SECTION_ENGRAVING_PREFIX,
                        route_token,
                        local_section,
                    ),
                    "{} - Section {:02d} Number Engraving".format(
                        route_name, local_section
                    ),
                    "StraightEngravingGeometry", "SectionNumberEngraving",
                    EXPORT_CATEGORY_ENGRAVING, "section_numbers",
                    section_number=local_section,
                    travel_order_number=local_section,
                    section_length=section_length(section_index),
                    route_id=route_id,
                    route_name=route_name,
                ))
    return records


def bind_export_records_to_current_set(doc, set_id, records):
    recognised = []
    for obj in list(doc.Objects):
        if object_string_property(obj, "GeneratedBy") != GENERATOR_ID:
            continue
        if object_string_property(obj, "TemplateSetID") != set_id:
            continue
        recognised.append(obj)
    if not recognised:
        raise ValueError(
            "No recognised generated objects were found for template set {}.".format(
                set_id
            )
        )

    def integer_property(obj, name):
        if name not in getattr(obj, "PropertiesList", []):
            return 0
        try:
            return int(getattr(obj, name))
        except Exception:
            return 0

    for record in records:
        current_source_name = str(record.get("source_name") or "")
        current_source = doc.getObject(current_source_name) if current_source_name else None
        record_id = str(record.get("record_id") or "")
        if (
            current_source is not None
            and record_id
            and object_string_property(
                current_source, PRODUCTION_RECORD_ID_PROPERTY, ""
            ) == record_id
        ):
            continue
        role = str(record.get("role", ""))
        subtype = str(record.get("subtype", ""))
        route_id = str(record.get("route_id", "") or "")
        track_number = int(record.get("track_number") or 0)
        platform_number = int(record.get("platform_number") or 0)
        section_number = int(record.get("section_number") or 0)
        feature_number = int(record.get("feature_number") or 0)
        candidates = [
            obj for obj in recognised
            if object_string_property(obj, "GeneratedRole") == role
            and (
                not route_id
                or object_string_property(obj, "RouteID", "") == route_id
            )
        ]
        exact = []
        for obj in candidates:
            object_subtype = object_string_property(obj, "ExportSubtype", "")
            compatible_subtypes = {subtype, "TrackTemplateSectionCombined"}
            if subtype == "PlatformSectionOutline":
                compatible_subtypes.add("PlatformSection")
            if object_subtype and object_subtype not in compatible_subtypes:
                continue
            object_track = _integer_object_property(obj, "TrackNumber", 0)
            object_platform = _integer_object_property(obj, "PlatformNumber", 0)
            object_section = _integer_object_property(obj, "SectionNumber", 0)
            object_feature = _integer_object_property(obj, "FeatureNumber", 0)
            if track_number and object_track and track_number != object_track:
                continue
            if platform_number and object_platform and platform_number != object_platform:
                continue
            if section_number and object_section and section_number != object_section:
                continue
            if feature_number and object_feature and feature_number != object_feature:
                continue
            exact.append(obj)
        if not exact:
            continue
        if len(exact) == 1:
            obj = exact[0]
            source_name = str(obj.Name)
            if track_number and _integer_object_property(obj, "TrackNumber", 0) == 0:
                source_name += "::Track_{:02d}".format(track_number)
            if platform_number and _integer_object_property(obj, "PlatformNumber", 0) == 0:
                source_name += "::Platform_{:02d}".format(platform_number)
            record["source_name"] = source_name
            record["source_label"] = str(getattr(obj, "Label", source_name))
            if record.get("category") in (
                EXPORT_CATEGORY_SOLID,
                EXPORT_CATEGORY_ENGRAVING,
                EXPORT_CATEGORY_HOLES,
                EXPORT_CATEGORY_JOINTS,
            ):
                object_shape = getattr(obj, "Shape", None)
                valid, _reason = validate_export_record({
                    "shape": object_shape,
                    "category": record.get("category"),
                })
                if valid and not bool(record.get("force_production_source", False)) and not (
                    (track_number > 0 and _integer_object_property(obj, "TrackNumber", 0) == 0)
                    or (platform_number > 0 and _integer_object_property(obj, "PlatformNumber", 0) == 0)
                ):
                    record["shape"] = object_shape.copy()
        else:
            record["source_name"] = "+".join(str(obj.Name) for obj in exact)
            record["source_label"] = "+".join(
                str(getattr(obj, "Label", obj.Name)) for obj in exact
            )
    return records




# Compact single-line manufacturing font. Each 5x7 bitmap row becomes one or
# more centreline engraving strokes, so no external font or Draft workbench is
# required and the same geometry can drive DXF, SVG, STL and STEP output.
_ASSEMBLY_LABEL_FONT = {
    "A": ("01110", "10001", "10001", "11111", "10001", "10001", "10001"),
    "B": ("11110", "10001", "10001", "11110", "10001", "10001", "11110"),
    "C": ("01111", "10000", "10000", "10000", "10000", "10000", "01111"),
    "D": ("11110", "10001", "10001", "10001", "10001", "10001", "11110"),
    "E": ("11111", "10000", "10000", "11110", "10000", "10000", "11111"),
    "F": ("11111", "10000", "10000", "11110", "10000", "10000", "10000"),
    "G": ("01111", "10000", "10000", "10111", "10001", "10001", "01111"),
    "H": ("10001", "10001", "10001", "11111", "10001", "10001", "10001"),
    "I": ("11111", "00100", "00100", "00100", "00100", "00100", "11111"),
    "J": ("00111", "00010", "00010", "00010", "10010", "10010", "01100"),
    "K": ("10001", "10010", "10100", "11000", "10100", "10010", "10001"),
    "L": ("10000", "10000", "10000", "10000", "10000", "10000", "11111"),
    "M": ("10001", "11011", "10101", "10101", "10001", "10001", "10001"),
    "N": ("10001", "11001", "10101", "10011", "10001", "10001", "10001"),
    "O": ("01110", "10001", "10001", "10001", "10001", "10001", "01110"),
    "P": ("11110", "10001", "10001", "11110", "10000", "10000", "10000"),
    "Q": ("01110", "10001", "10001", "10001", "10101", "10010", "01101"),
    "R": ("11110", "10001", "10001", "11110", "10100", "10010", "10001"),
    "S": ("01111", "10000", "10000", "01110", "00001", "00001", "11110"),
    "T": ("11111", "00100", "00100", "00100", "00100", "00100", "00100"),
    "U": ("10001", "10001", "10001", "10001", "10001", "10001", "01110"),
    "V": ("10001", "10001", "10001", "10001", "10001", "01010", "00100"),
    "W": ("10001", "10001", "10001", "10101", "10101", "11011", "10001"),
    "X": ("10001", "10001", "01010", "00100", "01010", "10001", "10001"),
    "Y": ("10001", "10001", "01010", "00100", "00100", "00100", "00100"),
    "Z": ("11111", "00001", "00010", "00100", "01000", "10000", "11111"),
    "0": ("01110", "10001", "10011", "10101", "11001", "10001", "01110"),
    "1": ("00100", "01100", "00100", "00100", "00100", "00100", "01110"),
    "2": ("01110", "10001", "00001", "00010", "00100", "01000", "11111"),
    "3": ("11110", "00001", "00001", "01110", "00001", "00001", "11110"),
    "4": ("00010", "00110", "01010", "10010", "11111", "00010", "00010"),
    "5": ("11111", "10000", "10000", "11110", "00001", "00001", "11110"),
    "6": ("01110", "10000", "10000", "11110", "10001", "10001", "01110"),
    "7": ("11111", "00001", "00010", "00100", "01000", "01000", "01000"),
    "8": ("01110", "10001", "10001", "01110", "10001", "10001", "01110"),
    "9": ("01110", "10001", "10001", "01111", "00001", "00001", "01110"),
    "-": ("00000", "00000", "00000", "11111", "00000", "00000", "00000"),
    "/": ("00001", "00010", "00010", "00100", "01000", "01000", "10000"),
    ".": ("00000", "00000", "00000", "00000", "00000", "00110", "00110"),
    "_": ("00000", "00000", "00000", "00000", "00000", "00000", "11111"),
}


def _assembly_label_sanitise_text(value):
    text = str(value or "").upper().strip()
    text = re.sub(r"\s+", " ", text)
    text = "".join(character if character in _ASSEMBLY_LABEL_FONT or character == " " else "-" for character in text)
    text = re.sub(r"\s*/\s*", " / ", text)
    text = re.sub(r"\s+", " ", text).strip(" /-")
    return text[:64]


def _assembly_label_target_family(record):
    subtype = str(record.get("subtype") or "")
    if subtype == ASSEMBLY_LABEL_SUBTYPE:
        return str(record.get("assembly_label_target_family") or "")
    if subtype in ("TrackTemplateCompound", "TrackTemplateSection"):
        return subtype
    if subtype in ("PlatformBody", "PlatformPlanOutline"):
        return "PlatformComplete"
    if subtype in ("PlatformSection", "PlatformSectionOutline"):
        return "PlatformSection"
    if subtype in ("FormationBody", "FormationPerimeter"):
        return "FormationComplete"
    if subtype in ("FormationSectionBody", "FormationSectionPerimeter"):
        return "FormationSection"
    return ""


def _assembly_label_target_key(record):
    stored = str(record.get("assembly_label_target_key") or "").strip()
    if stored:
        return stored
    family = _assembly_label_target_family(record)
    if not family:
        return ""
    return "|".join([
        str(record.get("template_set_id") or ""),
        str(record.get("route_id") or "CURVE"),
        family,
        "T{:02d}".format(int(record.get("track_number") or 0)),
        "P{:02d}".format(int(record.get("platform_number") or 0)),
        "S{:03d}".format(int(record.get("section_number") or 0)),
    ])


def _assembly_label_identity(record, config):
    platform_number = int(record.get("platform_number") or 0)
    track_number = int(record.get("track_number") or 0)
    family = _assembly_label_target_family(record)
    if platform_number > 0 and config.get("include_platform_identity", True):
        return "PLAT-{:02d}".format(platform_number)
    if family.startswith("Formation") and config.get("include_formation_identity", True):
        return "FB"
    if track_number > 0 and config.get("include_track_number", True):
        track_name = _assembly_label_sanitise_text(record.get("track_name") or "")
        if config.get("include_track_name", False) and track_name:
            return track_name
        return "T{:02d}".format(track_number)
    if family.startswith("TrackTemplate"):
        return "TRACKS"
    return "PART"


def assembly_label_text(record, config, set_id):
    config = validate_assembly_label_config(config)
    tokens = {
        "SET": str(set_id or record.get("template_set_id") or ""),
        "IDENTITY": _assembly_label_identity(record, config),
        "TRACK": "T{:02d}".format(int(record.get("track_number") or 0)) if int(record.get("track_number") or 0) > 0 else "",
        "TRACK_NAME": str(record.get("track_name") or ""),
        "SECTION": "S{:02d}".format(int(record.get("section_number") or 0)) if int(record.get("section_number") or 0) > 0 else "",
        "TRAVEL": "O{:02d}".format(int(record.get("travel_order_number") or 0)) if int(record.get("travel_order_number") or 0) > 0 else "",
        "PLATFORM": "PLAT-{:02d}".format(int(record.get("platform_number") or 0)) if int(record.get("platform_number") or 0) > 0 else "",
        "FORMATION": "FB" if _assembly_label_target_family(record).startswith("Formation") else "",
        "ROUTE": str(record.get("route_name") or ""),
    }
    if config["label_format"] == ASSEMBLY_LABEL_FORMAT_CUSTOM:
        text = str(config["custom_format"])
        for token, value in tokens.items():
            text = re.sub(r"\{" + token + r"\}", str(value), text, flags=re.I)
    else:
        parts = []
        if config.get("include_template_set_id", True) and tokens["SET"]:
            parts.append(tokens["SET"])
        identity = tokens["IDENTITY"]
        if identity and identity != "PART":
            parts.append(identity)
        if config.get("include_section_number", True) and tokens["SECTION"]:
            parts.append(tokens["SECTION"])
        if config.get("include_travel_order_number", False) and tokens["TRAVEL"]:
            parts.append(tokens["TRAVEL"])
        text = " / ".join(parts)
    text = _assembly_label_sanitise_text(text)
    if not text:
        raise ValueError("The selected assembly-label options produce empty label text.")
    return text


def _assembly_label_local_segments(text, text_height):
    text = _assembly_label_sanitise_text(text)
    cell = float(text_height) / 7.0
    glyph_advance = 6.0 * cell
    space_advance = 3.0 * cell
    segments = []
    cursor = 0.0
    for character in text:
        if character == " ":
            cursor += space_advance
            continue
        rows = _ASSEMBLY_LABEL_FONT.get(character, _ASSEMBLY_LABEL_FONT["-"])
        for row_index, row in enumerate(rows):
            start = None
            for column_index, bit in enumerate(row + "0"):
                if bit == "1" and start is None:
                    start = column_index
                elif bit != "1" and start is not None:
                    finish = column_index - 1
                    y_value = (6.5 - row_index) * cell
                    x_start = cursor + (start + 0.15) * cell
                    x_finish = cursor + (finish + 0.85) * cell
                    segments.append(((x_start, y_value), (x_finish, y_value)))
                    start = None
        cursor += glyph_advance
    width = max(cell, cursor - cell)
    return segments, width, float(text_height)


def _assembly_label_transform_point(x_value, y_value, origin, heading, z_value=0.0):
    tangent_x = math.cos(heading)
    tangent_y = math.sin(heading)
    normal_x, normal_y = left_normal(heading)
    return App.Vector(
        float(origin.x) + x_value * tangent_x + y_value * normal_x,
        float(origin.y) + x_value * tangent_y + y_value * normal_y,
        float(z_value),
    )


def _assembly_label_global_segments(local_segments, origin, heading, z_value=0.0):
    return [
        (
            _assembly_label_transform_point(start[0], start[1], origin, heading, z_value),
            _assembly_label_transform_point(finish[0], finish[1], origin, heading, z_value),
        )
        for start, finish in local_segments
    ]


def _assembly_label_rectangle(origin, heading, x_start, x_finish, y_start, y_finish):
    return _create_plan_face([
        _assembly_label_transform_point(x_start, y_start, origin, heading),
        _assembly_label_transform_point(x_finish, y_start, origin, heading),
        _assembly_label_transform_point(x_finish, y_finish, origin, heading),
        _assembly_label_transform_point(x_start, y_finish, origin, heading),
    ], "an assembly-label placement rectangle")


def _assembly_label_plan_faces(shape):
    """Return actual material faces in XY without treating internal holes as parts."""
    if _shape_is_null(shape):
        return []

    def flattened_faces(candidate):
        result = []
        try:
            candidate_faces = list(candidate.Faces)
        except Exception:
            candidate_faces = []
        for face in candidate_faces:
            if _horizontal_face_z(face) is None or float(getattr(face, "Area", 0.0)) <= GEOMETRY_TOLERANCE:
                continue
            copied = face.copy()
            vertices = _shape_vertices(copied)
            z_value = float(vertices[0].Point.z) if vertices else 0.0
            if abs(z_value) > GEOMETRY_TOLERANCE:
                copied.translate(App.Vector(0.0, 0.0, -z_value))
            result.append(copied)
        return result

    if shape_has_solid_geometry(shape):
        horizontal = []
        try:
            for face in shape.Faces:
                z_value = _horizontal_face_z(face)
                if z_value is not None and float(getattr(face, "Area", 0.0)) > GEOMETRY_TOLERANCE:
                    horizontal.append((float(z_value), face))
        except Exception:
            horizontal = []
        if not horizontal:
            return []
        top_z = max(item[0] for item in horizontal)
        top_faces = Part.makeCompound([
            face.copy() for z_value, face in horizontal
            if abs(z_value - top_z) <= 0.001
        ])
        return flattened_faces(top_faces)

    if not shape_is_planar_xy(shape):
        return []
    direct_faces = flattened_faces(shape)
    if direct_faces:
        return direct_faces

    try:
        wires = [wire.copy() for wire in shape.Wires if wire.isClosed()]
    except Exception:
        wires = []
    if not wires:
        try:
            wires = [shape.copy()] if shape.isClosed() else []
        except Exception:
            wires = []
    if not wires:
        return []

    # FaceMakerBullseye preserves internal voids and handles disjoint closed
    # profiles. This prevents a fixing hole or socket wire from becoming a
    # false label-placement face merely because it is closed.
    maker = getattr(Part, "makeFace", None)
    if callable(maker):
        try:
            built = maker(wires, "Part::FaceMakerBullseye")
            built_faces = flattened_faces(built)
            if built_faces:
                return built_faces
        except Exception:
            pass

    fallback_faces = []
    for wire in wires:
        try:
            face = Part.Face(wire)
            if not face.isNull() and float(face.Area) > GEOMETRY_TOLERANCE:
                fallback_faces.append(face)
        except Exception:
            continue
    if len(fallback_faces) <= 1:
        return fallback_faces

    # Without FaceMakerBullseye, remove faces wholly contained by a larger
    # face. Such nested faces represent voids, not usable production material.
    usable = []
    ordered = sorted(fallback_faces, key=lambda item: float(getattr(item, "Area", 0.0)), reverse=True)
    for candidate in ordered:
        nested = any(
            _candidate_inside_formation(candidate, outer)
            for outer in usable
            if float(getattr(outer, "Area", 0.0)) > float(getattr(candidate, "Area", 0.0))
        )
        if not nested:
            usable.append(candidate)
    return usable


def _assembly_label_protected_faces(records, target_record):
    protected = []
    target_route = str(target_record.get("route_id") or "")
    target_track = int(target_record.get("track_number") or 0)
    target_section = int(target_record.get("section_number") or 0)
    for record in records or []:
        if record.get("category") not in (EXPORT_CATEGORY_HOLES, EXPORT_CATEGORY_JOINTS):
            continue
        if str(record.get("route_id") or "") != target_route:
            continue
        record_track = int(record.get("track_number") or 0)
        record_section = int(record.get("section_number") or 0)
        if target_track > 0 and record_track not in (0, target_track):
            continue
        if target_section > 0 and record_section not in (0, target_section):
            continue
        protected.extend(_assembly_label_plan_faces(record.get("shape")))
    return protected


def _assembly_label_candidate_headings(face):
    headings = [0.0, 0.5 * math.pi]
    edges = []
    try:
        edges = sorted(list(face.Edges), key=lambda edge: float(edge.Length), reverse=True)
    except Exception:
        edges = []
    for edge in edges[:12]:
        try:
            vertices = list(edge.Vertexes)
            if len(vertices) < 2:
                continue
            start = vertices[0].Point
            finish = vertices[-1].Point
            dx = float(finish.x) - float(start.x)
            dy = float(finish.y) - float(start.y)
            if math.hypot(dx, dy) <= GEOMETRY_TOLERANCE:
                continue
            headings.append(math.atan2(dy, dx))
        except Exception:
            continue
    unique = []
    for heading in headings:
        normalised = heading % math.pi
        if all(abs(math.sin(normalised - existing)) > 1.0e-3 for existing in unique):
            unique.append(normalised)
    return unique


def _assembly_label_preference_order(preferred):
    if preferred == ASSEMBLY_LABEL_PLACE_UNDERSIDE_ENTRY:
        return ["entry", "exit", "centre"], ["underside", "top"]
    if preferred == ASSEMBLY_LABEL_PLACE_UNDERSIDE_EXIT:
        return ["exit", "entry", "centre"], ["underside", "top"]
    if preferred == ASSEMBLY_LABEL_PLACE_TOP_ENTRY:
        return ["entry", "exit", "centre"], ["top", "underside"]
    if preferred == ASSEMBLY_LABEL_PLACE_TOP_EXIT:
        return ["exit", "entry", "centre"], ["top", "underside"]
    return ["exit", "entry", "centre"], ["underside", "top"]


def _assembly_label_find_placement(plan_faces, protected_faces, width, height, margin, preferred):
    longitudinal_order, surfaces = _assembly_label_preference_order(preferred)
    for face in sorted(plan_faces, key=lambda item: float(getattr(item, "Area", 0.0)), reverse=True):
        vertices = _shape_vertices(face)
        if not vertices:
            continue
        for heading in _assembly_label_candidate_headings(face):
            tangent_x = math.cos(heading)
            tangent_y = math.sin(heading)
            normal_x, normal_y = left_normal(heading)
            t_values = [float(vertex.Point.x) * tangent_x + float(vertex.Point.y) * tangent_y for vertex in vertices]
            n_values = [float(vertex.Point.x) * normal_x + float(vertex.Point.y) * normal_y for vertex in vertices]
            if not t_values or not n_values:
                continue
            t_min, t_max = min(t_values), max(t_values)
            n_min, n_max = min(n_values), max(n_values)
            if t_max - t_min < width + 2.0 * margin or n_max - n_min < height + 2.0 * margin:
                continue
            t_starts = {
                "entry": t_min + margin,
                "exit": t_max - margin - width,
                "centre": 0.5 * (t_min + t_max - width),
            }
            n_starts = [
                n_min + margin,
                n_max - margin - height,
                0.5 * (n_min + n_max - height),
            ]
            for longitudinal in longitudinal_order:
                for n_start in n_starts:
                    t_start = t_starts[longitudinal]
                    origin = App.Vector(
                        t_start * tangent_x + n_start * normal_x,
                        t_start * tangent_y + n_start * normal_y,
                        0.0,
                    )
                    footprint = _assembly_label_rectangle(origin, heading, 0.0, width, 0.0, height)
                    clearance = _assembly_label_rectangle(
                        origin, heading, -margin, width + margin, -margin, height + margin
                    )
                    if not _candidate_inside_formation(clearance, face):
                        continue
                    if not _candidate_clear_of_protected(clearance, protected_faces):
                        continue
                    return {
                        "origin": origin,
                        "heading": heading,
                        "footprint": footprint,
                        "clearance": clearance,
                        "surface_order": surfaces,
                        "longitudinal": longitudinal,
                    }
    return None


def _assembly_label_line_shape(segments):
    edges = []
    for start, finish in segments:
        try:
            if start.distanceToPoint(finish) <= GEOMETRY_TOLERANCE:
                continue
        except Exception:
            pass
        edge = Part.makeLine(start, finish)
        if not edge.isNull():
            edges.append(edge)
    if not edges:
        return None
    return edges[0] if len(edges) == 1 else Part.makeCompound(edges)


def _assembly_label_segment_face(start, finish, width):
    dx = float(finish.x) - float(start.x)
    dy = float(finish.y) - float(start.y)
    length = math.hypot(dx, dy)
    if length <= GEOMETRY_TOLERANCE:
        return None
    nx = -dy / length
    ny = dx / length
    half = 0.5 * float(width)
    return _create_plan_face([
        App.Vector(start.x + half * nx, start.y + half * ny, 0.0),
        App.Vector(finish.x + half * nx, finish.y + half * ny, 0.0),
        App.Vector(finish.x - half * nx, finish.y - half * ny, 0.0),
        App.Vector(start.x - half * nx, start.y - half * ny, 0.0),
    ], "an assembly-label engraving stroke")


def _assembly_label_engrave_solid(shape, segments, stroke_width, depth, surface):
    if _shape_is_null(shape) or not shape_has_solid_geometry(shape):
        raise ValueError("Assembly-label engraving requires valid solid geometry.")
    bounds = shape.BoundBox
    thickness = max(0.0, float(bounds.ZLength))
    if thickness <= GEOMETRY_TOLERANCE:
        raise ValueError("The production solid has no usable thickness for engraving.")
    if depth >= thickness - 0.02:
        raise ValueError(
            "The {:.3f} mm engraving depth is too large for a {:.3f} mm part.".format(depth, thickness)
        )
    cutter_height = float(depth) + 0.08
    z_start = (
        float(bounds.ZMin) - 0.04
        if surface == "underside"
        else float(bounds.ZMax) - float(depth) - 0.04
    )
    cutters = []
    for start, finish in segments:
        face = _assembly_label_segment_face(start, finish, stroke_width)
        if face is None:
            continue
        face.translate(App.Vector(0.0, 0.0, z_start))
        cutters.append(face.extrude(App.Vector(0.0, 0.0, cutter_height)))
    if not cutters:
        raise ValueError("The assembly label produced no engraving cutters.")
    cutter = cutters[0] if len(cutters) == 1 else Part.makeCompound(cutters)
    try:
        before_volume = float(shape.Volume)
    except Exception:
        before_volume = 0.0
    result = _refine_shape(shape.copy().cut(cutter))
    if _shape_is_null(result) or not shape_has_solid_geometry(result):
        raise ValueError("The assembly-label cut did not leave a valid solid.")
    try:
        if not result.isValid():
            raise ValueError("The assembly-label cut produced an invalid OpenCascade shape.")
    except AttributeError:
        pass
    try:
        after_volume = float(result.Volume)
    except Exception:
        after_volume = before_volume
    if before_volume > GEOMETRY_TOLERANCE and before_volume - after_volume <= GEOMETRY_TOLERANCE:
        raise ValueError("The assembly-label cutters did not intersect the production solid.")
    try:
        if len(result.Solids) > len(shape.Solids):
            raise ValueError("The assembly-label cut would split the production solid.")
    except AttributeError:
        pass
    return result


def _assembly_label_group_records(records):
    grouped = {}
    for record in records or []:
        family = _assembly_label_target_family(record)
        if not family or str(record.get("subtype") or "") == ASSEMBLY_LABEL_SUBTYPE:
            continue
        key = _assembly_label_target_key(record)
        if key:
            grouped.setdefault(key, []).append(record)
    return grouped


def apply_assembly_labels_to_records(records, config, set_id):
    config = validate_assembly_label_config(config)
    base_records = [record for record in records or [] if str(record.get("subtype") or "") != ASSEMBLY_LABEL_SUBTYPE]
    for record in base_records:
        record.pop("assembly_label_status", None)
        record.pop("assembly_label_reason", None)
        record.pop("assembly_label_text", None)
        record.pop("assembly_label_surface", None)
        record.pop("assembly_label_target_key", None)
        record.pop("force_production_source", None)
        record.pop("assembly_label_derived", None)
    if not config.get("enabled", False):
        return base_records, []

    diagnostics = []
    label_records = []
    for target_key, grouped_records in sorted(_assembly_label_group_records(base_records).items()):
        cutting_records = [record for record in grouped_records if record.get("category") == EXPORT_CATEGORY_CUTTING]
        solid_records = [record for record in grouped_records if record.get("category") == EXPORT_CATEGORY_SOLID]
        representative = solid_records[0] if solid_records else (cutting_records[0] if cutting_records else grouped_records[0])
        representative["template_set_id"] = str(set_id or "")
        text = assembly_label_text(representative, config, set_id)
        local_segments, text_width, text_height = _assembly_label_local_segments(text, config["text_height"])
        plan_faces = []
        for record in cutting_records + solid_records:
            plan_faces.extend(_assembly_label_plan_faces(record.get("shape")))
            if plan_faces:
                break
        protected_faces = _assembly_label_protected_faces(base_records, representative)
        placement = _assembly_label_find_placement(
            plan_faces,
            protected_faces,
            text_width,
            text_height,
            config["edge_margin"],
            config["preferred_placement"],
        )
        if placement is None:
            reason = "No safe in-part placement remains after the configured edge, hole and joint clearances."
            for record in grouped_records:
                record["assembly_label_status"] = "Skipped"
                record["assembly_label_reason"] = reason
                record["assembly_label_text"] = text
                record["assembly_label_target_key"] = target_key
            diagnostics.append({
                "severity": PRODUCTION_PREFLIGHT_SEVERITY_WARNING,
                "target_key": target_key,
                "target_label": str(representative.get("source_label") or representative.get("role") or target_key),
                "label_text": text,
                "status": "Skipped",
                "reason": reason,
            })
            continue
        global_segments = _assembly_label_global_segments(
            local_segments, placement["origin"], placement["heading"], 0.0
        )
        line_shape = _assembly_label_line_shape(global_segments)
        if _shape_is_null(line_shape):
            reason = "The compact label font produced no usable engraving geometry."
            for record in grouped_records:
                record["assembly_label_status"] = "Skipped"
                record["assembly_label_reason"] = reason
                record["assembly_label_text"] = text
                record["assembly_label_target_key"] = target_key
            diagnostics.append({
                "severity": PRODUCTION_PREFLIGHT_SEVERITY_WARNING,
                "target_key": target_key,
                "target_label": str(representative.get("source_label") or representative.get("role") or target_key),
                "label_text": text,
                "status": "Skipped",
                "reason": reason,
            })
            continue

        chosen_surface = placement["surface_order"][0]
        solid_failure = ""
        for surface in placement["surface_order"]:
            engraved = []
            try:
                for record in solid_records:
                    engraved.append(_assembly_label_engrave_solid(
                        record.get("shape"), global_segments, config["stroke_width"],
                        config["engraving_depth"], surface,
                    ))
                for record, new_shape in zip(solid_records, engraved):
                    original_shape = record.get("shape")
                    record["assembly_label_base_shape"] = (
                        original_shape.copy() if original_shape is not None and hasattr(original_shape, "copy") else original_shape
                    )
                    record["shape"] = new_shape
                    record["force_production_source"] = True
                    record["assembly_label_derived"] = True
                chosen_surface = surface
                solid_failure = ""
                break
            except Exception as error:
                solid_failure = str(error)
                continue
        if solid_records and solid_failure:
            reason = "No safe 3D engraving surface could be created: {}".format(solid_failure)
            for record in grouped_records:
                record["assembly_label_status"] = "Skipped"
                record["assembly_label_reason"] = reason
                record["assembly_label_text"] = text
                record["assembly_label_target_key"] = target_key
            diagnostics.append({
                "severity": PRODUCTION_PREFLIGHT_SEVERITY_WARNING,
                "target_key": target_key,
                "target_label": str(representative.get("source_label") or representative.get("role") or target_key),
                "label_text": text,
                "status": "Skipped",
                "reason": reason,
            })
            continue

        for record in grouped_records:
            record["assembly_label_status"] = "Placed"
            record["assembly_label_reason"] = ""
            record["assembly_label_text"] = text
            record["assembly_label_surface"] = chosen_surface
            record["assembly_label_target_key"] = target_key
        label_record = make_export_record(
            line_shape,
            "RailwayAssemblyLabel_{}".format(len(label_records) + 1),
            "{} - {}".format(text, representative.get("source_label") or "Assembly label"),
            ASSEMBLY_LABEL_ROLE,
            ASSEMBLY_LABEL_SUBTYPE,
            EXPORT_CATEGORY_ENGRAVING,
            ASSEMBLY_LABEL_SELECTION_KEY,
            track_number=representative.get("track_number", 0),
            section_number=representative.get("section_number", 0),
            travel_order_number=representative.get("travel_order_number", 0),
            section_length=representative.get("section_length", 0.0),
            platform_number=representative.get("platform_number", 0),
            platform_name=representative.get("platform_name", ""),
            route_id=representative.get("route_id", ""),
            route_name=representative.get("route_name", ""),
            template_thickness=representative.get("template_thickness", TEMPLATE_THICKNESS),
            track_name=representative.get("track_name", ""),
            feature_number=len(label_records) + 1,
        )
        label_record.update({
            "template_set_id": str(set_id or ""),
            "assembly_label_status": "Placed",
            "assembly_label_text": text,
            "assembly_label_surface": chosen_surface,
            "assembly_label_target_key": target_key,
            "assembly_label_target_family": _assembly_label_target_family(representative),
            "assembly_label_target_record_id": str(representative.get("record_id") or ""),
            "assembly_label_target_feature_number": int(representative.get("feature_number") or 0),
            "assembly_label_derived": True,
            "force_production_source": True,
        })
        label_records.append(label_record)
        diagnostics.append({
            "severity": PRODUCTION_PREFLIGHT_SEVERITY_INFORMATION,
            "target_key": target_key,
            "target_label": str(representative.get("source_label") or representative.get("role") or target_key),
            "label_text": text,
            "status": "Placed",
            "surface": chosen_surface,
            "reason": "",
        })
    return base_records + label_records, diagnostics


def capture_assembly_label_base_sources(records):
    for record in records or []:
        if str(record.get("subtype") or "") == ASSEMBLY_LABEL_SUBTYPE:
            continue
        if not str(record.get("assembly_label_status") or ""):
            continue
        derived = bool(record.get("assembly_label_derived", False))
        source_name = str(record.get("source_name") or "")
        source_label = str(record.get("source_label") or "")
        if (not derived) or not str(record.get("base_source_name") or "").strip():
            record["base_source_name"] = source_name
        if (not derived) or not str(record.get("base_source_label") or "").strip():
            record["base_source_label"] = source_label
    return records


def materialise_assembly_label_base_sources(doc, parent_group, set_id, records):
    source_group = next((
        obj for obj in list(doc.Objects)
        if object_string_property(obj, "GeneratedBy", "") == GENERATOR_ID
        and object_string_property(obj, "TemplateSetID", "") == str(set_id or "")
        and object_string_property(obj, "GeneratedRole", "") == "ProductionSourceGroup"
    ), None)
    created = 0
    for record in records or []:
        if not bool(record.get("assembly_label_derived", False)):
            continue
        base_shape = record.get("assembly_label_base_shape")
        if _shape_is_null(base_shape):
            continue
        base_name = str(record.get("base_source_name") or "")
        base_object = (
            doc.getObject(base_name)
            if base_name and "::" not in base_name and "+" not in base_name
            else None
        )
        if base_object is not None:
            continue
        if source_group is None:
            group_name = unique_internal_name(
                doc,
                "RailwayProductionSources_{}".format(
                    safe_filename_component(set_id, "SET").replace("-", "_")
                ),
            )
            source_group = doc.addObject("App::DocumentObjectGroup", group_name)
            source_group.Label = "Production Sources [{}]".format(set_id)
            tag_generated_object(source_group, "ProductionSourceGroup", set_id)
            if parent_group is not None:
                parent_group.addObject(source_group)
            if Gui is not None:
                try:
                    source_group.ViewObject.Visibility = False
                except Exception:
                    pass
        source_object = doc.addObject(
            "Part::Feature",
            unique_internal_name(doc, "RailwayAssemblyLabelBaseSource_{}".format(created + 1)),
        )
        source_object.Label = "Unlabelled Production Source - {}".format(
            str(record.get("source_label") or record.get("subtype") or "Part")
        )
        source_object.Shape = base_shape.copy()
        tag_generated_object(source_object, "ProductionSource", set_id)
        if str(record.get("route_id") or "") or str(record.get("route_name") or ""):
            tag_route_metadata(source_object, record.get("route_id", ""), record.get("route_name", ""))
        tag_export_metadata(
            source_object,
            record.get("subtype", ""),
            record.get("category", ""),
            track_number=record.get("track_number", 0),
            platform_number=record.get("platform_number", 0),
            platform_name=record.get("platform_name", ""),
            section_number=record.get("section_number", 0),
            travel_order_number=record.get("travel_order_number", 0),
            section_length=record.get("section_length", 0.0),
            feature_number=record.get("feature_number", 0),
        )
        properties = [
            ensure_property(source_object, "App::PropertyBool", "AssemblyLabelBaseSource", "Production utilities", "Unlabelled source retained so labels can be disabled or regenerated safely"),
            ensure_property(source_object, "App::PropertyString", ASSEMBLY_LABEL_TARGET_PROPERTY, "Production utilities", "Semantic production-part key associated with this retained source"),
            ensure_property(source_object, "App::PropertyString", "TrackName", "Production export", "Generated track name"),
        ]
        source_object.AssemblyLabelBaseSource = True
        setattr(source_object, ASSEMBLY_LABEL_TARGET_PROPERTY, str(record.get("assembly_label_target_key") or ""))
        source_object.TrackName = str(record.get("track_name") or "")
        set_read_only(source_object, properties)
        source_group.addObject(source_object)
        if Gui is not None:
            try:
                source_object.ViewObject.Visibility = False
            except Exception:
                pass
        record["base_source_name"] = str(source_object.Name)
        record["base_source_label"] = str(source_object.Label)
        created += 1
    return created


def assembly_label_records_from_index(doc, set_id):
    payload = production_record_index_for_set(doc, set_id)
    records = []
    for stored in payload.get("records", []):
        if str(stored.get("subtype") or "") == ASSEMBLY_LABEL_SUBTYPE:
            continue
        record = dict(stored)
        source_name = str(record.get("base_source_name") or record.get("source_name") or "")
        source_object = doc.getObject(source_name) if source_name and "::" not in source_name and "+" not in source_name else None
        shape = getattr(source_object, "Shape", None) if source_object is not None else None
        record["shape"] = shape.copy() if shape is not None and hasattr(shape, "copy") else shape
        record["source_name"] = source_name
        record["source_label"] = str(record.get("base_source_label") or getattr(source_object, "Label", source_name) or source_name)
        record["source_binding_type"] = "direct" if source_object is not None else "unbound"
        record.pop("assembly_label_status", None)
        record.pop("assembly_label_reason", None)
        record.pop("assembly_label_text", None)
        record.pop("assembly_label_surface", None)
        record.pop("assembly_label_target_key", None)
        record.pop("force_production_source", None)
        record.pop("assembly_label_derived", None)
        records.append(record)
    assign_production_record_ids(records, set_id)
    return records


def read_assembly_label_config(obj):
    stored = object_string_property(obj, ASSEMBLY_LABEL_SETTINGS_PROPERTY, "")
    if stored:
        try:
            decoded = json.loads(stored)
            if isinstance(decoded, dict):
                return clone_assembly_label_config(decoded)
        except Exception:
            pass
    return default_assembly_label_config()


def store_assembly_label_config(obj, config):
    if obj is None:
        return
    property_name = ensure_property(
        obj,
        "App::PropertyString",
        ASSEMBLY_LABEL_SETTINGS_PROPERTY,
        "Production utilities",
        "Stored compact assembly-label settings",
    )
    setattr(obj, ASSEMBLY_LABEL_SETTINGS_PROPERTY, json.dumps(clone_assembly_label_config(config), sort_keys=True))
    set_read_only(obj, [property_name])


def _assembly_label_object_is_derived(obj, set_id):
    if object_string_property(obj, "TemplateSetID", "") != str(set_id or ""):
        return False
    if ASSEMBLY_LABEL_DERIVED_PROPERTY in getattr(obj, "PropertiesList", []):
        try:
            return bool(getattr(obj, ASSEMBLY_LABEL_DERIVED_PROPERTY))
        except Exception:
            pass
    return object_string_property(obj, "GeneratedRole", "") == ASSEMBLY_LABEL_ROLE


def remove_assembly_label_derived_objects(doc, set_id):
    names = [
        str(obj.Name) for obj in list(doc.Objects)
        if _assembly_label_object_is_derived(obj, set_id)
    ]
    for name in names:
        doc.removeObject(name)
    return names


def production_parent_group_for_set(doc, set_id):
    candidates = [
        obj for obj in list(doc.Objects)
        if object_string_property(obj, "GeneratedBy", "") == GENERATOR_ID
        and object_string_property(obj, "TemplateSetID", "") == str(set_id or "")
        and object_string_property(obj, "GeneratedRole", "") == "Group"
    ]
    return candidates[0] if candidates else None


def rebuild_assembly_labels_for_set(doc, set_id, config):
    settings = settings_for_template_set(doc, set_id)
    if settings is None:
        raise ValueError("The selected template set has no recognised settings object.")
    config = validate_assembly_label_config(config)
    base_records = assembly_label_records_from_index(doc, set_id)
    if not base_records:
        raise ValueError("The selected template set has no persistent production records to label.")
    labelled_records, diagnostics = apply_assembly_labels_to_records(base_records, config, set_id)
    assign_production_record_ids(labelled_records, set_id)
    blocking = [record for record in labelled_records if _shape_is_null(record.get("shape"))]
    if blocking:
        raise ValueError("One or more production records lost their source geometry during label preparation.")

    transaction_open = False
    try:
        doc.openTransaction("Apply Version {} assembly labels".format(MACRO_VERSION_NUMBER))
        transaction_open = True
        remove_assembly_label_derived_objects(doc, set_id)
        parent_group = production_parent_group_for_set(doc, set_id)
        capture_assembly_label_base_sources(labelled_records)
        materialise_assembly_label_base_sources(doc, parent_group, set_id, labelled_records)
        materialise_production_source_objects(doc, parent_group, set_id, labelled_records)
        capture_assembly_label_base_sources(labelled_records)
        tag_production_record_bindings(doc, set_id, labelled_records)
        index_payload = build_production_record_index(labelled_records, set_id)
        index_property = ensure_property(
            settings,
            "App::PropertyString",
            PRODUCTION_RECORD_INDEX_PROPERTY,
            "Production utilities",
            "Persistent one-record production catalogue",
        )
        setattr(settings, PRODUCTION_RECORD_INDEX_PROPERTY, json.dumps(index_payload, sort_keys=True))
        set_read_only(settings, [index_property])
        store_assembly_label_config(settings, config)
        _document_recompute(doc)
        doc.commitTransaction()
        transaction_open = False
    except Exception:
        if transaction_open:
            try:
                doc.abortTransaction()
            except Exception:
                pass
        raise

    # The existing report helpers each own a complete document transaction.
    # Run them only after the label transaction commits so FreeCAD never sees
    # nested transactions. Report refresh failure does not undo valid labels;
    # it is returned as a warning diagnostic instead.
    export_config = read_production_export_config(settings)
    try:
        schedule_rows = build_production_schedule_rows(index_payload, export_config, set_id)
        create_or_replace_production_schedule(doc, set_id, schedule_rows)
    except Exception as error:
        diagnostics.append({
            "severity": PRODUCTION_PREFLIGHT_SEVERITY_WARNING,
            "target_key": "",
            "target_label": "Production schedule",
            "label_text": "",
            "status": "Warning",
            "reason": "Assembly labels were applied, but the production schedule could not be refreshed: {}".format(error),
        })
    try:
        material_config = read_material_report_config(settings)
        material_rows, material_diagnostics = build_material_report_rows(
            doc, index_payload, settings, material_config, set_id
        )
        create_or_replace_material_report(
            doc, set_id, material_rows, material_config, material_diagnostics
        )
    except Exception as error:
        diagnostics.append({
            "severity": PRODUCTION_PREFLIGHT_SEVERITY_WARNING,
            "target_key": "",
            "target_label": "Material and length report",
            "label_text": "",
            "status": "Warning",
            "reason": "Assembly labels were applied, but the material report could not be refreshed: {}".format(error),
        })
    return index_payload, diagnostics

def complete_production_record_config(config):
    """Return a record-building configuration that recognises every available output."""
    complete = clone_production_export_config(config)
    complete["enabled"] = False
    complete["formats"] = {
        EXPORT_FORMAT_DXF: True,
        EXPORT_FORMAT_SVG: True,
        EXPORT_FORMAT_STL: True,
        EXPORT_FORMAT_STEP: True,
    }
    complete["selections"] = {
        key: True for key in default_production_export_config()["selections"]
    }
    return complete


def filter_records_for_export_config(records, config):
    """Filter complete catalogue records using the established export selections."""
    selected = []
    for record in records:
        selection_key = str(record.get("selection_key") or "")
        if selection_key and _record_selected(config, selection_key):
            selected.append(record)
    return selected


def populate_production_record_track_names(
    records,
    curve_alignments,
    straight_production_results,
):
    curve_names = {
        index + 1: str(alignment.get("name") or "Track {}".format(index + 1))
        for index, alignment in enumerate(curve_alignments or [])
    }
    straight_names = {}
    for bundle in straight_production_results or []:
        route_id = str(bundle.get("route_id") or "")
        straight_names[route_id] = {
            index + 1: str(alignment.get("name") or "Track {}".format(index + 1))
            for index, alignment in enumerate(bundle.get("alignments", []))
        }
    for record in records:
        track_number = int(record.get("track_number") or 0)
        if track_number <= 0 or str(record.get("track_name") or "").strip():
            continue
        route_id = str(record.get("route_id") or "")
        if route_id:
            record["track_name"] = straight_names.get(route_id, {}).get(
                track_number, "Track {}".format(track_number)
            )
        else:
            record["track_name"] = curve_names.get(
                track_number, "Track {}".format(track_number)
            )
    return records


def production_record_identity(record, set_id):
    route_token = str(record.get("route_id") or "CURVE").strip() or "CURVE"
    tokens = [
        str(set_id or "UNSET"),
        route_token,
        str(record.get("role") or "UnknownRole"),
        str(record.get("subtype") or "UnknownSubtype"),
        str(record.get("category") or "UnknownCategory"),
        "T{:02d}".format(int(record.get("track_number") or 0)),
        "P{:02d}".format(int(record.get("platform_number") or 0)),
        "S{:03d}".format(int(record.get("section_number") or 0)),
        "F{:03d}".format(int(record.get("feature_number") or 0)),
        str(record.get("selection_key") or "Unselected"),
    ]
    return "|".join(tokens)


def assign_production_record_ids(records, set_id):
    counts = {}
    for record in records:
        base = production_record_identity(record, set_id)
        counts[base] = counts.get(base, 0) + 1
        occurrence = counts[base]
        record["record_id"] = (
            base if occurrence == 1 else "{}|N{:02d}".format(base, occurrence)
        )
        record["template_set_id"] = str(set_id or "")
    return records


def _integer_object_property(obj, name, fallback=0):
    if obj is None or name not in getattr(obj, "PropertiesList", []):
        return fallback
    try:
        return int(getattr(obj, name))
    except Exception:
        return fallback


def _shape_bounding_dimensions(shape):
    if _shape_is_null(shape):
        return 0.0, 0.0, 0.0
    try:
        bounds = shape.BoundBox
        x_length = max(0.0, float(bounds.XLength))
        y_length = max(0.0, float(bounds.YLength))
        z_length = max(0.0, float(bounds.ZLength))
        return max(x_length, y_length), min(x_length, y_length), z_length
    except Exception:
        return 0.0, 0.0, 0.0


def _supported_formats_for_category(category):
    if category == EXPORT_CATEGORY_SOLID:
        return [EXPORT_FORMAT_STL, EXPORT_FORMAT_STEP]
    if category in (
        EXPORT_CATEGORY_CUTTING,
        EXPORT_CATEGORY_HOLES,
        EXPORT_CATEGORY_JOINTS,
        EXPORT_CATEGORY_ENGRAVING,
    ):
        return [EXPORT_FORMAT_DXF, EXPORT_FORMAT_SVG]
    return []


def _record_requires_track_identity(record):
    if str(record.get("subtype") or "") == ASSEMBLY_LABEL_SUBTYPE:
        return False
    if int(record.get("track_number") or 0) > 0:
        return True
    subtype = str(record.get("subtype") or "")
    return subtype in ("TrackCentreline", "TrackTemplateFixingHole")


def _record_requires_platform_identity(record):
    subtype = str(record.get("subtype") or "")
    if subtype == ASSEMBLY_LABEL_SUBTYPE:
        return False
    role = str(record.get("role") or "")
    return "Platform" in subtype or role.startswith("Platform")


def _record_requires_section_identity(record):
    subtype = str(record.get("subtype") or "")
    if subtype == ASSEMBLY_LABEL_SUBTYPE:
        return False
    return (
        "Section" in subtype
        or subtype in ("SectionNumberEngraving", "TrackTemplateFixingHole")
    )


def _record_requires_travel_order_identity(record):
    if _record_requires_section_identity(record):
        return True
    subtype = str(record.get("subtype") or "")
    return subtype in (
        "TrackTemplateJoint",
        "RegistrationJoint",
        "RegistrationHole",
    )


def production_record_metadata_issues(record, set_id):
    issues = []
    if not str(set_id or record.get("template_set_id") or "").strip():
        issues.append("Missing template-set identity")
    if not str(record.get("role") or "").strip():
        issues.append("Missing generated role")
    if not str(record.get("subtype") or "").strip():
        issues.append("Missing export subtype")
    if not str(record.get("category") or "").strip():
        issues.append("Missing export category")
    if _record_requires_track_identity(record):
        if int(record.get("track_number") or 0) <= 0:
            issues.append("Missing track number")
        if not str(record.get("track_name") or "").strip():
            issues.append("Missing track name")
    if _record_requires_platform_identity(record):
        if int(record.get("platform_number") or 0) <= 0:
            issues.append("Missing platform number")
        if not str(record.get("platform_name") or "").strip():
            issues.append("Missing platform name")
    if _record_requires_section_identity(record):
        if int(record.get("section_number") or 0) <= 0:
            issues.append("Missing section number")
    if _record_requires_travel_order_identity(record):
        if int(record.get("travel_order_number") or 0) <= 0:
            issues.append("Missing travel-order number")
    if not str(record.get("source_name") or "").strip():
        issues.append("Missing source-object identity")
    return issues


def _source_binding_type(source_name):
    name = str(source_name or "")
    if "+" in name:
        return "multiple-objects"
    if "::" in name:
        return "compound-member"
    return "direct" if name else "unbound"


def build_production_record_index(records, set_id):
    index_records = []
    for record in records:
        shape = record.get("shape")
        length, width, height = _shape_bounding_dimensions(shape)
        valid, invalid_reason = validate_export_record(record)
        metadata_issues = production_record_metadata_issues(record, set_id)
        diagnostic_status = "Information"
        diagnostic_details = []
        if not valid:
            diagnostic_status = "Error"
            diagnostic_details.append(str(invalid_reason or "Invalid geometry"))
        if metadata_issues:
            if diagnostic_status != "Error":
                diagnostic_status = "Warning"
            diagnostic_details.extend(metadata_issues)
        source_binding = str(record.get("source_binding_type") or "").strip()
        if not source_binding:
            source_binding = _source_binding_type(record.get("source_name"))
        if source_binding in ("compound-member", "multiple-objects", "unbound"):
            if diagnostic_status != "Error":
                diagnostic_status = "Warning"
            diagnostic_details.append(
                {
                    "compound-member": "Source geometry belongs to a combined generated object",
                    "multiple-objects": "Record matched more than one generated object",
                    "unbound": "Record did not bind to a generated object",
                }[source_binding]
            )
        if str(record.get("assembly_label_status") or "") == "Skipped":
            if diagnostic_status != "Error":
                diagnostic_status = "Warning"
            diagnostic_details.append(
                "Assembly label skipped: {}".format(
                    str(record.get("assembly_label_reason") or "no safe placement exists")
                )
            )
        index_records.append({
            "record_id": str(record.get("record_id") or ""),
            "template_set_id": str(set_id or ""),
            "source_name": str(record.get("source_name") or ""),
            "source_label": str(record.get("source_label") or ""),
            "source_binding_type": source_binding,
            "role": str(record.get("role") or ""),
            "subtype": str(record.get("subtype") or ""),
            "category": str(record.get("category") or ""),
            "selection_key": str(record.get("selection_key") or ""),
            "route_id": str(record.get("route_id") or ""),
            "route_name": str(record.get("route_name") or ""),
            "track_number": int(record.get("track_number") or 0),
            "track_name": str(record.get("track_name") or ""),
            "platform_number": int(record.get("platform_number") or 0),
            "platform_name": str(record.get("platform_name") or ""),
            "section_number": int(record.get("section_number") or 0),
            "travel_order_number": int(record.get("travel_order_number") or 0),
            "feature_number": int(record.get("feature_number") or 0),
            "section_length": max(0.0, float(record.get("section_length") or 0.0)),
            "template_thickness": max(
                0.0, float(record.get("template_thickness") or 0.0)
            ),
            "platform_height": max(
                0.0, float(record.get("platform_height") or 0.0)
            ),
            "overall_length": length,
            "overall_width": width,
            "overall_height": height,
            "measurement_classification": "Bounding-box estimate",
            "supported_formats": _supported_formats_for_category(
                record.get("category")
            ),
            "geometry_valid": bool(valid),
            "diagnostic_status": diagnostic_status,
            "diagnostic_details": "; ".join(diagnostic_details),
            "base_source_name": str(record.get("base_source_name") or ""),
            "base_source_label": str(record.get("base_source_label") or ""),
            "assembly_label_status": str(record.get("assembly_label_status") or ""),
            "assembly_label_reason": str(record.get("assembly_label_reason") or ""),
            "assembly_label_text": str(record.get("assembly_label_text") or ""),
            "assembly_label_surface": str(record.get("assembly_label_surface") or ""),
            "assembly_label_target_key": str(record.get("assembly_label_target_key") or ""),
            "assembly_label_target_family": str(record.get("assembly_label_target_family") or ""),
            "assembly_label_target_record_id": str(record.get("assembly_label_target_record_id") or ""),
            "assembly_label_target_feature_number": int(record.get("assembly_label_target_feature_number") or 0),
            "assembly_label_derived": bool(record.get("assembly_label_derived", False)),
        })
    return {
        "schema_version": PRODUCTION_RECORD_SCHEMA_VERSION,
        "macro_version": MACRO_VERSION,
        "created_at": datetime.datetime.now().astimezone().isoformat(
            timespec="seconds"
        ),
        "template_set_id": str(set_id or ""),
        "records": index_records,
    }



def materialise_production_source_objects(doc, parent_group, set_id, records):
    """Create hidden one-record source objects only where the visible binding is ambiguous."""
    direct_groups = {}
    for record in records:
        source_name = str(record.get("source_name") or "")
        if source_name and "::" not in source_name and "+" not in source_name:
            source_object = doc.getObject(source_name)
            if (
                source_object is not None
                and object_string_property(
                    source_object, "TemplateSetID", ""
                ) == set_id
            ):
                direct_groups.setdefault(source_name, []).append(record)

    direct_keeper_ids = set()
    for source_name, bound_records in direct_groups.items():
        keeper = None
        for candidate in bound_records:
            if candidate.get("category") == EXPORT_CATEGORY_SOLID:
                keeper = candidate
                break
        if keeper is None and bound_records:
            keeper = bound_records[0]
        if keeper is not None:
            direct_keeper_ids.add(str(keeper.get("record_id") or ""))

    source_group = next((
        obj for obj in list(doc.Objects)
        if object_string_property(obj, "GeneratedBy", "") == GENERATOR_ID
        and object_string_property(obj, "TemplateSetID", "") == str(set_id or "")
        and object_string_property(obj, "GeneratedRole", "") == "ProductionSourceGroup"
    ), None)
    materialised = 0
    for record in records:
        source_name = str(record.get("source_name") or "")
        direct_object = (
            doc.getObject(source_name)
            if source_name and "::" not in source_name and "+" not in source_name
            else None
        )
        if (
            direct_object is not None
            and object_string_property(direct_object, "TemplateSetID", "") != set_id
        ):
            direct_object = None
        record_valid, _record_reason = validate_export_record(record)
        direct_shape_valid = False
        if direct_object is not None:
            direct_shape_valid, _direct_reason = validate_export_record({
                "shape": getattr(direct_object, "Shape", None),
                "category": record.get("category"),
            })
        needs_source = (
            bool(record.get("force_production_source", False))
            or direct_object is None
            or str(record.get("record_id") or "") not in direct_keeper_ids
            or (record_valid and not direct_shape_valid)
        )
        if not needs_source:
            record["source_binding_type"] = "direct"
            continue
        valid, _reason = record_valid, _record_reason
        if not valid:
            record["source_binding_type"] = "unbound"
            continue
        if source_group is None:
            group_name = unique_internal_name(
                doc,
                "RailwayProductionSources_{}".format(
                    safe_filename_component(set_id, "SET").replace("-", "_")
                ),
            )
            source_group = doc.addObject("App::DocumentObjectGroup", group_name)
            source_group.Label = "Production Sources [{}]".format(set_id)
            tag_generated_object(source_group, "ProductionSourceGroup", set_id)
            if parent_group is not None:
                parent_group.addObject(source_group)
            if Gui is not None:
                try:
                    source_group.ViewObject.Visibility = False
                except Exception:
                    pass

        record_id = str(record.get("record_id") or "")
        source_object = doc.addObject(
            "Part::Feature",
            unique_internal_name(
                doc,
                "RailwayProductionSource_{}".format(materialised + 1),
            ),
        )
        source_object.Label = "Production Source - {}".format(
            str(record.get("source_label") or record.get("subtype") or record_id)
        )
        source_object.Shape = record["shape"].copy()
        tag_generated_object(source_object, "ProductionSource", set_id)
        if str(record.get("route_id") or "") or str(record.get("route_name") or ""):
            tag_route_metadata(
                source_object,
                record.get("route_id", ""),
                record.get("route_name", ""),
            )
        tag_export_metadata(
            source_object,
            record.get("subtype", ""),
            record.get("category", ""),
            track_number=record.get("track_number", 0),
            platform_number=record.get("platform_number", 0),
            platform_name=record.get("platform_name", ""),
            section_number=record.get("section_number", 0),
            travel_order_number=record.get("travel_order_number", 0),
            section_length=record.get("section_length", 0.0),
            feature_number=record.get("feature_number", 0),
        )
        properties = [
            ensure_property(
                source_object,
                "App::PropertyString",
                PRODUCTION_RECORD_ID_PROPERTY,
                "Production utilities",
                "Stable identity of this one-record production source",
            ),
            ensure_property(
                source_object,
                "App::PropertyString",
                PRODUCTION_RECORD_IDS_PROPERTY,
                "Production utilities",
                "Stable identities represented by this production source",
            ),
            ensure_property(
                source_object,
                "App::PropertyString",
                "SourceGeneratedRole",
                "Production utilities",
                "Original generated role represented by this source",
            ),
            ensure_property(
                source_object,
                "App::PropertyString",
                "SourceSelectionKey",
                "Production utilities",
                "Production selection group represented by this source",
            ),
            ensure_property(
                source_object,
                "App::PropertyString",
                "TrackName",
                "Production export",
                "Generated track name",
            ),
            ensure_property(
                source_object,
                "App::PropertyBool",
                ASSEMBLY_LABEL_DERIVED_PROPERTY,
                "Production utilities",
                "True when this hidden source is derived from optional assembly-label geometry",
            ),
            ensure_property(
                source_object,
                "App::PropertyString",
                ASSEMBLY_LABEL_TARGET_PROPERTY,
                "Production utilities",
                "Semantic production-part key associated with this assembly label",
            ),
        ]
        setattr(source_object, PRODUCTION_RECORD_ID_PROPERTY, record_id)
        setattr(source_object, PRODUCTION_RECORD_IDS_PROPERTY, json.dumps([record_id]))
        source_object.SourceGeneratedRole = str(record.get("role") or "")
        source_object.SourceSelectionKey = str(record.get("selection_key") or "")
        source_object.TrackName = str(record.get("track_name") or "")
        setattr(source_object, ASSEMBLY_LABEL_DERIVED_PROPERTY, bool(record.get("assembly_label_derived", False)))
        setattr(source_object, ASSEMBLY_LABEL_TARGET_PROPERTY, str(record.get("assembly_label_target_key") or ""))
        set_read_only(source_object, properties)
        source_group.addObject(source_object)
        if Gui is not None:
            try:
                source_object.ViewObject.Visibility = False
            except Exception:
                pass
        record["source_name"] = str(source_object.Name)
        record["source_label"] = str(source_object.Label)
        record["source_binding_type"] = "hidden-production-source"
        materialised += 1
    return materialised

def tag_production_record_bindings(doc, set_id, records):
    by_object_name = {}
    for record in records:
        source_name = str(record.get("source_name") or "")
        if not source_name or "::" in source_name or "+" in source_name:
            continue
        obj = doc.getObject(source_name)
        if obj is None:
            continue
        if object_string_property(obj, "TemplateSetID", "") != set_id:
            continue
        by_object_name.setdefault(source_name, []).append(record)

    for source_name, bound_records in by_object_name.items():
        obj = doc.getObject(source_name)
        record_ids = sorted({
            str(record.get("record_id") or "")
            for record in bound_records
            if str(record.get("record_id") or "")
        })
        if not record_ids:
            continue
        properties = [
            ensure_property(
                obj,
                "App::PropertyString",
                PRODUCTION_RECORD_ID_PROPERTY,
                "Production utilities",
                "Stable production-record identity when this object represents one record",
            ),
            ensure_property(
                obj,
                "App::PropertyString",
                PRODUCTION_RECORD_IDS_PROPERTY,
                "Production utilities",
                "All stable production-record identities represented by this object",
            ),
            ensure_property(
                obj,
                "App::PropertyString",
                "TrackName",
                "Production export",
                "Generated track name where the bound records share one track identity",
            ),
        ]
        setattr(
            obj,
            PRODUCTION_RECORD_ID_PROPERTY,
            record_ids[0] if len(record_ids) == 1 else "",
        )
        setattr(obj, PRODUCTION_RECORD_IDS_PROPERTY, json.dumps(record_ids))
        track_names = sorted({
            str(record.get("track_name") or "").strip()
            for record in bound_records
            if str(record.get("track_name") or "").strip()
        })
        obj.TrackName = track_names[0] if len(track_names) == 1 else ""
        set_read_only(obj, properties)


def settings_for_template_set(doc, set_id):
    candidates = [
        obj for obj in list(doc.Objects)
        if is_generated_settings(obj)
        and object_string_property(obj, "TemplateSetID", "") == set_id
    ]
    return candidates[-1] if candidates else None


def generated_template_set_ids(doc):
    set_ids = set()
    for obj in list(doc.Objects):
        if object_string_property(obj, "GeneratedBy", "") != GENERATOR_ID:
            continue
        set_id = object_string_property(obj, "TemplateSetID", "")
        if set_id:
            set_ids.add(set_id)

    def sort_key(value):
        match = re.search(r"([0-9]+)$", str(value))
        return (int(match.group(1)) if match else 10 ** 9, str(value))

    return sorted(set_ids, key=sort_key)


def read_production_record_index(obj):
    stored = object_string_property(obj, PRODUCTION_RECORD_INDEX_PROPERTY, "")
    if not stored:
        return None
    try:
        payload = json.loads(stored)
    except Exception:
        return None
    if not isinstance(payload, dict):
        return None
    records = payload.get("records")
    if not isinstance(records, list):
        return None
    return payload


def _legacy_index_record(obj, set_id, occurrence):
    shape = getattr(obj, "Shape", None)
    length, width, height = _shape_bounding_dimensions(shape)
    role = object_string_property(obj, "GeneratedRole", "")
    subtype = object_string_property(obj, "ExportSubtype", "")
    category = object_string_property(obj, "ExportCategory", "")
    record = {
        "role": role,
        "subtype": subtype,
        "category": category,
        "track_number": _integer_object_property(obj, "TrackNumber"),
        "track_name": object_string_property(obj, "TrackName", ""),
        "platform_number": _integer_object_property(obj, "PlatformNumber"),
        "platform_name": object_string_property(obj, "PlatformName", ""),
        "section_number": _integer_object_property(obj, "SectionNumber"),
        "travel_order_number": _integer_object_property(obj, "TravelOrderNumber"),
        "feature_number": _integer_object_property(obj, "FeatureNumber"),
        "route_id": object_string_property(obj, "RouteID", ""),
        "route_name": object_string_property(obj, "RouteName", ""),
        "source_name": str(getattr(obj, "Name", "")),
        "source_label": str(getattr(obj, "Label", getattr(obj, "Name", ""))),
        "selection_key": "",
    }
    record_id = object_string_property(obj, PRODUCTION_RECORD_ID_PROPERTY, "")
    if not record_id:
        record_id = production_record_identity(record, set_id)
        if occurrence > 1:
            record_id += "|LEGACY{:02d}".format(occurrence)
    metadata_issues = production_record_metadata_issues(record, set_id)
    if not subtype:
        metadata_issues.append("Legacy object has no export subtype")
    if not category:
        metadata_issues.append("Legacy object has no export category")
    valid = not _shape_is_null(shape)
    details = ["Legacy object scan; complete production-record catalogue unavailable"]
    details.extend(metadata_issues)
    if not valid:
        details.append("Missing or null shape")
    return {
        "record_id": record_id,
        "template_set_id": set_id,
        "source_name": record["source_name"],
        "source_label": record["source_label"],
        "source_binding_type": "legacy-object",
        "role": role,
        "subtype": subtype,
        "category": category,
        "selection_key": "",
        "route_id": record["route_id"],
        "route_name": record["route_name"],
        "track_number": record["track_number"],
        "track_name": record["track_name"],
        "platform_number": record["platform_number"],
        "platform_name": record["platform_name"],
        "section_number": record["section_number"],
        "travel_order_number": record["travel_order_number"],
        "feature_number": record["feature_number"],
        "section_length": quantity_value(obj, "SectionLength", 0.0),
        "template_thickness": quantity_value(obj, "TemplateThickness", 0.0),
        "platform_height": quantity_value(obj, "PlatformHeight", 0.0),
        "overall_length": length,
        "overall_width": width,
        "overall_height": height,
        "measurement_classification": "Bounding-box estimate",
        "supported_formats": _supported_formats_for_category(category),
        "geometry_valid": valid,
        "diagnostic_status": "Error" if not valid else "Warning",
        "diagnostic_details": "; ".join(details),
    }


def scan_legacy_production_record_index(doc, set_id):
    records = []
    identity_counts = {}
    excluded_roles = {
        "Group",
        "Settings",
        PRODUCTION_SCHEDULE_ROLE,
        MATERIAL_REPORT_ROLE,
        "ProductionSource",
        "ProductionSourceGroup",
    }
    for obj in list(doc.Objects):
        if object_string_property(obj, "GeneratedBy", "") != GENERATOR_ID:
            continue
        if object_string_property(obj, "TemplateSetID", "") != set_id:
            continue
        role = object_string_property(obj, "GeneratedRole", "")
        if role in excluded_roles:
            continue
        if not hasattr(obj, "Shape"):
            continue
        identity = "{}|{}|{}".format(
            role,
            object_string_property(obj, "ExportSubtype", ""),
            str(getattr(obj, "Name", "")),
        )
        identity_counts[identity] = identity_counts.get(identity, 0) + 1
        records.append(
            _legacy_index_record(obj, set_id, identity_counts[identity])
        )
    return {
        "schema_version": PRODUCTION_RECORD_SCHEMA_VERSION,
        "macro_version": MACRO_VERSION,
        "created_at": datetime.datetime.now().astimezone().isoformat(
            timespec="seconds"
        ),
        "template_set_id": set_id,
        "legacy_scan": True,
        "records": records,
    }


def production_record_index_for_set(doc, set_id):
    settings = settings_for_template_set(doc, set_id)
    payload = read_production_record_index(settings)
    if payload is not None:
        return payload
    return scan_legacy_production_record_index(doc, set_id)


def _format_schedule_number(value):
    try:
        number = float(value)
    except Exception:
        return ""
    if abs(number) <= GEOMETRY_TOLERANCE:
        return ""
    return "{:.3f}".format(number)


def _schedule_record_for_filename(index_record):
    return {
        "role": index_record.get("role", ""),
        "subtype": index_record.get("subtype", ""),
        "category": index_record.get("category", ""),
        "source_name": index_record.get("source_name", ""),
        "source_label": index_record.get("source_label", ""),
        "route_id": index_record.get("route_id", ""),
        "route_name": index_record.get("route_name", ""),
        "track_number": index_record.get("track_number", 0),
        "track_name": index_record.get("track_name", ""),
        "platform_number": index_record.get("platform_number", 0),
        "platform_name": index_record.get("platform_name", ""),
        "section_number": index_record.get("section_number", 0),
        "travel_order_number": index_record.get("travel_order_number", 0),
        "feature_number": index_record.get("feature_number", 0),
        "selection_key": index_record.get("selection_key", ""),
    }


def build_production_schedule_rows(index_payload, export_config, set_id):
    config = clone_production_export_config(export_config)
    output_directory = str(config.get("output_directory") or "").strip()
    selected_formats = config.get("formats", {})
    rows = []
    for index_record in index_payload.get("records", []):
        supported = list(index_record.get("supported_formats") or [])
        configured = [
            key for key in supported if bool(selected_formats.get(key, False))
        ]
        selection_key = str(index_record.get("selection_key") or "")
        selected_output = (
            True if not selection_key
            else bool(config.get("selections", {}).get(selection_key, False))
        )
        filename_record = _schedule_record_for_filename(index_record)
        stem = record_filename_stem(filename_record, config, set_id)
        filenames = ["{}.{}".format(stem, key) for key in configured]
        if not selected_output:
            export_status = "Not selected"
        elif not configured:
            export_status = "No selected compatible format"
        elif not output_directory:
            export_status = "Output folder not configured"
        else:
            existing_count = sum(
                1 for name in filenames
                if os.path.isfile(os.path.join(output_directory, name))
            )
            if existing_count == len(filenames):
                export_status = "Existing"
            elif existing_count:
                export_status = "Partially existing"
            else:
                export_status = "Not exported"
        rows.append({
            "Template-set ID": set_id,
            "Route name": index_record.get("route_name", ""),
            "Route ID": index_record.get("route_id", ""),
            "Track number": index_record.get("track_number") or "",
            "Track name": index_record.get("track_name", ""),
            "Object type": index_record.get("subtype", "") or index_record.get("role", ""),
            "Generated role": index_record.get("role", ""),
            "Platform number": index_record.get("platform_number") or "",
            "Platform name": index_record.get("platform_name", ""),
            "Section number": index_record.get("section_number") or "",
            "Travel-order number": index_record.get("travel_order_number") or "",
            "Overall length (mm)": _format_schedule_number(index_record.get("overall_length", 0.0)),
            "Overall width (mm)": _format_schedule_number(index_record.get("overall_width", 0.0)),
            "Overall height or thickness (mm)": _format_schedule_number(index_record.get("overall_height", 0.0)),
            "Measurement classification": index_record.get("measurement_classification", "Bounding-box estimate"),
            "Export subtype": index_record.get("subtype", ""),
            "Supported export formats": "; ".join(
                EXPORT_FORMAT_LABELS.get(key, str(key).upper()) for key in supported
            ),
            "Configured export formats": "; ".join(
                EXPORT_FORMAT_LABELS.get(key, str(key).upper()) for key in configured
            ),
            "Expected export filenames": "; ".join(filenames),
            "Export status": export_status,
            "Diagnostic status": index_record.get("diagnostic_status", "Information"),
            "Diagnostic details": index_record.get("diagnostic_details", ""),
            "Source object": index_record.get("source_name", ""),
            "Production-record ID": index_record.get("record_id", ""),
        })
    rows.sort(key=lambda row: (
        str(row.get("Route ID") or ""),
        int(row.get("Track number") or 0),
        int(row.get("Platform number") or 0),
        int(row.get("Travel-order number") or 0),
        int(row.get("Section number") or 0),
        str(row.get("Object type") or ""),
        str(row.get("Production-record ID") or ""),
    ))
    return rows


def _spreadsheet_column_name(index):
    value = int(index) + 1
    letters = []
    while value:
        value, remainder = divmod(value - 1, 26)
        letters.append(chr(ord("A") + remainder))
    return "".join(reversed(letters))


def _spreadsheet_text(value):
    text = str(value if value is not None else "")
    if text.startswith("="):
        return "'" + text
    return text


def find_template_set_group(doc, set_id):
    for obj in list(doc.Objects):
        if object_string_property(obj, "GeneratedBy", "") != GENERATOR_ID:
            continue
        if object_string_property(obj, "TemplateSetID", "") != set_id:
            continue
        if object_string_property(obj, "GeneratedRole", "") == "Group":
            return obj
    return None


def create_or_replace_production_schedule(doc, set_id, rows):
    if not isinstance(rows, list):
        raise ValueError("The production schedule rows are invalid.")
    existing = [
        obj for obj in list(doc.Objects)
        if object_string_property(obj, "GeneratedBy", "") == GENERATOR_ID
        and object_string_property(obj, "TemplateSetID", "") == set_id
        and object_string_property(obj, "GeneratedRole", "") == PRODUCTION_SCHEDULE_ROLE
    ]
    transaction_open = False
    try:
        doc.openTransaction(
            "Update Version {} production schedule".format(MACRO_VERSION_NUMBER)
        )
        transaction_open = True
        name = unique_internal_name(
            doc,
            "{}_{}".format(
                PRODUCTION_SCHEDULE_NAME,
                safe_filename_component(set_id, "SET").replace("-", "_"),
            ),
        )
        sheet = doc.addObject("Spreadsheet::Sheet", name)
        sheet.Label = "Production Schedule [{}]".format(set_id)
        tag_generated_object(sheet, PRODUCTION_SCHEDULE_ROLE, set_id)
        properties = [
            ensure_property(
                sheet,
                "App::PropertyInteger",
                "ScheduleSchemaVersion",
                "Production schedule",
                "Production-schedule schema version",
            ),
            ensure_property(
                sheet,
                "App::PropertyString",
                "ScheduleCreatedAt",
                "Production schedule",
                "Date and time when this schedule was created",
            ),
            ensure_property(
                sheet,
                "App::PropertyInteger",
                "ProductionRecordCount",
                "Production schedule",
                "Number of production schedule rows",
            ),
        ]
        sheet.ScheduleSchemaVersion = PRODUCTION_SCHEDULE_SCHEMA_VERSION
        sheet.ScheduleCreatedAt = datetime.datetime.now().astimezone().isoformat(
            timespec="seconds"
        )
        sheet.ProductionRecordCount = len(rows)
        set_read_only(sheet, properties)

        for column_index, field in enumerate(PRODUCTION_SCHEDULE_FIELDS):
            cell = "{}1".format(_spreadsheet_column_name(column_index))
            sheet.set(cell, field)
        for row_index, row in enumerate(rows, start=2):
            for column_index, field in enumerate(PRODUCTION_SCHEDULE_FIELDS):
                cell = "{}{}".format(
                    _spreadsheet_column_name(column_index), row_index
                )
                sheet.set(cell, _spreadsheet_text(row.get(field, "")))
        try:
            last_column = _spreadsheet_column_name(
                len(PRODUCTION_SCHEDULE_FIELDS) - 1
            )
            sheet.setStyle("A1:{}1".format(last_column), "bold", "add")
            sheet.setBackground("A1:{}1".format(last_column), (0.85, 0.85, 0.85))
            sheet.setColumnWidth("A", 120)
            for column_index in range(1, len(PRODUCTION_SCHEDULE_FIELDS)):
                sheet.setColumnWidth(
                    _spreadsheet_column_name(column_index),
                    150 if column_index < 11 else 190,
                )
        except Exception:
            pass

        group = find_template_set_group(doc, set_id)
        if group is not None:
            group.addObject(sheet)
        for old_sheet in existing:
            if old_sheet is sheet:
                continue
            doc.removeObject(old_sheet.Name)
        _document_recompute(doc)
        doc.commitTransaction()
        transaction_open = False
        return sheet
    except Exception:
        if transaction_open:
            try:
                doc.abortTransaction()
            except Exception:
                pass
        raise


def _safe_csv_schedule_value(value):
    text = str(value if value is not None else "")
    if text.startswith(("=", "+", "-", "@")):
        return "'" + text
    return text


def write_production_schedule_csv(path, rows):
    if not rows:
        raise ValueError("The production schedule contains no records.")
    directory = os.path.dirname(os.path.abspath(path))
    if not os.path.isdir(directory):
        raise ValueError("The selected CSV directory does not exist: {}".format(directory))
    temporary_path = _temporary_export_path(path)
    try:
        with open(temporary_path, "w", newline="", encoding="utf-8-sig") as handle:
            writer = csv.DictWriter(
                handle,
                fieldnames=PRODUCTION_SCHEDULE_FIELDS,
                extrasaction="ignore",
                lineterminator="\n",
            )
            writer.writeheader()
            for row in rows:
                writer.writerow({
                    field: _safe_csv_schedule_value(row.get(field, ""))
                    for field in PRODUCTION_SCHEDULE_FIELDS
                })
        if not os.path.isfile(temporary_path) or os.path.getsize(temporary_path) <= 0:
            raise ValueError("The production schedule CSV contained no data.")
        os.replace(temporary_path, path)
    except Exception:
        if os.path.exists(temporary_path):
            try:
                os.remove(temporary_path)
            except Exception:
                pass
        raise


class ProductionScheduleDialog(QtWidgets.QDialog):
    def __init__(self, doc, parent=None):
        super(ProductionScheduleDialog, self).__init__(parent)
        self.doc = doc
        self.rows = []
        self.index_payload = None
        self.setWindowTitle(versioned_dialog_title("Production schedule"))
        self.resize(1500, 760)

        layout = QtWidgets.QVBoxLayout(self)
        top_layout = QtWidgets.QHBoxLayout()
        top_layout.addWidget(QtWidgets.QLabel("Template set:"))
        self.set_box = QtWidgets.QComboBox()
        self.set_box.addItems(generated_template_set_ids(doc))
        top_layout.addWidget(self.set_box)
        self.refresh_button = QtWidgets.QPushButton("Refresh preview")
        top_layout.addWidget(self.refresh_button)
        top_layout.addStretch(1)
        layout.addLayout(top_layout)

        self.summary_label = QtWidgets.QLabel("")
        self.summary_label.setWordWrap(True)
        layout.addWidget(self.summary_label)

        self.table = QtWidgets.QTableWidget(0, len(PRODUCTION_SCHEDULE_FIELDS))
        self.table.setHorizontalHeaderLabels(PRODUCTION_SCHEDULE_FIELDS)
        try:
            self.table.setEditTriggers(
                QtWidgets.QAbstractItemView.NoEditTriggers
            )
            self.table.setSelectionBehavior(
                QtWidgets.QAbstractItemView.SelectRows
            )
        except AttributeError:
            self.table.setEditTriggers(
                QtWidgets.QAbstractItemView.EditTrigger.NoEditTriggers
            )
            self.table.setSelectionBehavior(
                QtWidgets.QAbstractItemView.SelectionBehavior.SelectRows
            )
        self.table.setAlternatingRowColors(True)
        self.table.setSortingEnabled(False)
        layout.addWidget(self.table, 1)

        button_layout = QtWidgets.QHBoxLayout()
        self.update_sheet_button = QtWidgets.QPushButton("Update FreeCAD schedule")
        self.export_csv_button = QtWidgets.QPushButton("Export CSV...")
        close_button = QtWidgets.QPushButton("Close")
        button_layout.addWidget(self.update_sheet_button)
        button_layout.addWidget(self.export_csv_button)
        button_layout.addStretch(1)
        button_layout.addWidget(close_button)
        layout.addLayout(button_layout)

        self.set_box.currentIndexChanged.connect(self.refresh_preview)
        self.refresh_button.clicked.connect(self.refresh_preview)
        self.update_sheet_button.clicked.connect(self.update_freecad_schedule)
        self.export_csv_button.clicked.connect(self.export_csv)
        close_button.clicked.connect(self.accept)

        if self.set_box.count() > 0:
            selected_set = ""
            if Gui is not None:
                try:
                    for obj in reversed(Gui.Selection.getSelection()):
                        candidate = object_string_property(obj, "TemplateSetID", "")
                        if candidate:
                            selected_set = candidate
                            break
                except Exception:
                    pass
            if selected_set:
                index = self.set_box.findText(selected_set)
                if index >= 0:
                    self.set_box.setCurrentIndex(index)
            self.refresh_preview()
        else:
            self.summary_label.setText(
                "No recognised generated template sets exist in this document."
            )
            self.update_sheet_button.setEnabled(False)
            self.export_csv_button.setEnabled(False)

    def current_set_id(self):
        return str(self.set_box.currentText()).strip()

    def refresh_preview(self, *_args):
        set_id = self.current_set_id()
        if not set_id:
            self.rows = []
            self.table.setRowCount(0)
            return
        try:
            self.index_payload = production_record_index_for_set(self.doc, set_id)
            settings = settings_for_template_set(self.doc, set_id)
            export_config = read_production_export_config(settings)
            self.rows = build_production_schedule_rows(
                self.index_payload, export_config, set_id
            )
            self.table.setSortingEnabled(False)
            self.table.setRowCount(len(self.rows))
            for row_index, row in enumerate(self.rows):
                for column_index, field in enumerate(PRODUCTION_SCHEDULE_FIELDS):
                    item = QtWidgets.QTableWidgetItem(str(row.get(field, "")))
                    self.table.setItem(row_index, column_index, item)
            for column_index in range(len(PRODUCTION_SCHEDULE_FIELDS)):
                self.table.setColumnWidth(
                    column_index, 125 if column_index < 11 else 180
                )
            self.table.setSortingEnabled(True)
            warning_count = sum(
                1 for row in self.rows
                if row.get("Diagnostic status") == "Warning"
            )
            error_count = sum(
                1 for row in self.rows
                if row.get("Diagnostic status") == "Error"
            )
            legacy_text = (
                " Legacy metadata scan used; regenerate deliberately with Version {} "
                "to create the complete persistent catalogue.".format(MACRO_VERSION_NUMBER)
                if self.index_payload.get("legacy_scan", False)
                else ""
            )
            self.summary_label.setText(
                "{} recognised production records; {} warning(s); {} error(s).{}".format(
                    len(self.rows), warning_count, error_count, legacy_text
                )
            )
            self.update_sheet_button.setEnabled(bool(self.rows))
            self.export_csv_button.setEnabled(bool(self.rows))
        except Exception as error:
            self.rows = []
            self.table.setRowCount(0)
            self.summary_label.setText("Schedule preview failed: {}".format(error))
            self.update_sheet_button.setEnabled(False)
            self.export_csv_button.setEnabled(False)

    def update_freecad_schedule(self):
        if not self.rows:
            return
        try:
            sheet = create_or_replace_production_schedule(
                self.doc, self.current_set_id(), self.rows
            )
            QtWidgets.QMessageBox.information(
                self,
                versioned_dialog_title("Production schedule updated"),
                "Created {} with {} production records. Existing railway geometry was not changed.".format(
                    str(getattr(sheet, "Label", "Production Schedule")),
                    len(self.rows),
                ),
            )
        except Exception as error:
            QtWidgets.QMessageBox.critical(
                self,
                versioned_dialog_title("Production schedule error"),
                str(error),
            )

    def export_csv(self):
        if not self.rows:
            return
        set_id = self.current_set_id()
        settings = settings_for_template_set(self.doc, set_id)
        export_config = read_production_export_config(settings)
        directory = str(export_config.get("output_directory") or "").strip()
        if not directory or not os.path.isdir(directory):
            directory = os.path.expanduser("~")
        suggested = os.path.join(
            directory,
            "{}_{}_Production_Schedule.csv".format(
                safe_filename_component(set_id, "SET"),
                safe_filename_component(MACRO_VERSION_NUMBER, "Version"),
            ),
        )
        selection = QtWidgets.QFileDialog.getSaveFileName(
            self,
            versioned_dialog_title("Export production schedule CSV"),
            suggested,
            "CSV files (*.csv)",
        )
        selected = selection[0] if isinstance(selection, (tuple, list)) else selection
        if not selected:
            return
        path = str(selected)
        if not path.lower().endswith(".csv"):
            path += ".csv"
        try:
            write_production_schedule_csv(path, self.rows)
            QtWidgets.QMessageBox.information(
                self,
                versioned_dialog_title("Production schedule exported"),
                "Production schedule CSV written to:\n{}".format(path),
            )
        except Exception as error:
            QtWidgets.QMessageBox.critical(
                self,
                versioned_dialog_title("Production schedule CSV error"),
                str(error),
            )



def _project_open_record_shape_to_xy(shape, description):
    """Project display wires to Z=0 without changing the document object.

    Closed wire topology is retained for timber outlines. Open rail, centreline,
    label and datum records remain open. The routine is deliberately limited to
    lightweight production-export copies; it never mutates generated geometry.
    """
    if _shape_is_null(shape):
        return None
    sequences = []
    try:
        wires = list(shape.Wires)
    except Exception:
        wires = []
    if wires:
        candidates = wires
    else:
        try:
            edges = list(shape.Edges)
        except Exception:
            edges = []
        candidates = edges if edges else [shape]
    for candidate in candidates:
        try:
            vertices = list(candidate.OrderedVertexes)
        except Exception:
            try:
                vertices = list(candidate.Vertexes)
            except Exception:
                vertices = []
        points = []
        for vertex in vertices:
            try:
                point = vertex.Point
                projected = vector_xy(float(point.x), float(point.y))
            except Exception:
                continue
            if not points or _xy_distance(points[-1], projected) > 1.0e-7:
                points.append(projected)
        if len(points) < 2:
            continue
        closed = False
        try:
            closed = bool(candidate.isClosed())
        except Exception:
            closed = (
                len(points) > 2
                and _xy_distance(points[0], points[-1]) <= 1.0e-7
            )
        if closed and _xy_distance(points[0], points[-1]) > 1.0e-7:
            points.append(points[0])
        wire = Part.makePolygon(points)
        if not wire.isNull():
            sequences.append(wire)
    if not sequences:
        raise ValueError("{} could not be projected to a usable XY wire.".format(description))
    if len(sequences) == 1:
        return sequences[0]
    compound = Part.makeCompound(sequences)
    if compound.isNull():
        raise ValueError("{} could not be combined after XY projection.".format(description))
    return compound


def _hydrated_production_record_shape(record, source_shape):
    """Return the safe persisted export shape for a production record."""
    if _shape_is_null(source_shape):
        return None
    try:
        candidate = source_shape.copy()
    except Exception:
        candidate = source_shape
    valid, _reason = validate_export_record({
        "shape": candidate,
        "category": record.get("category"),
    })
    if valid:
        return candidate
    subtype = str(record.get("subtype") or "")
    category = str(record.get("category") or "")
    projection_descriptions = {
        "PlatformEdge": (
            "platform edge",
            "Projected sloped platform display edge to XY engraving geometry",
        ),
        "CrossoverRailGeometry": (
            "managed crossover rail geometry",
            "Projected managed crossover rail display geometry to XY engraving geometry",
        ),
        "CrossoverConstructionMarks": (
            "managed crossover construction marks",
            "Projected managed crossover construction marks to XY engraving geometry",
        ),
        "TurnoutRailGeometry": (
            "turnout rail and centreline references",
            "Projected turnout rail display geometry to XY engraving geometry",
        ),
        "TurnoutTimberGeometry": (
            "turnout timber outlines",
            "Projected turnout timber outlines to XY engraving geometry",
        ),
        "TurnoutTimberCentres": (
            "turnout timber centre lines",
            "Projected turnout timber centre lines to XY engraving geometry",
        ),
        "TurnoutTimberLabels": (
            "turnout timber labels",
            "Projected turnout timber labels to XY engraving geometry",
        ),
        "TurnoutConstructionMarks": (
            "turnout construction marks",
            "Projected turnout construction marks to XY engraving geometry",
        ),
    }
    if subtype in projection_descriptions and category == EXPORT_CATEGORY_ENGRAVING:
        description, repair_note = projection_descriptions[subtype]
        projected = _project_open_record_shape_to_xy(
            source_shape,
            str(record.get("source_label") or record.get("source_name") or description),
        )
        projected_valid, projected_reason = validate_export_record({
            "shape": projected,
            "category": EXPORT_CATEGORY_ENGRAVING,
        })
        if not projected_valid:
            raise ValueError(
                "The {} XY projection is not exportable: {}".format(
                    description, projected_reason
                )
            )
        record["hydration_repair"] = repair_note
        return projected
    return candidate


def hydrate_production_index_records(doc, index_payload):
    """Attach current document shapes to metadata-only production records."""
    hydrated = []
    for stored in index_payload.get("records", []):
        record = dict(stored)
        source_name = str(record.get("source_name") or "")
        source_object = None
        if source_name and "::" not in source_name and "+" not in source_name:
            source_object = doc.getObject(source_name)
        shape = getattr(source_object, "Shape", None) if source_object is not None else None
        try:
            record["shape"] = _hydrated_production_record_shape(record, shape)
        except Exception as error:
            record["shape"] = None
            record["hydration_error"] = str(error)
        hydrated.append(record)
    return hydrated


def _shape_exact_length(shape):
    if _shape_is_null(shape):
        return 0.0
    try:
        return max(0.0, float(shape.Length))
    except Exception:
        total = 0.0
        try:
            for edge in shape.Edges:
                total += max(0.0, float(edge.Length))
        except Exception:
            return 0.0
        return total


def _shape_exact_volume(shape):
    if _shape_is_null(shape):
        return 0.0
    try:
        return max(0.0, float(shape.Volume))
    except Exception:
        total = 0.0
        try:
            for solid in shape.Solids:
                total += max(0.0, float(solid.Volume))
        except Exception:
            return 0.0
        return total


def _shape_horizontal_plan_area(shape, tolerance=0.001):
    if _shape_is_null(shape):
        return 0.0
    groups = {}
    try:
        faces = list(shape.Faces)
    except Exception:
        faces = []
    for face in faces:
        z_value = _horizontal_face_z(face, tolerance)
        try:
            area = float(face.Area)
        except Exception:
            area = 0.0
        if z_value is None or area <= GEOMETRY_TOLERANCE:
            continue
        key = int(round(float(z_value) / max(float(tolerance), 1.0e-6)))
        groups[key] = groups.get(key, 0.0) + area
    return max(groups.values()) if groups else 0.0


def _shape_planar_profile_area(shape):
    if _shape_is_null(shape) or not shape_is_planar_xy(shape):
        return 0.0
    try:
        wires = [wire.copy() for wire in shape.Wires if wire.isClosed()]
    except Exception:
        wires = []
    if not wires:
        return 0.0
    try:
        maker = getattr(Part, "makeFace", None)
        if callable(maker):
            face = maker(wires, "Part::FaceMakerBullseye")
            area = float(face.Area)
            if area > GEOMETRY_TOLERANCE:
                return area
    except Exception:
        pass
    if len(wires) == 1:
        try:
            area = float(Part.Face(wires[0]).Area)
            if area > GEOMETRY_TOLERANCE:
                return area
        except Exception:
            pass
    return 0.0


def measure_record_plan_area(record):
    shape = record.get("shape")
    horizontal_area = _shape_horizontal_plan_area(shape)
    if horizontal_area > GEOMETRY_TOLERANCE:
        return horizontal_area, MEASUREMENT_EXACT, "Horizontal FreeCAD face area"
    profile_area = _shape_planar_profile_area(shape)
    if profile_area > GEOMETRY_TOLERANCE:
        return profile_area, MEASUREMENT_EXACT, "Closed planar FreeCAD profile area"
    length, width, _height = _shape_bounding_dimensions(shape)
    if length > GEOMETRY_TOLERANCE and width > GEOMETRY_TOLERANCE:
        return (
            length * width,
            MEASUREMENT_BOUNDING_BOX,
            "Overall XY bounding rectangle",
        )
    return 0.0, MEASUREMENT_BOUNDING_BOX, "No measurable plan area"


def _material_family(record):
    subtype = str(record.get("subtype") or "")
    if subtype.startswith("TrackTemplate"):
        return "Track template"
    if subtype.startswith("Platform"):
        return "Platform"
    if subtype.startswith("Formation"):
        return "Formation board"
    return ""


def _record_route_token(record):
    return str(record.get("route_id") or "CURVE")


def _material_scope_key(record, family):
    route = _record_route_token(record)
    if family == "Platform":
        return (
            route,
            int(record.get("platform_number") or 0),
            str(record.get("platform_name") or ""),
        )
    return (route,)


def _material_part_key(record, family):
    route = _record_route_token(record)
    section = int(record.get("section_number") or 0)
    if family == "Track template":
        return (route, int(record.get("track_number") or 0), section)
    if family == "Platform":
        return (
            route,
            int(record.get("platform_number") or 0),
            str(record.get("platform_name") or ""),
            section,
        )
    return (route, section)


def _is_section_material_record(record, family):
    subtype = str(record.get("subtype") or "")
    section = int(record.get("section_number") or 0)
    if section <= 0:
        return False
    if family == "Track template":
        return subtype == "TrackTemplateSection" or (
            subtype == "TrackTemplateCrossoverIntegrated" and section > 0
        )
    if family == "Platform":
        return subtype in ("PlatformSection", "PlatformSectionOutline")
    if family == "Formation board":
        return subtype in ("FormationSectionBody", "FormationSectionPerimeter")
    return False


def _is_complete_material_record(record, family):
    subtype = str(record.get("subtype") or "")
    if family == "Track template":
        return subtype == "TrackTemplateCompound" or (
            subtype == "TrackTemplateCrossoverIntegrated"
            and int(record.get("section_number") or 0) <= 0
        )
    if family == "Platform":
        return subtype in ("PlatformBody", "PlatformPlanOutline")
    if family == "Formation board":
        return subtype in ("FormationBody", "FormationPerimeter")
    return False


def _preferred_material_record(records):
    usable = [record for record in records if not _shape_is_null(record.get("shape"))]
    if not usable:
        return None
    usable.sort(key=lambda record: (
        0 if record.get("category") == EXPORT_CATEGORY_SOLID else 1,
        0 if record.get("category") == EXPORT_CATEGORY_CUTTING else 1,
        str(record.get("record_id") or ""),
    ))
    return usable[0]


def select_physical_material_parts(records):
    """Choose one physical representation per part without double-counting outputs."""
    selected = []
    for family in ("Track template", "Platform", "Formation board"):
        family_records = [
            record for record in records
            if _material_family(record) == family
            and record.get("category") in (EXPORT_CATEGORY_SOLID, EXPORT_CATEGORY_CUTTING)
        ]
        scopes = {}
        for record in family_records:
            scopes.setdefault(_material_scope_key(record, family), []).append(record)
        for _scope, scope_records in scopes.items():
            section_records = [
                record for record in scope_records
                if _is_section_material_record(record, family)
            ]
            if section_records:
                grouped = {}
                for record in section_records:
                    grouped.setdefault(
                        _material_part_key(record, family), []
                    ).append(record)
                candidates = [
                    _preferred_material_record(group)
                    for group in grouped.values()
                ]
            else:
                complete_records = [
                    record for record in scope_records
                    if _is_complete_material_record(record, family)
                ]
                candidates = [_preferred_material_record(complete_records)]
            for record in candidates:
                if record is None:
                    continue
                copied = dict(record)
                copied["material_family"] = family
                selected.append(copied)
    selected.sort(key=lambda record: (
        str(record.get("material_family") or ""),
        _record_route_token(record),
        int(record.get("track_number") or 0),
        int(record.get("platform_number") or 0),
        int(record.get("section_number") or 0),
        str(record.get("record_id") or ""),
    ))
    return selected


def _record_material_thickness(record, config, settings=None):
    _length, _width, height = _shape_bounding_dimensions(record.get("shape"))
    if height > GEOMETRY_TOLERANCE:
        return height
    family = str(record.get("material_family") or _material_family(record))
    if family == "Track template":
        thickness = float(record.get("template_thickness") or 0.0)
        if thickness > GEOMETRY_TOLERANCE:
            return thickness
    if family == "Platform":
        thickness = float(record.get("platform_height") or 0.0)
        if thickness > GEOMETRY_TOLERANCE:
            return thickness
    if family == "Formation board":
        try:
            thickness = float(read_formation_config(settings).get("board_thickness") or 0.0)
        except Exception:
            thickness = 0.0
        if thickness > GEOMETRY_TOLERANCE:
            return thickness
    configured = float(config.get("material_thickness") or 0.0)
    return configured if configured > GEOMETRY_TOLERANCE else 0.0


def _format_report_value(value, decimals=3):
    try:
        number = float(value)
    except Exception:
        return str(value if value is not None else "")
    if abs(number - round(number)) <= 1.0e-9 and decimals == 0:
        return str(int(round(number)))
    return ("{:.%df}" % int(decimals)).format(number)


def _material_report_row(
    set_id,
    section,
    metric,
    value,
    unit,
    classification,
    method,
    records=None,
    route_name="",
    route_id="",
    track_number=0,
    track_name="",
    platform_number=0,
    platform_name="",
    part_count=0,
    notes="",
    decimals=3,
):
    source_records = list(records or [])
    ids = [
        str(record.get("record_id") or "")
        for record in source_records
        if str(record.get("record_id") or "")
    ]
    return {
        "Template-set ID": str(set_id or ""),
        "Report section": str(section or ""),
        "Metric": str(metric or ""),
        "Route name": str(route_name or ""),
        "Route ID": str(route_id or ""),
        "Track number": int(track_number) if int(track_number or 0) > 0 else "",
        "Track name": str(track_name or ""),
        "Platform number": int(platform_number) if int(platform_number or 0) > 0 else "",
        "Platform name": str(platform_name or ""),
        "Value": _format_report_value(value, decimals),
        "Unit": str(unit or ""),
        "Measurement classification": str(classification or ""),
        "Calculation method": str(method or ""),
        "Part count": int(part_count or 0) if int(part_count or 0) > 0 else "",
        "Source-record count": len(source_records) if source_records else "",
        "Source production-record IDs": "; ".join(ids),
        "Notes": str(notes or ""),
    }


def _aggregate_area(records):
    total = 0.0
    methods = []
    exact = True
    measured = []
    for record in records:
        value, classification, method = measure_record_plan_area(record)
        if value <= GEOMETRY_TOLERANCE:
            exact = False
            continue
        total += value
        measured.append(record)
        methods.append(method)
        if classification != MEASUREMENT_EXACT:
            exact = False
    classification = MEASUREMENT_EXACT if exact and measured else MEASUREMENT_BOUNDING_BOX
    return total, classification, "; ".join(sorted(set(methods))), measured


def _platform_length_measurements(records, settings):
    groups = {}
    platform_configs = read_platform_configs(settings)
    platform_records = [
        record for record in records if _material_family(record) == "Platform"
    ]
    for record in platform_records:
        key = (
            _record_route_token(record),
            int(record.get("platform_number") or 0),
            str(record.get("platform_name") or ""),
        )
        groups.setdefault(key, []).append(record)
    edge_groups = {}
    for record in records:
        if str(record.get("subtype") or "") != "PlatformEdge":
            continue
        key = (
            _record_route_token(record),
            int(record.get("platform_number") or 0),
            str(record.get("platform_name") or ""),
        )
        edge_groups.setdefault(key, []).append(record)
    results = []
    for key, source_records in sorted(groups.items()):
        route_token, platform_number, platform_name = key
        route_id = "" if route_token == "CURVE" else route_token
        route_name = str(source_records[0].get("route_name") or "")
        value = 0.0
        classification = MEASUREMENT_BOUNDING_BOX
        method = "Longest platform-part bounding dimension"
        if route_token == "CURVE" and platform_number > 0 and platform_number <= len(platform_configs):
            configured = float(
                platform_configs[platform_number - 1].get("platform_length") or 0.0
            )
            if configured > GEOMETRY_TOLERANCE:
                value = configured
                classification = MEASUREMENT_EXACT
                method = "Stored generated platform length"
        if value <= GEOMETRY_TOLERANCE:
            edges = edge_groups.get(key, [])
            edge_lengths = [
                _shape_exact_length(record.get("shape")) for record in edges
            ]
            edge_lengths = [item for item in edge_lengths if item > GEOMETRY_TOLERANCE]
            if edge_lengths:
                value = sum(edge_lengths) / float(len(edge_lengths))
                classification = MEASUREMENT_EXACT
                method = "Mean generated platform-edge length"
                source_records = edges
        if value <= GEOMETRY_TOLERANCE:
            dimensions = [
                _shape_bounding_dimensions(record.get("shape"))[0]
                for record in source_records
            ]
            value = max(dimensions) if dimensions else 0.0
        results.append({
            "route_id": route_id,
            "route_name": route_name,
            "platform_number": platform_number,
            "platform_name": platform_name,
            "value": value,
            "classification": classification,
            "method": method,
            "records": source_records,
        })
    return results


def _sheet_part_orientations(width, length, allow_rotation):
    options = [(float(width), float(length))]
    if allow_rotation and abs(float(width) - float(length)) > GEOMETRY_TOLERANCE:
        options.append((float(length), float(width)))
    return options


def _estimate_rectangular_sheet_group(parts, config):
    sheet_width = float(config["sheet_width"])
    sheet_length = float(config["sheet_length"])
    margin = float(config["usable_edge_margin"])
    usable_width = sheet_width - 2.0 * margin
    usable_length = sheet_length - 2.0 * margin
    clearance = float(config["kerf_allowance"]) + float(config["part_spacing"])
    allow_rotation = bool(config["allow_rotation"])
    prepared = []
    oversize = []
    for part in parts:
        length, width, _height = _shape_bounding_dimensions(part.get("shape"))
        if length <= GEOMETRY_TOLERANCE or width <= GEOMETRY_TOLERANCE:
            oversize.append(part)
            continue
        prepared.append({
            "record": part,
            "raw_width": width,
            "raw_length": length,
            "width": width + clearance,
            "length": length + clearance,
            "area": width * length,
        })
    prepared.sort(key=lambda item: (
        -max(item["width"], item["length"]),
        -(item["width"] * item["length"]),
        str(item["record"].get("record_id") or ""),
    ))
    sheets = []

    def place_on_sheet(sheet, item):
        for shelf in sheet["shelves"]:
            for width, length in _sheet_part_orientations(
                item["width"], item["length"], allow_rotation
            ):
                if (
                    length <= shelf["height"] + GEOMETRY_TOLERANCE
                    and shelf["used_width"] + width <= usable_width + GEOMETRY_TOLERANCE
                ):
                    shelf["used_width"] += width
                    shelf["items"].append(item)
                    return True
        used_length = sum(shelf["height"] for shelf in sheet["shelves"])
        candidates = []
        for width, length in _sheet_part_orientations(
            item["width"], item["length"], allow_rotation
        ):
            if width <= usable_width + GEOMETRY_TOLERANCE and used_length + length <= usable_length + GEOMETRY_TOLERANCE:
                candidates.append((length, width))
        if not candidates:
            return False
        length, width = min(candidates, key=lambda candidate: (candidate[0], candidate[1]))
        sheet["shelves"].append({
            "height": length,
            "used_width": width,
            "items": [item],
        })
        return True

    for item in prepared:
        fits_empty = any(
            width <= usable_width + GEOMETRY_TOLERANCE
            and length <= usable_length + GEOMETRY_TOLERANCE
            for width, length in _sheet_part_orientations(
                item["width"], item["length"], allow_rotation
            )
        )
        if not fits_empty:
            oversize.append(item["record"])
            continue
        placed = False
        for sheet in sheets:
            if place_on_sheet(sheet, item):
                placed = True
                break
        if not placed:
            sheet = {"shelves": []}
            if not place_on_sheet(sheet, item):
                oversize.append(item["record"])
                continue
            sheets.append(sheet)
    raw_area = sum(item["area"] for item in prepared if item["record"] not in oversize)
    usable_sheet_area = usable_width * usable_length
    occupancy = (
        100.0 * raw_area / (len(sheets) * usable_sheet_area)
        if sheets and usable_sheet_area > GEOMETRY_TOLERANCE
        else 0.0
    )
    return {
        "sheet_count": len(sheets),
        "oversize": oversize,
        "raw_area": raw_area,
        "usable_sheet_area": usable_sheet_area,
        "occupancy": occupancy,
        "usable_width": usable_width,
        "usable_length": usable_length,
    }


def build_material_report_rows(doc, index_payload, settings, config, set_id):
    config = validate_material_report_config(config)
    records = hydrate_production_index_records(doc, index_payload)
    if not records:
        raise ValueError("The selected template set has no recognised production records.")
    rows = []
    setting_rows = (
        ("Sheet width", config["sheet_width"], "mm"),
        ("Sheet length", config["sheet_length"], "mm"),
        ("Usable edge margin", config["usable_edge_margin"], "mm"),
        ("Kerf allowance", config["kerf_allowance"], "mm"),
        ("Material thickness filter", config["material_thickness"], "mm"),
        ("Preferred part spacing", config["part_spacing"], "mm"),
        ("Allow rectangular rotation", "Yes" if config["allow_rotation"] else "No", ""),
    )
    for metric, value, unit in setting_rows:
        rows.append(_material_report_row(
            set_id, "Sheet settings", metric, value, unit,
            MEASUREMENT_CONFIGURED, "User-configured report setting",
            decimals=3 if isinstance(value, (int, float)) else 0,
        ))

    unavailable = [record for record in records if _shape_is_null(record.get("shape"))]
    if unavailable:
        rows.append(_material_report_row(
            set_id,
            "Diagnostics",
            "Records without readable source geometry",
            len(unavailable),
            "records",
            MEASUREMENT_BOUNDING_BOX,
            "Production-record source binding check",
            records=unavailable,
            notes="These records were excluded from geometric totals.",
            decimals=0,
        ))

    centreline_records = [
        record for record in records
        if str(record.get("subtype") or "") == "TrackCentreline"
        and not _shape_is_null(record.get("shape"))
    ]
    centreline_groups = {}
    for record in centreline_records:
        key = (
            _record_route_token(record),
            int(record.get("track_number") or 0),
            str(record.get("track_name") or ""),
        )
        centreline_groups.setdefault(key, []).append(record)
    total_centreline = 0.0
    for key, group in sorted(centreline_groups.items()):
        route_token, track_number, track_name = key
        value = sum(_shape_exact_length(record.get("shape")) for record in group)
        total_centreline += value
        first = group[0]
        rows.append(_material_report_row(
            set_id,
            "Centreline lengths",
            "Centreline length by track",
            value,
            "mm",
            MEASUREMENT_EXACT,
            "FreeCAD edge length",
            records=group,
            route_name=first.get("route_name", ""),
            route_id="" if route_token == "CURVE" else route_token,
            track_number=track_number,
            track_name=track_name,
        ))
    rows.append(_material_report_row(
        set_id,
        "Centreline lengths",
        "Total centreline length",
        total_centreline,
        "mm",
        MEASUREMENT_EXACT,
        "Sum of generated track-centreline edge lengths",
        records=centreline_records,
    ))

    parts = select_physical_material_parts(records)
    family_parts = {
        family: [part for part in parts if part.get("material_family") == family]
        for family in ("Track template", "Platform", "Formation board")
    }

    area_metric = {
        "Track template": "Template area",
        "Platform": "Platform area",
        "Formation board": "Formation-board area",
    }
    total_areas = {}
    for family, selected_parts in family_parts.items():
        grouped = {}
        for part in selected_parts:
            scope = _material_scope_key(part, family)
            grouped.setdefault(scope, []).append(part)
        family_total = 0.0
        family_exact = True
        family_measured = []
        for scope, group in sorted(grouped.items(), key=lambda item: str(item[0])):
            value, classification, method, measured = _aggregate_area(group)
            family_total += value
            family_measured.extend(measured)
            if classification != MEASUREMENT_EXACT:
                family_exact = False
            first = group[0]
            rows.append(_material_report_row(
                set_id,
                "Areas",
                area_metric[family],
                value,
                "mm^2",
                classification,
                method,
                records=measured or group,
                route_name=first.get("route_name", ""),
                route_id=first.get("route_id", ""),
                platform_number=first.get("platform_number", 0) if family == "Platform" else 0,
                platform_name=first.get("platform_name", "") if family == "Platform" else "",
                part_count=len(group),
            ))
        total_areas[family] = family_total
        if len(grouped) > 1:
            rows.append(_material_report_row(
                set_id,
                "Areas",
                "Total {}".format(area_metric[family].lower()),
                family_total,
                "mm^2",
                MEASUREMENT_EXACT if family_exact and family_measured else MEASUREMENT_BOUNDING_BOX,
                "Sum of selected physical-part areas",
                records=family_measured,
                part_count=len(selected_parts),
            ))

    platform_lengths = _platform_length_measurements(records, settings)
    total_platform_length = 0.0
    all_platform_exact = True
    platform_length_records = []
    for item in platform_lengths:
        total_platform_length += item["value"]
        platform_length_records.extend(item["records"])
        if item["classification"] != MEASUREMENT_EXACT:
            all_platform_exact = False
        rows.append(_material_report_row(
            set_id,
            "Platform lengths",
            "Platform length",
            item["value"],
            "mm",
            item["classification"],
            item["method"],
            records=item["records"],
            route_name=item["route_name"],
            route_id=item["route_id"],
            platform_number=item["platform_number"],
            platform_name=item["platform_name"],
        ))
    if platform_lengths:
        rows.append(_material_report_row(
            set_id,
            "Platform lengths",
            "Total platform length",
            total_platform_length,
            "mm",
            MEASUREMENT_EXACT if all_platform_exact else MEASUREMENT_BOUNDING_BOX,
            "Sum of individual platform lengths",
            records=platform_length_records,
        ))

    template_section_keys = {
        (_record_route_token(record), int(record.get("track_number") or 0), int(record.get("section_number") or 0))
        for record in records
        if str(record.get("subtype") or "") in ("TrackTemplateSection", "TrackTemplateCrossoverIntegrated")
        and int(record.get("section_number") or 0) > 0
    }
    platform_section_keys = {
        (_record_route_token(record), int(record.get("platform_number") or 0), int(record.get("section_number") or 0))
        for record in records
        if str(record.get("subtype") or "") in ("PlatformSection", "PlatformSectionOutline")
        and int(record.get("section_number") or 0) > 0
    }
    formation_section_keys = {
        (_record_route_token(record), int(record.get("section_number") or 0))
        for record in records
        if str(record.get("subtype") or "") in ("FormationSectionBody", "FormationSectionPerimeter")
        and int(record.get("section_number") or 0) > 0
    }
    for metric, count in (
        ("Number of template sections", len(template_section_keys)),
        ("Number of platform sections", len(platform_section_keys)),
        ("Number of formation-board sections", len(formation_section_keys)),
    ):
        rows.append(_material_report_row(
            set_id,
            "Part counts",
            metric,
            count,
            "parts",
            MEASUREMENT_EXACT,
            "Unique route, object and section identities",
            decimals=0,
        ))

    total_volume = 0.0
    volume_records = []
    for family, selected_parts in family_parts.items():
        solids = [
            part for part in selected_parts
            if part.get("category") == EXPORT_CATEGORY_SOLID
            and _shape_exact_volume(part.get("shape")) > GEOMETRY_TOLERANCE
        ]
        volume = sum(_shape_exact_volume(part.get("shape")) for part in solids)
        if volume <= GEOMETRY_TOLERANCE:
            continue
        total_volume += volume
        volume_records.extend(solids)
        rows.append(_material_report_row(
            set_id,
            "Solid volumes",
            "{} solid volume".format(family),
            volume,
            "mm^3",
            MEASUREMENT_EXACT,
            "FreeCAD solid volume",
            records=solids,
            part_count=len(solids),
        ))
    if volume_records:
        rows.append(_material_report_row(
            set_id,
            "Solid volumes",
            "Total available solid volume",
            total_volume,
            "mm^3",
            MEASUREMENT_EXACT,
            "Sum of deduplicated physical solid-part volumes",
            records=volume_records,
            part_count=len(volume_records),
        ))

    target_thickness = float(config.get("material_thickness") or 0.0)
    thickness_groups = {}
    sheet_candidates = []
    filtered_out = []
    for part in parts:
        thickness = _record_material_thickness(part, config, settings)
        if target_thickness > GEOMETRY_TOLERANCE:
            tolerance = max(0.05, 0.02 * target_thickness)
            if thickness > GEOMETRY_TOLERANCE and abs(thickness - target_thickness) > tolerance:
                filtered_out.append(part)
                continue
            thickness = target_thickness
        key = round(thickness, 3) if thickness > GEOMETRY_TOLERANCE else 0.0
        thickness_groups.setdefault(key, []).append(part)
        sheet_candidates.append(part)

    total_sheets = 0
    all_oversize = []
    for thickness, group in sorted(thickness_groups.items()):
        estimate = _estimate_rectangular_sheet_group(group, config)
        total_sheets += estimate["sheet_count"]
        all_oversize.extend(estimate["oversize"])
        families = sorted({str(part.get("material_family") or "") for part in group})
        thickness_text = "unspecified thickness" if thickness <= GEOMETRY_TOLERANCE else "{:.3f} mm material".format(thickness)
        notes = (
            "{}; usable sheet {:.3f} x {:.3f} mm; families: {}."
        ).format(
            thickness_text,
            estimate["usable_width"],
            estimate["usable_length"],
            ", ".join(families),
        )
        rows.append(_material_report_row(
            set_id,
            "Sheet-use estimate",
            "Estimated sheets required",
            estimate["sheet_count"],
            "sheets",
            MEASUREMENT_SHEET_ESTIMATE,
            "First-fit decreasing rectangular shelf estimate from part bounding boxes",
            records=group,
            part_count=len(group),
            notes=notes,
            decimals=0,
        ))
        rows.append(_material_report_row(
            set_id,
            "Sheet-use estimate",
            "Rectangular part bounding area",
            estimate["raw_area"],
            "mm^2",
            MEASUREMENT_BOUNDING_BOX,
            "Sum of overall XY part bounding rectangles",
            records=group,
            part_count=len(group),
            notes=thickness_text,
        ))
        rows.append(_material_report_row(
            set_id,
            "Sheet-use estimate",
            "Estimated rectangular occupancy",
            estimate["occupancy"],
            "%",
            MEASUREMENT_SHEET_ESTIMATE,
            "Bounding area divided by estimated usable sheet area",
            records=group,
            part_count=len(group),
            notes=thickness_text,
        ))
        if estimate["oversize"]:
            rows.append(_material_report_row(
                set_id,
                "Sheet-use estimate",
                "Parts exceeding usable sheet rectangle",
                len(estimate["oversize"]),
                "parts",
                MEASUREMENT_BOUNDING_BOX,
                "Overall XY bounding rectangle fit check",
                records=estimate["oversize"],
                part_count=len(estimate["oversize"]),
                notes="These parts were not included in the estimated sheet count.",
                decimals=0,
            ))
    rows.append(_material_report_row(
        set_id,
        "Sheet-use estimate",
        "Total estimated sheets across material groups",
        total_sheets,
        "sheets",
        MEASUREMENT_SHEET_ESTIMATE,
        "Sum of separate thickness-group rectangular estimates",
        records=sheet_candidates,
        part_count=len(sheet_candidates),
        notes=(
            "{} part(s) excluded by the material-thickness filter. ".format(len(filtered_out))
            if filtered_out else ""
        ) + (
            "{} oversize part(s) require separate review.".format(len(all_oversize))
            if all_oversize else ""
        ),
        decimals=0,
    ))

    diagnostics = {
        "record_count": len(records),
        "unavailable_geometry": len(unavailable),
        "physical_part_count": len(parts),
        "sheet_candidate_count": len(sheet_candidates),
        "filtered_part_count": len(filtered_out),
        "oversize_part_count": len(all_oversize),
        "exact_rows": sum(1 for row in rows if row.get("Measurement classification") == MEASUREMENT_EXACT),
        "bounding_rows": sum(1 for row in rows if row.get("Measurement classification") == MEASUREMENT_BOUNDING_BOX),
        "estimate_rows": sum(1 for row in rows if row.get("Measurement classification") == MEASUREMENT_SHEET_ESTIMATE),
        "legacy_scan": bool(index_payload.get("legacy_scan", False)),
    }
    return rows, diagnostics


def create_or_replace_material_report(doc, set_id, rows, config, diagnostics=None):
    if not isinstance(rows, list) or not rows:
        raise ValueError("The material report contains no rows.")
    config = validate_material_report_config(config)
    existing = [
        obj for obj in list(doc.Objects)
        if object_string_property(obj, "GeneratedBy", "") == GENERATOR_ID
        and object_string_property(obj, "TemplateSetID", "") == set_id
        and object_string_property(obj, "GeneratedRole", "") == MATERIAL_REPORT_ROLE
    ]
    transaction_open = False
    try:
        doc.openTransaction(
            "Update Version {} material report".format(MACRO_VERSION_NUMBER)
        )
        transaction_open = True
        name = unique_internal_name(
            doc,
            "{}_{}".format(
                MATERIAL_REPORT_NAME,
                safe_filename_component(set_id, "SET").replace("-", "_"),
            ),
        )
        sheet = doc.addObject("Spreadsheet::Sheet", name)
        sheet.Label = "Material and Length Report [{}]".format(set_id)
        tag_generated_object(sheet, MATERIAL_REPORT_ROLE, set_id)
        properties = [
            ensure_property(
                sheet, "App::PropertyInteger", "MaterialReportSchemaVersion",
                "Material report", "Material-report schema version",
            ),
            ensure_property(
                sheet, "App::PropertyString", "MaterialReportCreatedAt",
                "Material report", "Date and time when this report was created",
            ),
            ensure_property(
                sheet, "App::PropertyInteger", "MaterialReportRowCount",
                "Material report", "Number of material-report rows",
            ),
            ensure_property(
                sheet, "App::PropertyString", MATERIAL_REPORT_SETTINGS_PROPERTY,
                "Material report", "Sheet-estimate settings used for this report",
            ),
            ensure_property(
                sheet, "App::PropertyString", "MaterialReportDiagnosticsJSON",
                "Material report", "Measurement and estimate diagnostic summary",
            ),
        ]
        sheet.MaterialReportSchemaVersion = MATERIAL_REPORT_SCHEMA_VERSION
        sheet.MaterialReportCreatedAt = datetime.datetime.now().astimezone().isoformat(
            timespec="seconds"
        )
        sheet.MaterialReportRowCount = len(rows)
        setattr(sheet, MATERIAL_REPORT_SETTINGS_PROPERTY, json.dumps(config, sort_keys=True))
        sheet.MaterialReportDiagnosticsJSON = json.dumps(
            diagnostics if isinstance(diagnostics, dict) else {}, sort_keys=True
        )
        set_read_only(sheet, properties)
        for column_index, field in enumerate(MATERIAL_REPORT_FIELDS):
            sheet.set("{}1".format(_spreadsheet_column_name(column_index)), field)
        for row_index, row in enumerate(rows, start=2):
            for column_index, field in enumerate(MATERIAL_REPORT_FIELDS):
                sheet.set(
                    "{}{}".format(_spreadsheet_column_name(column_index), row_index),
                    _spreadsheet_text(row.get(field, "")),
                )
        try:
            last_column = _spreadsheet_column_name(len(MATERIAL_REPORT_FIELDS) - 1)
            sheet.setStyle("A1:{}1".format(last_column), "bold", "add")
            sheet.setBackground("A1:{}1".format(last_column), (0.85, 0.85, 0.85))
            for column_index in range(len(MATERIAL_REPORT_FIELDS)):
                sheet.setColumnWidth(
                    _spreadsheet_column_name(column_index),
                    135 if column_index < 11 else 190,
                )
        except Exception:
            pass
        group = find_template_set_group(doc, set_id)
        if group is not None:
            group.addObject(sheet)
        for old_sheet in existing:
            if old_sheet is not sheet:
                doc.removeObject(old_sheet.Name)
        _document_recompute(doc)
        doc.commitTransaction()
        transaction_open = False
        return sheet
    except Exception:
        if transaction_open:
            try:
                doc.abortTransaction()
            except Exception:
                pass
        raise


def write_material_report_csv(path, rows):
    if not rows:
        raise ValueError("The material and length report contains no rows.")
    directory = os.path.dirname(os.path.abspath(path))
    if not os.path.isdir(directory):
        raise ValueError("The selected CSV directory does not exist: {}".format(directory))
    temporary_path = _temporary_export_path(path)
    try:
        with open(temporary_path, "w", newline="", encoding="utf-8-sig") as handle:
            writer = csv.DictWriter(
                handle,
                fieldnames=MATERIAL_REPORT_FIELDS,
                extrasaction="ignore",
                lineterminator="\n",
            )
            writer.writeheader()
            for row in rows:
                writer.writerow({
                    field: _safe_csv_schedule_value(row.get(field, ""))
                    for field in MATERIAL_REPORT_FIELDS
                })
        if not os.path.isfile(temporary_path) or os.path.getsize(temporary_path) <= 0:
            raise ValueError("The material and length report CSV contained no data.")
        os.replace(temporary_path, path)
    except Exception:
        if os.path.exists(temporary_path):
            try:
                os.remove(temporary_path)
            except Exception:
                pass
        raise


class MaterialLengthReportDialog(QtWidgets.QDialog):
    def __init__(self, doc, parent=None):
        super(MaterialLengthReportDialog, self).__init__(parent)
        self.doc = doc
        self.rows = []
        self.diagnostics = {}
        self.index_payload = None
        self._loading = False
        self.setWindowTitle(versioned_dialog_title("Material and length report"))
        self.resize(1500, 820)
        layout = QtWidgets.QVBoxLayout(self)

        top_layout = QtWidgets.QHBoxLayout()
        top_layout.addWidget(QtWidgets.QLabel("Template set:"))
        self.set_box = QtWidgets.QComboBox()
        self.set_box.addItems(generated_template_set_ids(doc))
        top_layout.addWidget(self.set_box)
        self.refresh_button = QtWidgets.QPushButton("Refresh report")
        top_layout.addWidget(self.refresh_button)
        top_layout.addStretch(1)
        layout.addLayout(top_layout)

        settings_group = QtWidgets.QGroupBox("Rectangular sheet-use estimate settings")
        settings_form = QtWidgets.QFormLayout(settings_group)

        def number_box(minimum, maximum, suffix, decimals=3):
            box = QtWidgets.QDoubleSpinBox()
            box.setRange(minimum, maximum)
            box.setDecimals(decimals)
            box.setSingleStep(1.0)
            box.setSuffix(suffix)
            return box

        self.sheet_width_box = number_box(1.0, 100000.0, " mm")
        self.sheet_length_box = number_box(1.0, 100000.0, " mm")
        self.edge_margin_box = number_box(0.0, 10000.0, " mm")
        self.kerf_box = number_box(0.0, 1000.0, " mm")
        self.material_thickness_box = number_box(0.0, 1000.0, " mm")
        self.part_spacing_box = number_box(0.0, 1000.0, " mm")
        self.allow_rotation_box = QtWidgets.QCheckBox(
            "Allow 90-degree rotation of rectangular part bounds"
        )
        self.material_thickness_box.setToolTip(
            "Set 0 mm to estimate all available material thicknesses separately. "
            "A value above zero filters the estimate to matching parts and supplies "
            "the thickness for otherwise untyped 2D profiles."
        )
        self.kerf_box.setToolTip(
            "Conservative dimensional allowance added to each rectangular part bound."
        )
        self.part_spacing_box.setToolTip(
            "Preferred clearance added between rectangular part bounds."
        )
        settings_form.addRow("Sheet width:", self.sheet_width_box)
        settings_form.addRow("Sheet length:", self.sheet_length_box)
        settings_form.addRow("Usable edge margin:", self.edge_margin_box)
        settings_form.addRow("Kerf allowance:", self.kerf_box)
        settings_form.addRow("Material thickness filter (0 = all):", self.material_thickness_box)
        settings_form.addRow("Preferred spacing between parts:", self.part_spacing_box)
        settings_form.addRow("Rotation:", self.allow_rotation_box)
        layout.addWidget(settings_group)

        estimate_note = QtWidgets.QLabel(
            "Exact totals use FreeCAD edge, face and solid measurements. Bounding-box values are identified explicitly. "
            "Sheet use is a conservative rectangular shelf estimate only; it is not nesting or CAM."
        )
        estimate_note.setWordWrap(True)
        layout.addWidget(estimate_note)
        self.summary_label = QtWidgets.QLabel("")
        self.summary_label.setWordWrap(True)
        layout.addWidget(self.summary_label)

        self.table = QtWidgets.QTableWidget(0, len(MATERIAL_REPORT_FIELDS))
        self.table.setHorizontalHeaderLabels(MATERIAL_REPORT_FIELDS)
        try:
            self.table.setEditTriggers(QtWidgets.QAbstractItemView.NoEditTriggers)
            self.table.setSelectionBehavior(QtWidgets.QAbstractItemView.SelectRows)
        except AttributeError:
            self.table.setEditTriggers(
                QtWidgets.QAbstractItemView.EditTrigger.NoEditTriggers
            )
            self.table.setSelectionBehavior(
                QtWidgets.QAbstractItemView.SelectionBehavior.SelectRows
            )
        self.table.setAlternatingRowColors(True)
        self.table.setSortingEnabled(False)
        layout.addWidget(self.table, 1)

        button_layout = QtWidgets.QHBoxLayout()
        self.save_settings_button = QtWidgets.QPushButton("Save sheet settings")
        self.update_sheet_button = QtWidgets.QPushButton("Update FreeCAD report")
        self.export_csv_button = QtWidgets.QPushButton("Export CSV...")
        close_button = QtWidgets.QPushButton("Close")
        button_layout.addWidget(self.save_settings_button)
        button_layout.addWidget(self.update_sheet_button)
        button_layout.addWidget(self.export_csv_button)
        button_layout.addStretch(1)
        button_layout.addWidget(close_button)
        layout.addLayout(button_layout)

        self.set_box.currentIndexChanged.connect(self._template_set_changed)
        self.refresh_button.clicked.connect(self.refresh_preview)
        self.save_settings_button.clicked.connect(self.save_settings)
        self.update_sheet_button.clicked.connect(self.update_freecad_report)
        self.export_csv_button.clicked.connect(self.export_csv)
        close_button.clicked.connect(self.accept)

        if self.set_box.count() > 0:
            selected_set = ""
            if Gui is not None:
                try:
                    for obj in reversed(Gui.Selection.getSelection()):
                        candidate = object_string_property(obj, "TemplateSetID", "")
                        if candidate:
                            selected_set = candidate
                            break
                except Exception:
                    pass
            if selected_set:
                index = self.set_box.findText(selected_set)
                if index >= 0:
                    self.set_box.setCurrentIndex(index)
            self._template_set_changed()
        else:
            self.summary_label.setText(
                "No recognised generated template sets exist in this document."
            )
            self.save_settings_button.setEnabled(False)
            self.update_sheet_button.setEnabled(False)
            self.export_csv_button.setEnabled(False)

    def current_set_id(self):
        return str(self.set_box.currentText()).strip()

    def _load_config(self, config):
        self._loading = True
        try:
            config = validate_material_report_config(config)
            self.sheet_width_box.setValue(config["sheet_width"])
            self.sheet_length_box.setValue(config["sheet_length"])
            self.edge_margin_box.setValue(config["usable_edge_margin"])
            self.kerf_box.setValue(config["kerf_allowance"])
            self.material_thickness_box.setValue(config["material_thickness"])
            self.part_spacing_box.setValue(config["part_spacing"])
            self.allow_rotation_box.setChecked(config["allow_rotation"])
        finally:
            self._loading = False

    def current_config(self):
        return validate_material_report_config({
            "sheet_width": float(self.sheet_width_box.value()),
            "sheet_length": float(self.sheet_length_box.value()),
            "usable_edge_margin": float(self.edge_margin_box.value()),
            "kerf_allowance": float(self.kerf_box.value()),
            "material_thickness": float(self.material_thickness_box.value()),
            "allow_rotation": bool(self.allow_rotation_box.isChecked()),
            "part_spacing": float(self.part_spacing_box.value()),
        })

    def _template_set_changed(self, *_args):
        if self._loading:
            return
        set_id = self.current_set_id()
        settings = settings_for_template_set(self.doc, set_id)
        self._load_config(read_material_report_config(settings))
        self.refresh_preview()

    def refresh_preview(self, *_args):
        set_id = self.current_set_id()
        if not set_id:
            self.rows = []
            self.table.setRowCount(0)
            return
        try:
            config = self.current_config()
            settings = settings_for_template_set(self.doc, set_id)
            self.index_payload = production_record_index_for_set(self.doc, set_id)
            self.rows, self.diagnostics = build_material_report_rows(
                self.doc, self.index_payload, settings, config, set_id
            )
            self.table.setSortingEnabled(False)
            self.table.setRowCount(len(self.rows))
            for row_index, row in enumerate(self.rows):
                for column_index, field in enumerate(MATERIAL_REPORT_FIELDS):
                    self.table.setItem(
                        row_index,
                        column_index,
                        QtWidgets.QTableWidgetItem(str(row.get(field, ""))),
                    )
            for column_index in range(len(MATERIAL_REPORT_FIELDS)):
                self.table.setColumnWidth(column_index, 130 if column_index < 11 else 185)
            self.table.setSortingEnabled(True)
            legacy_text = (
                " Legacy metadata scan used; regenerate deliberately with Version {} for the complete catalogue.".format(
                    MACRO_VERSION_NUMBER
                )
                if self.diagnostics.get("legacy_scan") else ""
            )
            self.summary_label.setText(
                "{} report rows; {} physical parts; {} exact rows; {} bounding-box rows; "
                "{} sheet-estimate rows; {} unavailable source records; {} oversize parts.{}".format(
                    len(self.rows),
                    self.diagnostics.get("physical_part_count", 0),
                    self.diagnostics.get("exact_rows", 0),
                    self.diagnostics.get("bounding_rows", 0),
                    self.diagnostics.get("estimate_rows", 0),
                    self.diagnostics.get("unavailable_geometry", 0),
                    self.diagnostics.get("oversize_part_count", 0),
                    legacy_text,
                )
            )
            enabled = bool(self.rows)
            self.save_settings_button.setEnabled(True)
            self.update_sheet_button.setEnabled(enabled)
            self.export_csv_button.setEnabled(enabled)
        except Exception as error:
            self.rows = []
            self.diagnostics = {}
            self.table.setRowCount(0)
            self.summary_label.setText("Material report preview failed: {}".format(error))
            self.update_sheet_button.setEnabled(False)
            self.export_csv_button.setEnabled(False)

    def save_settings(self, silent=False):
        try:
            config = self.current_config()
            settings = settings_for_template_set(self.doc, self.current_set_id())
            store_material_report_config(settings, config)
            _document_recompute(self.doc)
            if not silent:
                QtWidgets.QMessageBox.information(
                    self,
                    versioned_dialog_title("Material report settings saved"),
                    "The validated sheet-estimate settings were saved. Railway geometry was not changed.",
                )
            return config
        except Exception as error:
            if not silent:
                QtWidgets.QMessageBox.critical(
                    self,
                    versioned_dialog_title("Material report settings error"),
                    str(error),
                )
            raise

    def update_freecad_report(self):
        if not self.rows:
            return
        try:
            config = self.save_settings(silent=True)
            sheet = create_or_replace_material_report(
                self.doc,
                self.current_set_id(),
                self.rows,
                config,
                self.diagnostics,
            )
            QtWidgets.QMessageBox.information(
                self,
                versioned_dialog_title("Material report updated"),
                "Created {} with {} rows. Existing railway geometry was not changed.".format(
                    str(getattr(sheet, "Label", "Material and Length Report")),
                    len(self.rows),
                ),
            )
        except Exception as error:
            QtWidgets.QMessageBox.critical(
                self,
                versioned_dialog_title("Material report error"),
                str(error),
            )

    def export_csv(self):
        if not self.rows:
            return
        try:
            config = self.save_settings(silent=True)
            set_id = self.current_set_id()
            settings = settings_for_template_set(self.doc, set_id)
            export_config = read_production_export_config(settings)
            directory = str(export_config.get("output_directory") or "").strip()
            if not directory or not os.path.isdir(directory):
                directory = os.path.expanduser("~")
            suggested = os.path.join(
                directory,
                "{}_{}_Material_Length_Report.csv".format(
                    safe_filename_component(set_id, "SET"),
                    safe_filename_component(MACRO_VERSION_NUMBER, "Version"),
                ),
            )
            selection = QtWidgets.QFileDialog.getSaveFileName(
                self,
                versioned_dialog_title("Export material and length report CSV"),
                suggested,
                "CSV files (*.csv)",
            )
            selected = selection[0] if isinstance(selection, (tuple, list)) else selection
            if not selected:
                return
            path = str(selected)
            if not path.lower().endswith(".csv"):
                path += ".csv"
            write_material_report_csv(path, self.rows)
            remember_last_material_report_config(config)
            QtWidgets.QMessageBox.information(
                self,
                versioned_dialog_title("Material report exported"),
                "Material and length report CSV written to:\n{}".format(path),
            )
        except Exception as error:
            QtWidgets.QMessageBox.critical(
                self,
                versioned_dialog_title("Material report CSV error"),
                str(error),
            )


def validate_export_record(record):
    shape = record.get("shape")
    if _shape_is_null(shape):
        return False, "No exportable geometry was created for this output."
    category = record.get("category")
    if category == EXPORT_CATEGORY_SOLID:
        if not shape_has_solid_geometry(shape):
            return False, "STL and STEP require a valid solid or solid compound."
        return True, ""
    if not shape_has_edges(shape):
        return False, "The selected 2D output has no edges."
    if not shape_is_planar_xy(shape):
        return False, "DXF and SVG require planar XY geometry."
    if category in (
        EXPORT_CATEGORY_CUTTING,
        EXPORT_CATEGORY_HOLES,
        EXPORT_CATEGORY_JOINTS,
    ) and not shape_has_closed_profiles(shape):
        return False, "A cutting, hole or joint profile contains an open wire."
    return True, ""


def record_compatible_formats(record, config):
    selected = config.get("formats", {})
    if record.get("category") == EXPORT_CATEGORY_SOLID:
        candidates = (EXPORT_FORMAT_STL, EXPORT_FORMAT_STEP)
    else:
        candidates = (EXPORT_FORMAT_DXF, EXPORT_FORMAT_SVG)
    return [key for key in candidates if selected.get(key, False)]


def plan_production_export(records, config, set_id):
    output_directory = config["output_directory"]
    overwrite = bool(config.get("overwrite_existing", False))
    tasks = []
    skipped = []
    reserved = set()
    desired_counts = {}
    valid_records = []

    for record in records:
        valid, reason = validate_export_record(record)
        formats = record_compatible_formats(record, config)
        if not valid:
            skipped.append({"record": record, "reason": reason, "format": ""})
            continue
        if not formats:
            skipped.append({
                "record": record,
                "reason": "No compatible selected format for this geometry type.",
                "format": "",
            })
            continue
        valid_records.append(record)
        is_section = int(record.get("section_number") or 0) > 0
        if not is_section or config.get("export_each_section", True):
            stem = record_filename_stem(record, config, set_id)
            for format_key in formats:
                desired = os.path.join(output_directory, "{}.{}".format(stem, format_key))
                path = allocate_export_path(
                    desired, overwrite, reserved, desired_counts
                )
                if path in reserved:
                    raise ValueError("Internal filename collision: {}".format(path))
                reserved.add(path)
                tasks.append({
                    "format": format_key,
                    "path": path,
                    "records": [record],
                    "combined": False,
                    "category": record["category"],
                })

    if config.get("create_combined_files", True):
        for category in (
            EXPORT_CATEGORY_CUTTING,
            EXPORT_CATEGORY_HOLES,
            EXPORT_CATEGORY_JOINTS,
            EXPORT_CATEGORY_ENGRAVING,
        ):
            members = [item for item in valid_records if item["category"] == category]
            subtypes = set(item.get("subtype", "") for item in members)
            if "TrackTemplateSection" in subtypes:
                members = [item for item in members if item.get("subtype") != "TrackTemplateCompound"]
            if "PlatformSection" in subtypes:
                members = [item for item in members if item.get("subtype") != "PlatformPlanOutline"]
            if "FormationSectionPerimeter" in subtypes:
                members = [item for item in members if item.get("subtype") != "FormationPerimeter"]
            if not members:
                continue
            for format_key in (EXPORT_FORMAT_DXF, EXPORT_FORMAT_SVG):
                if not config.get("formats", {}).get(format_key, False):
                    continue
                stem = combined_filename_stem(category, set_id)
                desired = os.path.join(output_directory, "{}.{}".format(stem, format_key))
                path = allocate_export_path(
                    desired, overwrite, reserved, desired_counts
                )
                reserved.add(path)
                tasks.append({
                    "format": format_key,
                    "path": path,
                    "records": members,
                    "combined": True,
                    "category": category,
                })
        solid_members = [
            item for item in valid_records if item["category"] == EXPORT_CATEGORY_SOLID
        ]
        solid_subtypes = set(item.get("subtype", "") for item in solid_members)
        if "TrackTemplateSection" in solid_subtypes:
            solid_members = [item for item in solid_members if item.get("subtype") != "TrackTemplateCompound"]
        if "PlatformSection" in solid_subtypes:
            solid_members = [item for item in solid_members if item.get("subtype") != "PlatformBody"]
        if "FormationSectionBody" in solid_subtypes:
            solid_members = [item for item in solid_members if item.get("subtype") != "FormationBody"]
        if solid_members and config.get("formats", {}).get(EXPORT_FORMAT_STEP, False):
            stem = combined_filename_stem(EXPORT_CATEGORY_SOLID, set_id)
            desired = os.path.join(output_directory, "{}.step".format(stem))
            path = allocate_export_path(
                desired, overwrite, reserved, desired_counts
            )
            reserved.add(path)
            tasks.append({
                "format": EXPORT_FORMAT_STEP,
                "path": path,
                "records": solid_members,
                "combined": True,
                "category": EXPORT_CATEGORY_SOLID,
            })

    for record in valid_records:
        is_section = int(record.get("section_number") or 0) > 0
        included_individually = (not is_section) or config.get("export_each_section", True)
        included_combined = bool(config.get("create_combined_files", True))
        if not included_individually and not included_combined:
            skipped.append({
                "record": record,
                "reason": "Separate section export and combined files are both disabled.",
                "format": "",
            })

    manifest_path = ""
    if config.get("create_manifest", True):
        desired = os.path.join(
            output_directory,
            "Curve_{}_Export_Manifest.csv".format(export_set_filename_token(set_id)),
        )
        manifest_path = allocate_export_path(
            desired, overwrite, reserved, desired_counts
        )
    return {
        "tasks": tasks,
        "skipped": skipped,
        "manifest_path": manifest_path,
        "reserved_paths": reserved,
    }


def _temporary_export_path(final_path):
    directory = os.path.dirname(final_path)
    stem, extension = os.path.splitext(os.path.basename(final_path))
    return os.path.join(
        directory,
        ".{}_tmp_{}{}".format(stem, uuid.uuid4().hex, extension),
    )


def ensure_dxf_millimetre_units(path):
    """Set ASCII DXF insertion units to millimetres without altering geometry."""
    with open(path, "rb") as handle:
        raw = handle.read()
    if raw.startswith(b"AutoCAD Binary DXF"):
        raise ValueError(
            "The DXF exporter produced a binary file whose millimetre header "
            "cannot be verified safely."
        )
    try:
        text = raw.decode("utf-8")
        encoding = "utf-8"
    except UnicodeDecodeError:
        text = raw.decode("latin-1")
        encoding = "latin-1"
    newline = "\r\n" if "\r\n" in text else "\n"
    lines = text.splitlines()
    if len(lines) < 2:
        raise ValueError("The DXF exporter produced an incomplete text file.")

    pairs = []
    for index in range(0, len(lines) - 1, 2):
        pairs.append([lines[index], lines[index + 1]])

    def set_header_variable(name, value):
        for pair_index, pair in enumerate(pairs):
            if pair[0].strip() == "9" and pair[1].strip() == name:
                if pair_index + 1 >= len(pairs):
                    raise ValueError("DXF header variable {} has no value.".format(name))
                pairs[pair_index + 1][1] = str(value)
                return True
        return False

    has_insunits = set_header_variable("$INSUNITS", 4)
    has_measurement = set_header_variable("$MEASUREMENT", 1)
    if not has_insunits or not has_measurement:
        header_end = None
        in_header = False
        for pair_index, pair in enumerate(pairs):
            code = pair[0].strip()
            value = pair[1].strip().upper()
            if code == "0" and value == "SECTION":
                if pair_index + 1 < len(pairs):
                    next_pair = pairs[pair_index + 1]
                    in_header = (
                        next_pair[0].strip() == "2"
                        and next_pair[1].strip().upper() == "HEADER"
                    )
            elif in_header and code == "0" and value == "ENDSEC":
                header_end = pair_index
                break
        additions = []
        if not has_insunits:
            additions.extend([["9", "$INSUNITS"], ["70", "4"]])
        if not has_measurement:
            additions.extend([["9", "$MEASUREMENT"], ["70", "1"]])
        if header_end is None:
            additions = [
                ["0", "SECTION"],
                ["2", "HEADER"],
            ] + additions + [["0", "ENDSEC"]]
            pairs[0:0] = additions
        else:
            pairs[header_end:header_end] = additions

    output_lines = []
    for code, value in pairs:
        output_lines.extend([code, value])
    output_text = newline.join(output_lines) + newline
    with open(path, "w", encoding=encoding, newline="") as handle:
        handle.write(output_text)


def _format_svg_number(value):
    text = "{:.9f}".format(float(value)).rstrip("0").rstrip(".")
    return "0" if text in ("", "-0") else text


def repair_svg_degenerate_viewbox(path, minimum_span=SVG_MINIMUM_VIEWBOX_SPAN):
    """Expand only a zero-width or zero-height SVG page around line geometry."""
    try:
        tree = ET.parse(path)
        root = tree.getroot()
    except Exception as error:
        raise ValueError("The SVG exporter produced invalid XML: {}".format(error))

    physical_pattern = r"^([+-]?(?:[0-9]+(?:\.[0-9]*)?|\.[0-9]+))mm$"
    width_text = str(root.attrib.get("width", "")).strip()
    height_text = str(root.attrib.get("height", "")).strip()
    width_match = re.match(physical_pattern, width_text, re.I)
    height_match = re.match(physical_pattern, height_text, re.I)
    if width_match is None or height_match is None:
        return False

    view_box_text = str(
        root.attrib.get("viewBox", root.attrib.get("viewbox", ""))
    ).strip()
    parts = re.split(r"[ ,]+", view_box_text)
    if len(parts) != 4:
        return False
    try:
        view_x, view_y, view_width, view_height = [float(value) for value in parts]
        physical_width = float(width_match.group(1))
        physical_height = float(height_match.group(1))
    except Exception:
        return False

    tolerance = 1.0e-12
    if view_width < -tolerance or view_height < -tolerance:
        raise ValueError("The SVG exporter created a negative viewBox span.")
    repair_width = view_width <= tolerance
    repair_height = view_height <= tolerance
    if not repair_width and not repair_height:
        return False

    minimum_span = max(float(minimum_span), 0.001)
    scale_candidates = []
    if view_width > tolerance and physical_width > tolerance:
        scale_candidates.append(physical_width / view_width)
    if view_height > tolerance and physical_height > tolerance:
        scale_candidates.append(physical_height / view_height)
    physical_scale = scale_candidates[0] if scale_candidates else 1.0

    if repair_width:
        view_x -= 0.5 * minimum_span
        view_width = minimum_span
        physical_width = minimum_span * physical_scale
    if repair_height:
        view_y -= 0.5 * minimum_span
        view_height = minimum_span
        physical_height = minimum_span * physical_scale

    root.set("width", "{}mm".format(_format_svg_number(physical_width)))
    root.set("height", "{}mm".format(_format_svg_number(physical_height)))
    root.set(
        "viewBox",
        "{} {} {} {}".format(
            _format_svg_number(view_x),
            _format_svg_number(view_y),
            _format_svg_number(view_width),
            _format_svg_number(view_height),
        ),
    )
    root.attrib.pop("viewbox", None)
    if root.tag.startswith("{"):
        namespace = root.tag[1:].split("}", 1)[0]
        ET.register_namespace("", namespace)
    tree.write(path, encoding="utf-8", xml_declaration=True)
    return True


def validate_svg_millimetre_scale(path):
    """Reject SVG output that lacks physical millimetre size and a viewBox."""
    try:
        root = ET.parse(path).getroot()
    except Exception as error:
        raise ValueError("The SVG exporter produced invalid XML: {}".format(error))
    width = str(root.attrib.get("width", "")).strip()
    height = str(root.attrib.get("height", "")).strip()
    view_box = str(
        root.attrib.get("viewBox", root.attrib.get("viewbox", ""))
    ).strip()
    physical_pattern = r"^[+-]?(?:[0-9]+(?:\.[0-9]*)?|\.[0-9]+)mm$"
    if not re.match(physical_pattern, width, re.I) or not re.match(
        physical_pattern, height, re.I
    ):
        raise ValueError(
            "The SVG exporter did not declare its physical width and height in millimetres."
        )
    parts = re.split(r"[ ,]+", view_box)
    if len(parts) != 4:
        raise ValueError("The SVG exporter did not create a valid four-value viewBox.")
    try:
        values = [float(value) for value in parts]
    except Exception:
        raise ValueError("The SVG exporter created a non-numeric viewBox.")
    if values[2] <= 0.0 or values[3] <= 0.0:
        raise ValueError("The SVG exporter created an empty viewBox.")


def _create_temporary_export_objects(doc, task):
    objects = []
    try:
        for index, record in enumerate(task["records"]):
            shape = record["shape"]
            if task["format"] in (EXPORT_FORMAT_DXF, EXPORT_FORMAT_SVG):
                shape = flatten_shape_to_xy(shape)
            else:
                shape = shape.copy()
            name = unique_internal_name(
                doc,
                "TemporaryProductionExport_{}_{}".format(uuid.uuid4().hex[:8], index),
            )
            obj = doc.addObject("Part::Feature", name)
            obj.Label = str(record.get("source_label") or record.get("source_name"))
            obj.Shape = shape
            objects.append(obj)
        _document_recompute(doc)
        return objects
    except Exception:
        for obj in reversed(objects):
            try:
                if doc.getObject(obj.Name) is not None:
                    doc.removeObject(obj.Name)
            except Exception:
                pass
        try:
            _document_recompute(doc)
        except Exception:
            pass
        raise


def _remove_temporary_export_objects(doc, objects):
    for obj in reversed(objects):
        try:
            if doc.getObject(obj.Name) is not None:
                doc.removeObject(obj.Name)
        except Exception:
            pass
    try:
        _document_recompute(doc)
    except Exception:
        pass


def dispatch_freecad_export(doc, task, temporary_path):
    objects = _create_temporary_export_objects(doc, task)
    try:
        format_key = task["format"]
        if format_key == EXPORT_FORMAT_DXF:
            import importDXF
            importDXF.export(objects, temporary_path)
            ensure_dxf_millimetre_units(temporary_path)
        elif format_key == EXPORT_FORMAT_SVG:
            import importSVG
            importSVG.export(objects, temporary_path)
            repair_svg_degenerate_viewbox(temporary_path)
            validate_svg_millimetre_scale(temporary_path)
        elif format_key == EXPORT_FORMAT_STL:
            import Mesh
            Mesh.export(objects, temporary_path)
        elif format_key == EXPORT_FORMAT_STEP:
            Part.export(objects, temporary_path)
        else:
            raise ValueError("Unsupported export format: {}".format(format_key))
    finally:
        _remove_temporary_export_objects(doc, objects)


def execute_export_tasks(doc, plan, config, exporter_override=None):
    results = []
    for task in plan["tasks"]:
        final_path = task["path"]
        temporary_path = _temporary_export_path(final_path)
        try:
            if not config.get("overwrite_existing", False) and os.path.exists(final_path):
                raise ValueError(
                    "The planned filename appeared after validation and was not overwritten."
                )
            if os.path.exists(temporary_path):
                os.remove(temporary_path)
            if exporter_override is None:
                dispatch_freecad_export(doc, task, temporary_path)
            else:
                exporter_override(doc, task, temporary_path)
            if not os.path.isfile(temporary_path) or os.path.getsize(temporary_path) <= 0:
                raise ValueError("The exporter produced no valid file data.")
            os.replace(temporary_path, final_path)
            results.append({"task": task, "success": True, "error": ""})
        except Exception as error:
            if os.path.exists(temporary_path):
                try:
                    os.remove(temporary_path)
                except Exception:
                    pass
            results.append({
                "task": task,
                "success": False,
                "error": str(error),
            })
    return results


def _manifest_row(
    record,
    set_id,
    format_key,
    path,
    status,
    error,
    export_timestamp,
    platform_config,
    formation_config,
    registration_config,
    template_assembly_config,
):
    role = str(record.get("role", ""))
    is_template = role in (
        "Template", "TrackTemplateSection", "TrackTemplateFixingHole", "TrackTemplateJoint",
        "StraightTrackTemplate", "StraightTrackTemplateSection",
        "StraightTrackTemplateFixingHole", "StraightTrackTemplateJoint",
    )
    is_platform = role in (
        "PlatformBody", "PlatformSection", "PlatformOutline", "PlatformEdge"
    )
    is_formation = role in (
        "FormationOutline", "FormationBody", "FormationSection", "FormationMatchingHole",
        "RegistrationFeature", "AlignmentHole", "StraightFormationOutline",
        "StraightFormationBody", "StraightFormationSection",
        "StraightFormationMatchingHole", "StraightRegistrationFeature",
        "StraightAlignmentHole",
    )
    joint_type = ""
    if role in ("TrackTemplateJoint", "StraightTrackTemplateJoint"):
        joint_type = template_assembly_config.get("joint_type", "")
    elif role in (
        "RegistrationFeature", "AlignmentHole",
        "StraightRegistrationFeature", "StraightAlignmentHole",
    ):
        joint_type = registration_config.get("joint_type", "")
    platform_height = float(
        record.get(
            "platform_height",
            platform_config.get("platform_height", 0.0),
        )
        or 0.0
    )
    return {
        "Macro version": MACRO_VERSION,
        "Export date and time": export_timestamp,
        "Template-set identifier": set_id,
        "Generated object name": record.get("source_name", ""),
        "Generated object role": role,
        "Track number": record.get("track_number") or "",
        "Platform number": record.get("platform_number") or "",
        "Platform name": record.get("platform_name") or "",
        "Section number": record.get("section_number") or "",
        "Travel-order number": record.get("travel_order_number") or "",
        "Export format": EXPORT_FORMAT_LABELS.get(format_key, str(format_key).upper()) if format_key else "",
        "Export filename": os.path.basename(path) if path else "",
        "Full export path": path or "",
        "Section length": "{:.3f}".format(record.get("section_length", 0.0)) if record.get("section_length", 0.0) else "",
        "Template thickness": "{:.3f}".format(record.get("template_thickness", TEMPLATE_THICKNESS)) if is_template else "",
        "Platform thickness": "{:.3f}".format(platform_height) if is_platform else "",
        "Formation-board thickness": "{:.3f}".format(formation_config.get("board_thickness", 0.0)) if is_formation else "",
        "Joint type": joint_type,
        "Fixing-hole diameter": "{:.3f}".format(template_assembly_config.get("hole_diameter", 0.0)) if role in ("TrackTemplateFixingHole", "FormationMatchingHole", "StraightTrackTemplateFixingHole", "StraightFormationMatchingHole") else "",
        "Export status": status,
        "Error message": error or "",
    }


def build_manifest_rows(
    results,
    skipped,
    set_id,
    platform_config,
    formation_config,
    registration_config,
    template_assembly_config,
):
    timestamp = datetime.datetime.now().astimezone().isoformat(timespec="seconds")
    rows = []
    for result in results:
        task = result["task"]
        status = "Success" if result["success"] else "Failure"
        for record in task["records"]:
            rows.append(_manifest_row(
                record, set_id, task["format"], task["path"], status,
                result.get("error", ""), timestamp, platform_config,
                formation_config, registration_config, template_assembly_config,
            ))
    for item in skipped:
        rows.append(_manifest_row(
            item["record"], set_id, item.get("format", ""), "", "Skipped",
            item.get("reason", ""), timestamp, platform_config, formation_config,
            registration_config, template_assembly_config,
        ))
    return rows


def write_export_manifest(path, rows):
    temporary_path = _temporary_export_path(path)
    try:
        with open(temporary_path, "w", newline="", encoding="utf-8-sig") as handle:
            writer = csv.DictWriter(
                handle,
                fieldnames=EXPORT_MANIFEST_FIELDS,
                extrasaction="ignore",
                lineterminator="\n",
            )
            writer.writeheader()
            for row in rows:
                writer.writerow(row)
        if not os.path.isfile(temporary_path) or os.path.getsize(temporary_path) <= 0:
            raise ValueError("The export manifest contained no data.")
        os.replace(temporary_path, path)
    except Exception:
        if os.path.exists(temporary_path):
            try:
                os.remove(temporary_path)
            except Exception:
                pass
        raise


def _export_record_report_name(record):
    """Build a stable human-readable identity for an export record."""
    record = record or {}
    label = str(
        record.get("source_label")
        or record.get("source_name")
        or record.get("route_name")
        or record.get("subtype")
        or record.get("role")
        or "Unnamed output"
    ).strip()
    qualifiers = []
    role = str(record.get("role") or "").strip()
    route_name = str(record.get("route_name") or "").strip()
    if role and role.casefold() not in label.casefold():
        qualifiers.append(role)
    if route_name and route_name.casefold() not in label.casefold():
        qualifiers.append("route {}".format(route_name))
    track_number = int(record.get("track_number") or 0)
    platform_number = int(record.get("platform_number") or 0)
    section_number = int(record.get("section_number") or 0)
    if track_number:
        qualifiers.append("track {}".format(track_number))
    if platform_number:
        platform_name = str(record.get("platform_name") or "").strip()
        if platform_name:
            qualifiers.append("platform {} {}".format(platform_number, platform_name))
        else:
            qualifiers.append("platform {}".format(platform_number))
    if section_number:
        qualifiers.append("section {}".format(section_number))
    return "{} [{}]".format(label, ", ".join(qualifiers)) if qualifiers else label


def _failed_export_report(item):
    task = item.get("task", {})
    format_key = str(task.get("format") or "")
    format_label = EXPORT_FORMAT_LABELS.get(format_key, format_key.upper() or "Unknown format")
    path = str(task.get("path") or "")
    filename = os.path.basename(path) or "unnamed output"
    records = list(task.get("records") or [])
    combined = bool(task.get("combined", False))
    if combined:
        object_text = "combined output containing {} record{}".format(
            len(records), "" if len(records) == 1 else "s"
        )
    elif records:
        object_text = _export_record_report_name(records[0])
    else:
        object_text = "no bound generated object"
    error = str(item.get("error") or "Unknown exporter failure").strip()
    summary = "{} '{}' - {}: {}".format(
        format_label, filename, object_text, error
    )
    detail_lines = [
        "Format: {}".format(format_label),
        "Filename: {}".format(filename),
        "Full path: {}".format(path or "Not allocated"),
        "Output type: {}".format("Combined" if combined else "Individual"),
        "Reason: {}".format(error),
        "Generated records:",
    ]
    if records:
        detail_lines.extend(
            "  - {}".format(_export_record_report_name(record))
            for record in records
        )
    else:
        detail_lines.append("  - None")
    return summary, "\n".join(detail_lines)


def _skipped_export_report(item):
    record = item.get("record") or {}
    format_key = str(item.get("format") or "")
    format_label = EXPORT_FORMAT_LABELS.get(format_key, format_key.upper()) if format_key else "No file created"
    reason = str(item.get("reason") or "No skip reason was recorded.").strip()
    identity = _export_record_report_name(record)
    summary = "{} - {}: {}".format(format_label, identity, reason)
    detail = "\n".join([
        "Requested output: {}".format(identity),
        "Format: {}".format(format_label),
        "Reason: {}".format(reason),
    ])
    return summary, detail


def run_production_export(
    doc,
    plan,
    config,
    set_id,
    platform_config,
    formation_config,
    registration_config,
    template_assembly_config,
    exporter_override=None,
):
    results = execute_export_tasks(doc, plan, config, exporter_override)
    manifest_rows = build_manifest_rows(
        results, plan["skipped"], set_id, platform_config, formation_config,
        registration_config, template_assembly_config,
    )
    manifest_path = plan.get("manifest_path", "")
    manifest_error = ""
    manifest_success = False
    if manifest_path:
        try:
            write_export_manifest(manifest_path, manifest_rows)
            manifest_success = True
        except Exception as error:
            manifest_error = str(error)

    successful = [item for item in results if item["success"]]
    failed = [item for item in results if not item["success"]]
    formats = sorted(set(item["task"]["format"].upper() for item in successful))

    failures = []
    failure_details = []
    for item in failed:
        summary, detail = _failed_export_report(item)
        failures.append(summary)
        failure_details.append(detail)
    if manifest_error:
        manifest_summary = "CSV manifest '{}': {}".format(
            os.path.basename(manifest_path) or "unnamed manifest",
            manifest_error,
        )
        failures.append(manifest_summary)
        failure_details.append("\n".join([
            "Output type: CSV manifest",
            "Filename: {}".format(os.path.basename(manifest_path) or "unnamed manifest"),
            "Full path: {}".format(manifest_path or "Not allocated"),
            "Reason: {}".format(manifest_error),
        ]))

    skipped_outputs = []
    skipped_details = []
    for item in plan.get("skipped", []):
        summary, detail = _skipped_export_report(item)
        skipped_outputs.append(summary)
        skipped_details.append(detail)

    return {
        "output_directory": config["output_directory"],
        "successful_files": len(successful) + (1 if manifest_success else 0),
        "failed_files": len(failed) + (1 if manifest_error else 0),
        "skipped_objects": len(plan.get("skipped", [])),
        "formats": formats,
        "manifest_path": manifest_path if manifest_success else "",
        "manifest_requested": bool(manifest_path),
        "failures": failures,
        "failure_details": failure_details,
        "skipped_outputs": skipped_outputs,
        "skipped_details": skipped_details,
        "results": results,
    }


def _preflight_severity_rank(severity):
    return {
        PRODUCTION_PREFLIGHT_SEVERITY_ERROR: 0,
        PRODUCTION_PREFLIGHT_SEVERITY_WARNING: 1,
        PRODUCTION_PREFLIGHT_SEVERITY_INFORMATION: 2,
    }.get(str(severity), 3)


def make_preflight_issue(
    issue_code,
    severity,
    message,
    set_id,
    record=None,
    format_key="",
    proposed_path="",
    blocks_export=None,
):
    record = record or {}
    if blocks_export is None:
        blocks_export = severity == PRODUCTION_PREFLIGHT_SEVERITY_ERROR
    return {
        "schema_version": PRODUCTION_PREFLIGHT_SCHEMA_VERSION,
        "issue_code": str(issue_code or "UNKNOWN"),
        "severity": str(severity or PRODUCTION_PREFLIGHT_SEVERITY_INFORMATION),
        "message": str(message or ""),
        "blocks_export": bool(blocks_export),
        "template_set_id": str(set_id or record.get("template_set_id") or ""),
        "route_id": str(record.get("route_id") or ""),
        "route_name": str(record.get("route_name") or ""),
        "track_number": int(record.get("track_number") or 0),
        "track_name": str(record.get("track_name") or ""),
        "platform_number": int(record.get("platform_number") or 0),
        "platform_name": str(record.get("platform_name") or ""),
        "section_number": int(record.get("section_number") or 0),
        "travel_order_number": int(record.get("travel_order_number") or 0),
        "format": str(format_key or ""),
        "proposed_path": str(proposed_path or ""),
        "source_name": str(record.get("source_name") or ""),
        "record_id": str(record.get("record_id") or ""),
    }


def preflight_issue_row(issue):
    return {
        "Severity": issue.get("severity", ""),
        "Issue code": issue.get("issue_code", ""),
        "Message": issue.get("message", ""),
        "Blocks export": "Yes" if issue.get("blocks_export", False) else "No",
        "Template-set ID": issue.get("template_set_id", ""),
        "Route name": issue.get("route_name", ""),
        "Route ID": issue.get("route_id", ""),
        "Track number": issue.get("track_number") or "",
        "Track name": issue.get("track_name", ""),
        "Platform number": issue.get("platform_number") or "",
        "Platform name": issue.get("platform_name", ""),
        "Section number": issue.get("section_number") or "",
        "Travel-order number": issue.get("travel_order_number") or "",
        "Export format": EXPORT_FORMAT_LABELS.get(
            issue.get("format", ""), str(issue.get("format", "")).upper()
        ) if issue.get("format") else "",
        "Proposed path": issue.get("proposed_path", ""),
        "Source object": issue.get("source_name", ""),
        "Production-record ID": issue.get("record_id", ""),
    }


def sort_preflight_issues(issues):
    return sorted(
        list(issues or []),
        key=lambda issue: (
            _preflight_severity_rank(issue.get("severity")),
            str(issue.get("route_id") or ""),
            int(issue.get("track_number") or 0),
            int(issue.get("platform_number") or 0),
            int(issue.get("section_number") or 0),
            str(issue.get("issue_code") or ""),
            str(issue.get("record_id") or ""),
        ),
    )


def summarise_preflight(issues):
    counts = {
        PRODUCTION_PREFLIGHT_SEVERITY_INFORMATION: 0,
        PRODUCTION_PREFLIGHT_SEVERITY_WARNING: 0,
        PRODUCTION_PREFLIGHT_SEVERITY_ERROR: 0,
    }
    for issue in issues or []:
        severity = str(issue.get("severity") or "")
        counts[severity] = counts.get(severity, 0) + 1
    counts["blocking"] = sum(
        1 for issue in issues or [] if issue.get("blocks_export", False)
    )
    return counts


def _preflight_route_key(record):
    return str(record.get("route_id") or "CURVE")


def _preflight_record_for_group(record):
    return {
        "route_id": str(record.get("route_id") or ""),
        "route_name": str(record.get("route_name") or ""),
        "track_number": int(record.get("track_number") or 0),
        "track_name": str(record.get("track_name") or ""),
        "platform_number": int(record.get("platform_number") or 0),
        "platform_name": str(record.get("platform_name") or ""),
        "section_number": int(record.get("section_number") or 0),
        "travel_order_number": int(record.get("travel_order_number") or 0),
        "source_name": str(record.get("source_name") or ""),
        "record_id": str(record.get("record_id") or ""),
    }


def _preflight_expected_linear_plan_record(record):
    """Return True for production records that are intentionally open linear XY output."""
    if str(record.get("category") or "") != EXPORT_CATEGORY_ENGRAVING:
        return False
    subtype = str(record.get("subtype") or "")
    role = str(record.get("role") or "")
    return (
        subtype in ("TrackCentreline", "PlatformEdge")
        or role in (
            "Centreline",
            "StraightTrackCentreline",
            "PlatformEdge",
        )
    )


def preflight_metadata_and_geometry(records, set_id):
    issues = []
    for record in records or []:
        metadata_issues = production_record_metadata_issues(record, set_id)
        for detail in metadata_issues:
            issues.append(make_preflight_issue(
                "MISSING_METADATA",
                PRODUCTION_PREFLIGHT_SEVERITY_ERROR,
                detail,
                set_id,
                record,
            ))
        binding_type = str(record.get("source_binding_type") or "").strip()
        if binding_type == "legacy-object":
            issues.append(make_preflight_issue(
                "LEGACY_RECORD_BINDING",
                PRODUCTION_PREFLIGHT_SEVERITY_WARNING,
                "This record comes from a cautious legacy object scan; one-to-one production identity cannot be guaranteed until deliberate regeneration under Version {}.".format(
                    MACRO_VERSION_NUMBER
                ),
                set_id,
                record,
                blocks_export=False,
            ))
        elif binding_type in ("unbound", "multiple-objects", "compound-member"):
            issues.append(make_preflight_issue(
                "AMBIGUOUS_RECORD_BINDING",
                PRODUCTION_PREFLIGHT_SEVERITY_ERROR,
                "The production record does not have a safe one-to-one source binding ({}).".format(
                    binding_type
                ),
                set_id,
                record,
            ))
        valid, reason = validate_export_record(record)
        if not valid:
            issues.append(make_preflight_issue(
                "INVALID_GEOMETRY",
                PRODUCTION_PREFLIGHT_SEVERITY_ERROR,
                str(reason or "The production record has invalid geometry."),
                set_id,
                record,
            ))
            continue
        if record.get("category") in (
            EXPORT_CATEGORY_CUTTING,
            EXPORT_CATEGORY_HOLES,
            EXPORT_CATEGORY_JOINTS,
            EXPORT_CATEGORY_ENGRAVING,
        ):
            shape = record.get("shape")
            try:
                bounds = shape.BoundBox
                x_span = max(0.0, float(bounds.XLength))
                y_span = max(0.0, float(bounds.YLength))
            except Exception:
                x_span = 0.0
                y_span = 0.0
            if x_span <= GEOMETRY_TOLERANCE and y_span <= GEOMETRY_TOLERANCE:
                issues.append(make_preflight_issue(
                    "EMPTY_2D_BOUNDS",
                    PRODUCTION_PREFLIGHT_SEVERITY_ERROR,
                    "The planar output has no usable X or Y extent.",
                    set_id,
                    record,
                ))
            elif x_span <= GEOMETRY_TOLERANCE or y_span <= GEOMETRY_TOLERANCE:
                if _preflight_expected_linear_plan_record(record):
                    continue
                issues.append(make_preflight_issue(
                    "DEGENERATE_2D_SPAN",
                    PRODUCTION_PREFLIGHT_SEVERITY_INFORMATION,
                    "The planar output is unexpectedly one-dimensional; the established SVG viewBox repair will be used where required.",
                    set_id,
                    record,
                    blocks_export=False,
                ))
    return issues


def _preflight_numbering_family(record):
    subtype = str(record.get("subtype") or "")
    route_key = _preflight_route_key(record)
    track_number = int(record.get("track_number") or 0)
    platform_number = int(record.get("platform_number") or 0)
    if subtype == "TrackTemplateSection":
        return ("TrackTemplateSection", route_key, track_number, 0)
    if subtype == "TrackTemplateFixingHole":
        return ("TrackTemplateFixingHole", route_key, track_number, 0)
    if subtype == "PlatformSection":
        return ("PlatformSection", route_key, 0, platform_number)
    if subtype in ("FormationSectionPerimeter", "FormationSectionBody"):
        return ("FormationSection", route_key, 0, 0)
    if subtype == "SectionNumberEngraving":
        return ("SectionNumberEngraving", route_key, 0, 0)
    return None


def preflight_numbering(records, set_id):
    issues = []
    groups = {}
    for record in records or []:
        family = _preflight_numbering_family(record)
        if family is None:
            continue
        groups.setdefault(family, []).append(record)

    for family, members in groups.items():
        representative = _preflight_record_for_group(members[0])
        representation_counts = {}
        section_to_travel = {}
        travel_to_sections = {}
        sections = set()
        for record in members:
            section_number = int(record.get("section_number") or 0)
            travel_number = int(record.get("travel_order_number") or 0)
            if section_number > 0:
                sections.add(section_number)
                representation_key = (
                    section_number,
                    str(record.get("subtype") or ""),
                    str(record.get("category") or ""),
                    str(record.get("selection_key") or ""),
                )
                representation_counts[representation_key] = (
                    representation_counts.get(representation_key, 0) + 1
                )
            if section_number > 0 and travel_number > 0:
                section_to_travel.setdefault(section_number, set()).add(travel_number)
                travel_to_sections.setdefault(travel_number, set()).add(section_number)

        for representation_key, count in representation_counts.items():
            if count <= 1:
                continue
            section_number = representation_key[0]
            record = dict(representative)
            record["section_number"] = section_number
            issues.append(make_preflight_issue(
                "DUPLICATE_SECTION_NUMBER",
                PRODUCTION_PREFLIGHT_SEVERITY_ERROR,
                "Section {} occurs {} times for the same production representation in {}.".format(
                    section_number, count, family[0]
                ),
                set_id,
                record,
            ))

        if sections:
            expected = set(range(1, max(sections) + 1))
            missing = sorted(expected - sections)
            if missing:
                issues.append(make_preflight_issue(
                    "SECTION_NUMBER_GAP",
                    PRODUCTION_PREFLIGHT_SEVERITY_ERROR,
                    "{} has a gap in section numbering; missing {}.".format(
                        family[0], ", ".join(str(value) for value in missing)
                    ),
                    set_id,
                    representative,
                ))

        for section_number, travel_values in sorted(section_to_travel.items()):
            if len(travel_values) > 1:
                record = dict(representative)
                record["section_number"] = section_number
                issues.append(make_preflight_issue(
                    "CONFLICTING_TRAVEL_ORDER",
                    PRODUCTION_PREFLIGHT_SEVERITY_ERROR,
                    "Section {} has conflicting travel-order numbers: {}.".format(
                        section_number,
                        ", ".join(str(value) for value in sorted(travel_values)),
                    ),
                    set_id,
                    record,
                ))
        for travel_number, section_values in sorted(travel_to_sections.items()):
            if len(section_values) > 1:
                record = dict(representative)
                record["travel_order_number"] = travel_number
                issues.append(make_preflight_issue(
                    "DUPLICATE_TRAVEL_ORDER",
                    PRODUCTION_PREFLIGHT_SEVERITY_ERROR,
                    "Travel-order number {} is assigned to sections {} in {}.".format(
                        travel_number,
                        ", ".join(str(value) for value in sorted(section_values)),
                        family[0],
                    ),
                    set_id,
                    record,
                ))
    return issues


def _records_by_route_and_subtype(records, subtype):
    grouped = {}
    for record in records or []:
        if str(record.get("subtype") or "") != subtype:
            continue
        grouped.setdefault(_preflight_route_key(record), []).append(record)
    return grouped


def _unique_section_keys(records, subtype):
    result = set()
    for record in records or []:
        if str(record.get("subtype") or "") != subtype:
            continue
        section_number = int(record.get("section_number") or 0)
        if section_number <= 0:
            continue
        result.add((
            _preflight_route_key(record),
            int(record.get("track_number") or 0),
            int(record.get("platform_number") or 0),
            section_number,
        ))
    return result


def _assembly_labels_enabled(settings_obj):
    if settings_obj is None:
        return False
    stored = object_string_property(
        settings_obj, "AssemblyLabelConfigurationJSON", ""
    )
    if not stored:
        return False
    try:
        payload = json.loads(stored)
    except Exception:
        return False
    return bool(payload.get("enabled", False)) if isinstance(payload, dict) else False


def preflight_expected_features(
    records,
    set_id,
    section_config,
    registration_config,
    template_assembly_config,
    settings_obj=None,
    assembly_label_config=None,
):
    issues = []
    section_config = clone_section_config(section_config)
    registration_config = clone_registration_config(registration_config)
    template_assembly_config = clone_template_assembly_config(
        template_assembly_config
    )

    formation_sections = {}
    for record in records or []:
        if str(record.get("subtype") or "") not in (
            "FormationSectionPerimeter", "FormationSectionBody"
        ):
            continue
        section_number = int(record.get("section_number") or 0)
        if section_number > 0:
            formation_sections.setdefault(_preflight_route_key(record), set()).add(
                section_number
            )
    if section_config.get("enabled", False):
        joint_type = registration_config.get("joint_type")
        expected_subtype = ""
        expected_label = ""
        if joint_type == REGISTRATION_HOLES:
            expected_subtype = "RegistrationHole"
            expected_label = "registration-hole"
        elif joint_type in (REGISTRATION_PINS, REGISTRATION_TONGUE):
            expected_subtype = "RegistrationJoint"
            expected_label = "registration-joint"
        if expected_subtype:
            actual_by_route = _records_by_route_and_subtype(
                records, expected_subtype
            )
            for route_key, section_numbers in formation_sections.items():
                expected_count = max(0, len(section_numbers) - 1)
                actual_count = len(actual_by_route.get(route_key, []))
                if actual_count < expected_count:
                    representative = next(
                        record for record in records
                        if _preflight_route_key(record) == route_key
                        and str(record.get("subtype") or "") in (
                            "FormationSectionPerimeter", "FormationSectionBody"
                        )
                    )
                    issues.append(make_preflight_issue(
                        "MISSING_REGISTRATION_FEATURE",
                        PRODUCTION_PREFLIGHT_SEVERITY_ERROR,
                        "Expected {} {} record(s) for {} formation sections, but found {}.".format(
                            expected_count,
                            expected_label,
                            len(section_numbers),
                            actual_count,
                        ),
                        set_id,
                        representative,
                    ))

    if template_assembly_config.get("enabled", False):
        track_sections = _unique_section_keys(records, "TrackTemplateSection")
        if template_assembly_config.get("fixing_holes_enabled", False):
            fixing_holes = _unique_section_keys(records, "TrackTemplateFixingHole")
            missing_holes = sorted(track_sections - fixing_holes)
            for route_key, track_number, _platform_number, section_number in missing_holes:
                representative = next(
                    record for record in records
                    if _preflight_route_key(record) == route_key
                    and int(record.get("track_number") or 0) == track_number
                    and int(record.get("section_number") or 0) == section_number
                    and str(record.get("subtype") or "") == "TrackTemplateSection"
                )
                issues.append(make_preflight_issue(
                    "MISSING_TEMPLATE_FIXING_HOLES",
                    PRODUCTION_PREFLIGHT_SEVERITY_ERROR,
                    "Track {} section {} has no recognised fixing-hole record although fixing holes are enabled.".format(
                        track_number, section_number
                    ),
                    set_id,
                    representative,
                ))

            if template_assembly_config.get("matching_formation_holes", False):
                matching_by_route = _records_by_route_and_subtype(
                    records, "FormationMatchingFixingHole"
                )
                routes_with_sections = sorted({item[0] for item in track_sections})
                for route_key in routes_with_sections:
                    if matching_by_route.get(route_key):
                        continue
                    representative = next(
                        record for record in records
                        if _preflight_route_key(record) == route_key
                        and str(record.get("subtype") or "") == "TrackTemplateSection"
                    )
                    issues.append(make_preflight_issue(
                        "MISSING_FORMATION_MATCHING_HOLES",
                        PRODUCTION_PREFLIGHT_SEVERITY_ERROR,
                        "Matching formation-board fixing holes are enabled but no recognised matching-hole record exists for this route.",
                        set_id,
                        representative,
                    ))

        if template_assembly_config.get("joint_type") != TEMPLATE_JOINT_PLAIN:
            sections_by_route = {}
            for route_key, _track_number, _platform_number, section_number in track_sections:
                sections_by_route.setdefault(route_key, set()).add(section_number)
            joints_by_route = _records_by_route_and_subtype(
                records, "TrackTemplateJoint"
            )
            for route_key, section_numbers in sections_by_route.items():
                expected_count = max(0, len(section_numbers) - 1)
                actual_count = len(joints_by_route.get(route_key, []))
                if actual_count < expected_count:
                    representative = next(
                        record for record in records
                        if _preflight_route_key(record) == route_key
                        and str(record.get("subtype") or "") == "TrackTemplateSection"
                    )
                    issues.append(make_preflight_issue(
                        "MISSING_TEMPLATE_JOINT",
                        PRODUCTION_PREFLIGHT_SEVERITY_ERROR,
                        "Expected {} track-template joint record(s) for {} sections, but found {}.".format(
                            expected_count, len(section_numbers), actual_count
                        ),
                        set_id,
                        representative,
                    ))

    if isinstance(assembly_label_config, dict):
        label_config = clone_assembly_label_config(assembly_label_config)
    elif settings_obj is not None:
        label_config = read_assembly_label_config(settings_obj)
    else:
        label_config = default_assembly_label_config()
    if label_config.get("enabled", False):
        target_groups = _assembly_label_group_records(records)
        label_keys = {
            str(record.get("assembly_label_target_key") or "")
            for record in records or []
            if str(record.get("subtype") or "") == ASSEMBLY_LABEL_SUBTYPE
            and str(record.get("assembly_label_target_key") or "")
        }
        if not target_groups:
            issues.append(make_preflight_issue(
                "NO_ASSEMBLY_LABEL_TARGETS",
                PRODUCTION_PREFLIGHT_SEVERITY_WARNING,
                "Assembly labels are enabled but no eligible track-template, platform or formation-board production parts were found.",
                set_id,
                blocks_export=False,
            ))
        for target_key, grouped_records in sorted(target_groups.items()):
            representative = next(
                (record for record in grouped_records if record.get("category") == EXPORT_CATEGORY_SOLID),
                grouped_records[0],
            )
            statuses = {
                str(record.get("assembly_label_status") or "")
                for record in grouped_records
                if str(record.get("assembly_label_status") or "")
            }
            reasons = sorted({
                str(record.get("assembly_label_reason") or "")
                for record in grouped_records
                if str(record.get("assembly_label_reason") or "")
            })
            if "Skipped" in statuses:
                issues.append(make_preflight_issue(
                    "ASSEMBLY_LABEL_SKIPPED",
                    PRODUCTION_PREFLIGHT_SEVERITY_WARNING,
                    "Assembly label was safely skipped for this part: {}".format(
                        "; ".join(reasons) if reasons else "no safe placement exists"
                    ),
                    set_id,
                    representative,
                    blocks_export=False,
                ))
                continue
            if "Placed" not in statuses:
                issues.append(make_preflight_issue(
                    "MISSING_ASSEMBLY_LABEL_STATUS",
                    PRODUCTION_PREFLIGHT_SEVERITY_ERROR,
                    "Assembly labels are enabled but this eligible production part has no placement result.",
                    set_id,
                    representative,
                ))
                continue
            if target_key not in label_keys:
                issues.append(make_preflight_issue(
                    "MISSING_ASSEMBLY_LABEL_GEOMETRY",
                    PRODUCTION_PREFLIGHT_SEVERITY_ERROR,
                    "The part is marked as labelled but its separate DXF/SVG assembly-label engraving record is missing.",
                    set_id,
                    representative,
                ))
    return issues


def proposed_export_targets(records, config, set_id):
    config = clone_production_export_config(config)
    output_directory = str(config.get("output_directory") or "")
    targets = []
    valid_records = []
    for record in records or []:
        valid, _reason = validate_export_record(record)
        formats = record_compatible_formats(record, config)
        if valid and formats:
            valid_records.append(record)
        if not valid or not formats:
            continue
        is_section = int(record.get("section_number") or 0) > 0
        if not is_section or config.get("export_each_section", True):
            stem = record_filename_stem(record, config, set_id)
            for format_key in formats:
                targets.append({
                    "path": os.path.abspath(os.path.join(
                        output_directory, "{}.{}".format(stem, format_key)
                    )),
                    "format": format_key,
                    "records": [record],
                    "combined": False,
                })

    if config.get("create_combined_files", True):
        for category in (
            EXPORT_CATEGORY_CUTTING,
            EXPORT_CATEGORY_HOLES,
            EXPORT_CATEGORY_JOINTS,
            EXPORT_CATEGORY_ENGRAVING,
        ):
            members = [item for item in valid_records if item.get("category") == category]
            subtypes = {str(item.get("subtype") or "") for item in members}
            if "TrackTemplateSection" in subtypes:
                members = [item for item in members if item.get("subtype") != "TrackTemplateCompound"]
            if "PlatformSection" in subtypes:
                members = [item for item in members if item.get("subtype") != "PlatformPlanOutline"]
            if "FormationSectionPerimeter" in subtypes:
                members = [item for item in members if item.get("subtype") != "FormationPerimeter"]
            if not members:
                continue
            for format_key in (EXPORT_FORMAT_DXF, EXPORT_FORMAT_SVG):
                if not config.get("formats", {}).get(format_key, False):
                    continue
                stem = combined_filename_stem(category, set_id)
                targets.append({
                    "path": os.path.abspath(os.path.join(
                        output_directory, "{}.{}".format(stem, format_key)
                    )),
                    "format": format_key,
                    "records": members,
                    "combined": True,
                })
        solid_members = [
            item for item in valid_records
            if item.get("category") == EXPORT_CATEGORY_SOLID
        ]
        solid_subtypes = {str(item.get("subtype") or "") for item in solid_members}
        if "TrackTemplateSection" in solid_subtypes:
            solid_members = [item for item in solid_members if item.get("subtype") != "TrackTemplateCompound"]
        if "PlatformSection" in solid_subtypes:
            solid_members = [item for item in solid_members if item.get("subtype") != "PlatformBody"]
        if "FormationSectionBody" in solid_subtypes:
            solid_members = [item for item in solid_members if item.get("subtype") != "FormationBody"]
        if solid_members and config.get("formats", {}).get(EXPORT_FORMAT_STEP, False):
            stem = combined_filename_stem(EXPORT_CATEGORY_SOLID, set_id)
            targets.append({
                "path": os.path.abspath(os.path.join(
                    output_directory, "{}.step".format(stem)
                )),
                "format": EXPORT_FORMAT_STEP,
                "records": solid_members,
                "combined": True,
            })
    if config.get("create_manifest", True):
        targets.append({
            "path": os.path.abspath(os.path.join(
                output_directory,
                "Curve_{}_Export_Manifest.csv".format(
                    export_set_filename_token(set_id)
                ),
            )),
            "format": "csv",
            "records": [],
            "combined": True,
        })
    return targets


def preflight_exporter_availability(config, set_id, capabilities=None):
    issues = []
    capabilities = capabilities or detect_exporter_capabilities()
    for format_key, selected in config.get("formats", {}).items():
        if not selected:
            continue
        capability = capabilities.get(format_key, {})
        if capability.get("available", False):
            continue
        issues.append(make_preflight_issue(
            "EXPORTER_UNAVAILABLE",
            PRODUCTION_PREFLIGHT_SEVERITY_ERROR,
            str(capability.get("reason") or "The selected exporter is unavailable."),
            set_id,
            format_key=format_key,
        ))
    return issues


def preflight_export_formats(records, config, set_id):
    issues = []
    for record in records or []:
        supported = _supported_formats_for_category(record.get("category"))
        if not supported:
            issues.append(make_preflight_issue(
                "UNSUPPORTED_EXPORT_CATEGORY",
                PRODUCTION_PREFLIGHT_SEVERITY_ERROR,
                "The production record has no supported export format.",
                set_id,
                record,
            ))
            continue
        compatible = record_compatible_formats(record, config)
        if not compatible:
            issues.append(make_preflight_issue(
                "NO_COMPATIBLE_SELECTED_FORMAT",
                PRODUCTION_PREFLIGHT_SEVERITY_INFORMATION,
                "This production record will be skipped because none of its compatible export formats is selected.",
                set_id,
                record,
                blocks_export=False,
            ))
    return issues


def preflight_filenames_and_overwrites(records, config, set_id):
    issues = []
    targets = proposed_export_targets(records, config, set_id)
    by_path = {}
    for target in targets:
        by_path.setdefault(target["path"], []).append(target)
    for path, path_targets in sorted(by_path.items()):
        if len(path_targets) > 1:
            record = path_targets[0]["records"][0] if path_targets[0]["records"] else None
            issues.append(make_preflight_issue(
                "DUPLICATE_PROPOSED_FILENAME",
                PRODUCTION_PREFLIGHT_SEVERITY_ERROR,
                "{} export tasks propose the same filename before revision allocation.".format(
                    len(path_targets)
                ),
                set_id,
                record,
                path_targets[0].get("format", ""),
                path,
            ))
            continue
        target = path_targets[0]
        record = target["records"][0] if target["records"] else None
        if os.path.exists(path):
            if config.get("overwrite_existing", False):
                issues.append(make_preflight_issue(
                    "EXISTING_FILE_OVERWRITE",
                    PRODUCTION_PREFLIGHT_SEVERITY_WARNING,
                    "The existing export file will be overwritten after confirmation.",
                    set_id,
                    record,
                    target.get("format", ""),
                    path,
                    blocks_export=False,
                ))
            else:
                revision_path = resolve_revision_path(path, False)
                issues.append(make_preflight_issue(
                    "EXISTING_FILE_REVISION",
                    PRODUCTION_PREFLIGHT_SEVERITY_INFORMATION,
                    "The existing file will be preserved; export will use '{}'.".format(
                        os.path.basename(revision_path)
                    ),
                    set_id,
                    record,
                    target.get("format", ""),
                    path,
                    blocks_export=False,
                ))
    return issues, targets


def _probe_writable_directory(directory):
    handle_path = ""
    try:
        descriptor, handle_path = tempfile.mkstemp(
            prefix=".railway_preflight_", suffix=".tmp", dir=directory
        )
        os.close(descriptor)
    except Exception as error:
        return False, str(error)
    finally:
        if handle_path and os.path.exists(handle_path):
            try:
                os.remove(handle_path)
            except Exception:
                pass
    return True, ""


def preflight_output_path(config, set_id):
    issues = []
    directory_text = str(config.get("output_directory") or "").strip()
    if not directory_text:
        issues.append(make_preflight_issue(
            "MISSING_OUTPUT_PATH",
            PRODUCTION_PREFLIGHT_SEVERITY_ERROR,
            "No production export output folder is configured.",
            set_id,
        ))
        return issues
    directory = os.path.abspath(os.path.expanduser(directory_text))
    if os.path.exists(directory) and not os.path.isdir(directory):
        issues.append(make_preflight_issue(
            "OUTPUT_PATH_NOT_DIRECTORY",
            PRODUCTION_PREFLIGHT_SEVERITY_ERROR,
            "The configured production export path exists but is not a directory.",
            set_id,
            proposed_path=directory,
        ))
        return issues
    probe_directory = directory if os.path.isdir(directory) else _nearest_existing_directory(
        os.path.dirname(directory)
    )
    if not probe_directory:
        issues.append(make_preflight_issue(
            "NO_WRITABLE_OUTPUT_PARENT",
            PRODUCTION_PREFLIGHT_SEVERITY_ERROR,
            "No existing parent directory is available for the configured output folder.",
            set_id,
            proposed_path=directory,
        ))
        return issues
    writable, reason = _probe_writable_directory(probe_directory)
    if not writable:
        issues.append(make_preflight_issue(
            "OUTPUT_PATH_NOT_WRITABLE",
            PRODUCTION_PREFLIGHT_SEVERITY_ERROR,
            "The output folder or nearest existing parent is not writable: {}".format(reason),
            set_id,
            proposed_path=probe_directory,
        ))
    elif not os.path.isdir(directory):
        issues.append(make_preflight_issue(
            "OUTPUT_DIRECTORY_WILL_BE_CREATED",
            PRODUCTION_PREFLIGHT_SEVERITY_INFORMATION,
            "The output folder does not yet exist and will be created only after preflight confirmation.",
            set_id,
            proposed_path=directory,
            blocks_export=False,
        ))
    return issues


def validate_dxf_export_bounds(path, tolerance=GEOMETRY_TOLERANCE):
    with open(path, "rb") as handle:
        raw = handle.read()
    if raw.startswith(b"AutoCAD Binary DXF"):
        raise ValueError("Binary DXF bounds cannot be validated safely.")
    try:
        text = raw.decode("utf-8")
    except UnicodeDecodeError:
        text = raw.decode("latin-1")
    lines = text.splitlines()
    if len(lines) < 2:
        raise ValueError("The DXF file is empty or incomplete.")
    pairs = []
    for index in range(0, len(lines) - 1, 2):
        pairs.append((lines[index].strip(), lines[index + 1].strip()))
    in_entities = False
    entity_count = 0
    x_values = []
    y_values = []
    radii = []
    index = 0
    while index < len(pairs):
        code, value = pairs[index]
        upper = value.upper()
        if code == "0" and upper == "SECTION" and index + 1 < len(pairs):
            next_code, next_value = pairs[index + 1]
            in_entities = next_code == "2" and next_value.upper() == "ENTITIES"
            index += 1
        elif code == "0" and upper == "ENDSEC":
            in_entities = False
        elif in_entities:
            if code == "0" and upper not in ("SEQEND", "ENDSEC"):
                entity_count += 1
            try:
                numeric = float(value)
            except Exception:
                numeric = None
            if numeric is not None:
                try:
                    group_code = int(code)
                except Exception:
                    group_code = -1
                if 10 <= group_code <= 18:
                    x_values.append(numeric)
                elif 20 <= group_code <= 28:
                    y_values.append(numeric)
                elif group_code == 40:
                    radii.append(abs(numeric))
        index += 1
    if entity_count <= 0:
        raise ValueError("The DXF file contains no geometry entities.")
    if not x_values and not y_values and not radii:
        raise ValueError("The DXF geometry has no measurable bounds.")
    x_span = max(x_values) - min(x_values) if x_values else 0.0
    y_span = max(y_values) - min(y_values) if y_values else 0.0
    radius = max(radii) if radii else 0.0
    if x_span <= tolerance and y_span <= tolerance and radius <= tolerance:
        raise ValueError("The DXF geometry has empty bounds.")
    return {
        "x_span": max(0.0, x_span),
        "y_span": max(0.0, y_span),
        "maximum_radius": max(0.0, radius),
    }


def validate_svg_export_bounds(path):
    validate_svg_millimetre_scale(path)
    root = ET.parse(path).getroot()
    view_box = str(root.attrib.get("viewBox", root.attrib.get("viewbox", ""))).strip()
    values = [float(value) for value in re.split(r"[ ,]+", view_box)]
    if len(values) != 4 or values[2] <= 0.0 or values[3] <= 0.0:
        raise ValueError("The SVG geometry has empty bounds.")
    return {"x_span": values[2], "y_span": values[3]}


def _create_isolated_preflight_document():
    creator = getattr(App, "newDocument", None)
    if not callable(creator):
        raise ValueError(
            "FreeCAD cannot create the isolated temporary document required for exporter-bound preflight probes."
        )
    name = "RailwayPreflight_{}".format(uuid.uuid4().hex[:12])
    return creator(name)


def _close_isolated_preflight_document(probe_doc, original_document_name=""):
    if probe_doc is not None:
        closer = getattr(App, "closeDocument", None)
        if callable(closer):
            try:
                closer(str(getattr(probe_doc, "Name", "")))
            except Exception:
                pass
    if original_document_name:
        setter = getattr(App, "setActiveDocument", None)
        if callable(setter):
            try:
                setter(original_document_name)
            except Exception:
                pass
        if Gui is not None:
            gui_setter = getattr(Gui, "activeDocument", None)
            if callable(gui_setter):
                try:
                    active = gui_setter()
                    if active is not None and hasattr(active, "activeView"):
                        active.activeView()
                except Exception:
                    pass


def probe_2d_export_bounds(
    doc,
    plan,
    set_id,
    exporter_override=None,
):
    issues = []
    tasks = [
        task for task in (plan or {}).get("tasks", [])
        if task.get("format") in (EXPORT_FORMAT_DXF, EXPORT_FORMAT_SVG)
    ]
    if not tasks:
        return issues
    original_document_name = str(getattr(doc, "Name", "") or "")
    probe_doc = doc
    isolated_document = None
    if exporter_override is None:
        try:
            isolated_document = _create_isolated_preflight_document()
            probe_doc = isolated_document
        except Exception as error:
            issues.append(make_preflight_issue(
                "ISOLATED_PROBE_DOCUMENT_FAILURE",
                PRODUCTION_PREFLIGHT_SEVERITY_ERROR,
                str(error),
                set_id,
            ))
            return issues
    try:
        with tempfile.TemporaryDirectory(prefix="railway_preflight_") as directory:
            for index, task in enumerate(tasks):
                format_key = str(task.get("format") or "")
                path = os.path.join(
                    directory,
                    "probe_{:05d}.{}".format(index + 1, format_key),
                )
                try:
                    if exporter_override is None:
                        dispatch_freecad_export(probe_doc, task, path)
                    else:
                        exporter_override(probe_doc, task, path)
                    if not os.path.isfile(path) or os.path.getsize(path) <= 0:
                        raise ValueError("The exporter probe produced no file data.")
                    if format_key == EXPORT_FORMAT_DXF:
                        validate_dxf_export_bounds(path)
                    else:
                        validate_svg_export_bounds(path)
                except Exception as error:
                    record = (
                        task.get("records", [None])[0]
                        if task.get("records") else None
                    )
                    issues.append(make_preflight_issue(
                        "EMPTY_OR_INVALID_EXPORT_BOUNDS",
                        PRODUCTION_PREFLIGHT_SEVERITY_ERROR,
                        "Temporary {} exporter-bound probe failed: {}".format(
                            EXPORT_FORMAT_LABELS.get(
                                format_key, format_key.upper()
                            ),
                            error,
                        ),
                        set_id,
                        record,
                        format_key,
                        task.get("path", ""),
                    ))
    finally:
        if isolated_document is not None:
            _close_isolated_preflight_document(
                isolated_document, original_document_name
            )
    return issues


def preflight_crossover_production_readiness(doc, records, set_id):
    """Block production export for stale or chair-unvalidated integrated crossovers.

    The helper deliberately keys from production-record metadata rather than
    object labels, so selected-item and whole-set preflight use the same stable
    crossover identity.
    """
    integrated_subtypes = {
        "TrackTemplateCrossoverIntegrated",
        "CrossoverResolvedTimberGeometry",
    }
    representative_by_id = {}
    for record in records or []:
        if str(record.get("subtype") or "") not in integrated_subtypes:
            continue
        identifier = str(record.get("route_id") or "").strip()
        if identifier:
            representative_by_id.setdefault(identifier, record)
    issues = []
    for identifier in sorted(representative_by_id):
        record = representative_by_id[identifier]
        try:
            config = crossover_config_by_id(doc, identifier)
        except Exception:
            config = None
        if config is None:
            issues.append(make_preflight_issue(
                "CROSSOVER_INTEGRATION_METADATA_MISSING",
                PRODUCTION_PREFLIGHT_SEVERITY_ERROR,
                "Integrated crossover {} has no readable managed-crossover configuration.".format(identifier),
                set_id,
                record,
            ))
            continue
        status = crossover_host_integration_effective_status(doc, config)
        if status != CROSSOVER_INTEGRATION_STATUS_ACTIVE:
            issues.append(make_preflight_issue(
                "CROSSOVER_HOST_INTEGRATION_NOT_CURRENT",
                PRODUCTION_PREFLIGHT_SEVERITY_ERROR,
                "Integrated crossover {} is not current ({}). Remove or rebuild its host integration before production export.".format(identifier, status),
                set_id,
                record,
            ))
            continue
        if not bool(config.get("production_ready", False)):
            issues.append(make_preflight_issue(
                "CROSSOVER_CHAIR_VALIDATION_OUTSTANDING",
                PRODUCTION_PREFLIGHT_SEVERITY_WARNING,
                "Integrated crossover {} has validated timbering and host integration, but chair assignment and fit validation remain outstanding; exported geometry is not yet a chair-validated production assembly.".format(identifier),
                set_id,
                record,
                blocks_export=False,
            ))
    return issues


def run_production_preflight(
    doc,
    catalogue_records,
    export_records,
    config,
    set_id,
    section_config,
    registration_config,
    template_assembly_config,
    settings_obj=None,
    assembly_label_config=None,
    plan=None,
    include_export_checks=True,
    probe_export_bounds=True,
    exporter_override=None,
    exporter_capabilities=None,
    filename_issues_override=None,
):
    catalogue_records = list(catalogue_records or [])
    export_records = list(export_records or [])
    issues = []
    format_issues = []
    if include_export_checks:
        format_issues = preflight_export_formats(export_records, config, set_id)
        checked_records = [
            record for record in export_records
            if record_compatible_formats(record, config)
        ]
    else:
        checked_records = catalogue_records
    if not checked_records:
        issues.extend(format_issues)
        if include_export_checks and export_records:
            issues.append(make_preflight_issue(
                "NO_COMPATIBLE_SELECTED_FORMATS",
                PRODUCTION_PREFLIGHT_SEVERITY_ERROR,
                "None of the selected production records supports the selected export formats.",
                set_id,
            ))
        else:
            issues.append(make_preflight_issue(
                "NO_MATCHING_PRODUCTION_RECORDS",
                PRODUCTION_PREFLIGHT_SEVERITY_ERROR,
                "No valid production records match the requested preflight scope.",
                set_id,
            ))
        return sort_preflight_issues(issues)

    issues.extend(preflight_metadata_and_geometry(checked_records, set_id))
    issues.extend(preflight_crossover_production_readiness(doc, checked_records, set_id))
    issues.extend(preflight_chair_analysis_readiness(doc, checked_records, set_id))
    issues.extend(preflight_numbering(catalogue_records, set_id))
    issues.extend(preflight_expected_features(
        catalogue_records,
        set_id,
        section_config,
        registration_config,
        template_assembly_config,
        settings_obj,
        assembly_label_config,
    ))

    if include_export_checks:
        issues.extend(preflight_exporter_availability(
            config, set_id, exporter_capabilities
        ))
        issues.extend(format_issues)
        issues.extend(preflight_output_path(config, set_id))
        if filename_issues_override is None:
            filename_issues, _targets = preflight_filenames_and_overwrites(
                export_records, config, set_id
            )
        else:
            filename_issues = list(filename_issues_override or [])
        issues.extend(filename_issues)
        if plan is None:
            try:
                plan = plan_production_export(export_records, config, set_id)
            except Exception as error:
                issues.append(make_preflight_issue(
                    "EXPORT_PLAN_FAILURE",
                    PRODUCTION_PREFLIGHT_SEVERITY_ERROR,
                    "The export plan could not be created: {}".format(error),
                    set_id,
                ))
        if plan is not None and probe_export_bounds:
            issues.extend(probe_2d_export_bounds(
                doc, plan, set_id, exporter_override
            ))
    else:
        issues.append(make_preflight_issue(
            "EXPORT_CHECKS_NOT_REQUESTED",
            PRODUCTION_PREFLIGHT_SEVERITY_INFORMATION,
            "Metadata, geometry, numbering and expected-feature checks ran without filename, path or exporter-bound probes.",
            set_id,
            blocks_export=False,
        ))
    return sort_preflight_issues(issues)


def preflight_blocking_report(issues, limit=20):
    blocking = [
        issue for issue in issues or [] if issue.get("blocks_export", False)
    ]
    if not blocking:
        return ""
    lines = [
        "Production preflight found {} export-blocking error{}:".format(
            len(blocking), "" if len(blocking) == 1 else "s"
        )
    ]
    for issue in blocking[:limit]:
        identity = _export_record_report_name({
            "source_name": issue.get("source_name", ""),
            "route_name": issue.get("route_name", ""),
            "track_number": issue.get("track_number", 0),
            "track_name": issue.get("track_name", ""),
            "platform_number": issue.get("platform_number", 0),
            "platform_name": issue.get("platform_name", ""),
            "section_number": issue.get("section_number", 0),
        })
        lines.append("- {} — {}: {}".format(
            issue.get("issue_code", "ERROR"), identity, issue.get("message", "")
        ))
    if len(blocking) > limit:
        lines.append("- ...and {} more error(s).".format(len(blocking) - limit))
    lines.append("No generated object or existing export file has been changed.")
    return "\n".join(lines)


def confirm_preflight_warnings(issues):
    warnings = [
        issue for issue in issues or []
        if issue.get("severity") == PRODUCTION_PREFLIGHT_SEVERITY_WARNING
    ]
    if not warnings:
        return True
    if Gui is None:
        return False
    try:
        yes_button = QtWidgets.QMessageBox.Yes
        no_button = QtWidgets.QMessageBox.No
    except AttributeError:
        yes_button = QtWidgets.QMessageBox.StandardButton.Yes
        no_button = QtWidgets.QMessageBox.StandardButton.No
    lines = [
        "Production preflight found {} warning{}:".format(
            len(warnings), "" if len(warnings) == 1 else "s"
        )
    ]
    for issue in warnings[:12]:
        lines.append("- {}: {}".format(
            issue.get("issue_code", "WARNING"), issue.get("message", "")
        ))
    if len(warnings) > 12:
        lines.append("- ...and {} more warning(s).".format(len(warnings) - 12))
    lines.append("\nContinue with production generation and export?")
    answer = QtWidgets.QMessageBox.question(
        None,
        versioned_dialog_title("Production preflight warnings"),
        "\n".join(lines),
        yes_button | no_button,
        no_button,
    )
    return answer == yes_button


class ProductionPreflightDialog(QtWidgets.QDialog):
    def __init__(self, doc, parent=None):
        super(ProductionPreflightDialog, self).__init__(parent)
        self.doc = doc
        self.issues = []
        self.setWindowTitle(versioned_dialog_title("Production preflight"))
        self.resize(1580, 780)

        layout = QtWidgets.QVBoxLayout(self)
        top_layout = QtWidgets.QHBoxLayout()
        top_layout.addWidget(QtWidgets.QLabel("Template set:"))
        self.set_box = QtWidgets.QComboBox()
        self.set_box.addItems(generated_template_set_ids(doc))
        top_layout.addWidget(self.set_box)
        self.export_checks_box = QtWidgets.QCheckBox(
            "Include configured filename and output-path checks"
        )
        self.export_checks_box.setChecked(True)
        top_layout.addWidget(self.export_checks_box)
        self.probe_box = QtWidgets.QCheckBox(
            "Run temporary SVG/DXF exporter-bound probes"
        )
        self.probe_box.setChecked(True)
        top_layout.addWidget(self.probe_box)
        self.run_button = QtWidgets.QPushButton("Run preflight")
        top_layout.addWidget(self.run_button)
        top_layout.addStretch(1)
        layout.addLayout(top_layout)

        self.summary_label = QtWidgets.QLabel("")
        self.summary_label.setWordWrap(True)
        layout.addWidget(self.summary_label)

        self.table = QtWidgets.QTableWidget(0, len(PRODUCTION_PREFLIGHT_FIELDS))
        self.table.setHorizontalHeaderLabels(PRODUCTION_PREFLIGHT_FIELDS)
        try:
            self.table.setEditTriggers(QtWidgets.QAbstractItemView.NoEditTriggers)
            self.table.setSelectionBehavior(QtWidgets.QAbstractItemView.SelectRows)
        except AttributeError:
            self.table.setEditTriggers(
                QtWidgets.QAbstractItemView.EditTrigger.NoEditTriggers
            )
            self.table.setSelectionBehavior(
                QtWidgets.QAbstractItemView.SelectionBehavior.SelectRows
            )
        self.table.setAlternatingRowColors(True)
        self.table.setSortingEnabled(False)
        layout.addWidget(self.table, 1)

        button_layout = QtWidgets.QHBoxLayout()
        button_layout.addStretch(1)
        close_button = QtWidgets.QPushButton("Close")
        button_layout.addWidget(close_button)
        layout.addLayout(button_layout)

        self.run_button.clicked.connect(self.refresh_preview)
        self.set_box.currentIndexChanged.connect(self.refresh_preview)
        self.export_checks_box.toggled.connect(self._export_checks_toggled)
        close_button.clicked.connect(self.accept)
        self._export_checks_toggled(self.export_checks_box.isChecked())
        self.refresh_preview()

    def _export_checks_toggled(self, enabled):
        self.probe_box.setEnabled(bool(enabled))

    def _selected_set_id(self):
        return str(self.set_box.currentText() or "").strip()

    def refresh_preview(self, *_args):
        set_id = self._selected_set_id()
        self.table.setRowCount(0)
        if not set_id:
            self.summary_label.setText(
                "No recognised generated template set exists in the active document."
            )
            return
        settings = settings_for_template_set(self.doc, set_id)
        index_payload = production_record_index_for_set(self.doc, set_id)
        catalogue_records = hydrate_production_index_records(
            self.doc, index_payload
        )
        export_config = read_production_export_config(settings)
        include_export_checks = bool(self.export_checks_box.isChecked())
        if include_export_checks:
            export_records = filter_records_for_export_config(
                catalogue_records, export_config
            )
            if not export_records and index_payload.get("legacy_scan", False):
                export_records = list(catalogue_records)
        else:
            export_records = list(catalogue_records)
        plan = None
        if include_export_checks and export_records:
            try:
                plan = plan_production_export(
                    export_records, export_config, set_id
                )
            except Exception:
                plan = None
        self.issues = run_production_preflight(
            self.doc,
            catalogue_records,
            export_records,
            export_config,
            set_id,
            read_section_config(settings),
            read_registration_config(settings),
            read_template_assembly_config(settings),
            settings_obj=settings,
            plan=plan,
            include_export_checks=include_export_checks,
            probe_export_bounds=(
                include_export_checks and self.probe_box.isChecked()
            ),
        )
        counts = summarise_preflight(self.issues)
        legacy_text = (
            " Legacy metadata scan in use; regenerate deliberately under Version {} for the full persistent catalogue.".format(
                MACRO_VERSION_NUMBER
            )
            if index_payload.get("legacy_scan", False) else ""
        )
        self.summary_label.setText(
            "{}: {} error(s), {} warning(s), {} information item(s); {} blocking issue(s).{}".format(
                set_id,
                counts.get(PRODUCTION_PREFLIGHT_SEVERITY_ERROR, 0),
                counts.get(PRODUCTION_PREFLIGHT_SEVERITY_WARNING, 0),
                counts.get(PRODUCTION_PREFLIGHT_SEVERITY_INFORMATION, 0),
                counts.get("blocking", 0),
                legacy_text,
            )
        )
        self.table.setRowCount(len(self.issues))
        for row_index, issue in enumerate(self.issues):
            row = preflight_issue_row(issue)
            for column_index, field in enumerate(PRODUCTION_PREFLIGHT_FIELDS):
                self.table.setItem(
                    row_index,
                    column_index,
                    QtWidgets.QTableWidgetItem(str(row.get(field, ""))),
                )
        try:
            self.table.resizeColumnsToContents()
        except Exception:
            pass



def _selected_export_route_key(record):
    return str(record.get("route_id") or "")


def _selected_export_route_label(record):
    route_name = str(record.get("route_name") or "").strip()
    route_id = str(record.get("route_id") or "").strip()
    if route_name:
        return route_name
    if route_id:
        return route_id
    return "Curve route"


def selected_export_route_options(records):
    options = {}
    for record in records or []:
        route_id = _selected_export_route_key(record)
        options.setdefault(route_id, _selected_export_route_label(record))
    return [
        {"value": route_id, "label": options[route_id]}
        for route_id in sorted(
            options,
            key=lambda value: (0 if value == "" else 1, options[value].casefold(), value),
        )
    ]


def _selected_export_is_formation_record(record):
    subtype = str(record.get("subtype") or "")
    role = str(record.get("role") or "")
    return (
        subtype.startswith("Formation")
        or (subtype == ASSEMBLY_LABEL_SUBTYPE and str(record.get("assembly_label_target_family") or "").startswith("Formation"))
        or subtype in ("RegistrationHole", "RegistrationJoint")
        or "Formation" in role
        or "Registration" in role
        or role.endswith("AlignmentHole")
    )


def selected_export_target_options(records, scope_type, route_id):
    route_records = [
        record for record in records or []
        if _selected_export_route_key(record) == str(route_id or "")
    ]
    options = []
    if scope_type == SELECTED_EXPORT_SCOPE_SECTION:
        values = sorted({
            int(record.get("section_number") or 0)
            for record in route_records
            if int(record.get("section_number") or 0) > 0
        })
        options = [
            {"value": value, "label": "Section {:02d}".format(value)}
            for value in values
        ]
    elif scope_type == SELECTED_EXPORT_SCOPE_TRACK:
        values = {}
        for record in route_records:
            number = int(record.get("track_number") or 0)
            if number <= 0:
                continue
            values.setdefault(
                number,
                str(record.get("track_name") or "Track {}".format(number)),
            )
        options = [
            {
                "value": number,
                "label": "Track {:02d} — {}".format(number, values[number]),
            }
            for number in sorted(values)
        ]
    elif scope_type == SELECTED_EXPORT_SCOPE_PLATFORM:
        values = {}
        for record in route_records:
            number = int(record.get("platform_number") or 0)
            if number <= 0:
                continue
            values.setdefault(
                number,
                str(record.get("platform_name") or "Platform {}".format(number)),
            )
        options = [
            {
                "value": number,
                "label": "Platform {:02d} — {}".format(number, values[number]),
            }
            for number in sorted(values)
        ]
    return options


def selected_export_object_record_ids(obj):
    record_ids = set()
    single = object_string_property(obj, PRODUCTION_RECORD_ID_PROPERTY, "")
    if single:
        record_ids.add(single)
    stored = object_string_property(obj, PRODUCTION_RECORD_IDS_PROPERTY, "")
    if stored:
        try:
            payload = json.loads(stored)
        except Exception:
            payload = []
        if isinstance(payload, list):
            record_ids.update(
                str(value).strip() for value in payload if str(value).strip()
            )
    return record_ids


def selected_export_selection_snapshot(doc, set_id):
    selected = []
    if Gui is None:
        return selected
    try:
        objects = list(Gui.Selection.getSelection())
    except Exception:
        objects = []
    for obj in objects:
        object_set_id = object_string_property(obj, "TemplateSetID", "")
        record_ids = selected_export_object_record_ids(obj)
        if object_set_id and object_set_id != set_id:
            continue
        selected.append({
            "name": str(getattr(obj, "Name", "")),
            "label": str(getattr(obj, "Label", getattr(obj, "Name", ""))),
            "record_ids": record_ids,
            "generated_role": object_string_property(obj, "GeneratedRole", ""),
            "export_subtype": object_string_property(obj, "ExportSubtype", ""),
            "route_id": object_string_property(obj, "RouteID", ""),
            "track_number": _integer_object_property(obj, "TrackNumber", 0),
            "platform_number": _integer_object_property(obj, "PlatformNumber", 0),
            "section_number": _integer_object_property(obj, "SectionNumber", 0),
            "feature_number": _integer_object_property(obj, "FeatureNumber", 0),
        })
    return selected


def selected_export_scope_description(scope):
    scope_type = str(scope.get("scope_type") or "")
    route_label = str(scope.get("route_label") or "Curve route")
    if scope_type == SELECTED_EXPORT_SCOPE_OBJECTS:
        highlighted_count = len(scope.get("highlighted_record_ids") or [])
        if highlighted_count:
            return "{} highlighted production record{}".format(
                highlighted_count, "" if highlighted_count == 1 else "s"
            )
        count = len(scope.get("selected_objects") or [])
        return "{} selected FreeCAD object{}".format(count, "" if count == 1 else "s")
    if scope_type == SELECTED_EXPORT_SCOPE_SECTION:
        return "{} / section {:02d}".format(route_label, int(scope.get("section_number") or 0))
    if scope_type == SELECTED_EXPORT_SCOPE_TRACK:
        return "{} / track {:02d}".format(route_label, int(scope.get("track_number") or 0))
    if scope_type == SELECTED_EXPORT_SCOPE_PLATFORM:
        return "{} / platform {:02d}".format(route_label, int(scope.get("platform_number") or 0))
    if scope_type == SELECTED_EXPORT_SCOPE_FORMATION:
        return "{} / formation board".format(route_label)
    if scope_type == SELECTED_EXPORT_SCOPE_ROUTE:
        return route_label
    return "complete template set"


def selected_export_scope_token(scope):
    scope_type = str(scope.get("scope_type") or "")
    route_text = str(scope.get("route_id") or scope.get("route_label") or "Curve")
    route_token = safe_filename_component(route_text, "Curve")
    if scope_type == SELECTED_EXPORT_SCOPE_TEMPLATE_SET:
        return ""
    if scope_type == SELECTED_EXPORT_SCOPE_OBJECTS:
        identifiers = sorted({
            str(record_id)
            for record_id in scope.get("highlighted_record_ids") or []
            if str(record_id)
        })
        if not identifiers:
            identifiers = sorted({
                record_id
                for item in scope.get("selected_objects") or []
                for record_id in item.get("record_ids", set())
            })
        if not identifiers:
            identifiers = sorted(
                str(item.get("name") or "")
                for item in scope.get("selected_objects") or []
            )
        digest = hashlib.sha1("|".join(identifiers).encode("utf-8")).hexdigest()[:8]
        return "Selected_Objects_{}".format(digest)
    if scope_type == SELECTED_EXPORT_SCOPE_SECTION:
        return "{}_Section_{:03d}".format(route_token, int(scope.get("section_number") or 0))
    if scope_type == SELECTED_EXPORT_SCOPE_TRACK:
        return "{}_Track_{:02d}".format(route_token, int(scope.get("track_number") or 0))
    if scope_type == SELECTED_EXPORT_SCOPE_PLATFORM:
        return "{}_Platform_{:02d}".format(route_token, int(scope.get("platform_number") or 0))
    if scope_type == SELECTED_EXPORT_SCOPE_FORMATION:
        return "{}_Formation_Board".format(route_token)
    if scope_type == SELECTED_EXPORT_SCOPE_ROUTE:
        return "{}_Route".format(route_token)
    return safe_filename_component(scope_type, "Selected")


def _selected_export_physical_item_family(record):
    """Group 2D, 3D and assembly-label representations of one production part."""
    subtype = str(record.get("subtype") or "")
    if subtype == ASSEMBLY_LABEL_SUBTYPE:
        return str(record.get("assembly_label_target_family") or "")
    families = {
        "TrackTemplateCompound": "TrackTemplateCompound",
        "TrackTemplateSection": "TrackTemplateSection",
        "PlatformBody": "PlatformComplete",
        "PlatformPlanOutline": "PlatformComplete",
        "PlatformSection": "PlatformSection",
        "PlatformSectionOutline": "PlatformSection",
        "FormationBody": "FormationComplete",
        "FormationPerimeter": "FormationComplete",
        "FormationSectionBody": "FormationSection",
        "FormationSectionPerimeter": "FormationSection",
    }
    return families.get(subtype, subtype)


def _selected_export_physical_item_key(record):
    """Return a semantic item key without using document names or GUI row numbers."""
    return (
        _selected_export_route_key(record),
        _selected_export_physical_item_family(record),
        int(record.get("track_number") or 0),
        int(record.get("platform_number") or 0),
        int(record.get("section_number") or 0),
        int(
            record.get("assembly_label_target_feature_number")
            if str(record.get("subtype") or "") == ASSEMBLY_LABEL_SUBTYPE
            else record.get("feature_number") or 0
        ),
    )


def _expand_selected_object_representations(records, seed_records):
    """Include compatible 2D/3D representations belonging to a selected physical item."""
    keys = {
        _selected_export_physical_item_key(record)
        for record in seed_records or []
        if _selected_export_physical_item_family(record)
    }
    if not keys:
        return list(seed_records or [])
    expanded = []
    seen = set()
    for record in records or []:
        record_id = str(record.get("record_id") or "")
        if _selected_export_physical_item_key(record) not in keys:
            continue
        identity = record_id or id(record)
        if identity in seen:
            continue
        seen.add(identity)
        expanded.append(record)
    return expanded


def _selected_export_record_matches_object_metadata(record, selected_object):
    """Match a visible generated object when its detailed records use hidden sources."""
    selected_subtype = str(selected_object.get("export_subtype") or "")
    selected_role = str(selected_object.get("generated_role") or "")
    if not selected_subtype and not selected_role:
        return False
    if selected_subtype:
        if str(record.get("subtype") or "") != selected_subtype:
            return False
    elif str(record.get("role") or "") != selected_role:
        return False
    if _selected_export_route_key(record) != str(selected_object.get("route_id") or ""):
        return False
    for field in (
        "track_number", "platform_number", "section_number", "feature_number"
    ):
        selected_value = int(selected_object.get(field) or 0)
        if selected_value > 0 and int(record.get(field) or 0) != selected_value:
            return False
    return True


def filter_production_records_by_selected_scope(records, scope):
    scope_type = str(scope.get("scope_type") or "")
    route_id = str(scope.get("route_id") or "")
    if scope_type == SELECTED_EXPORT_SCOPE_TEMPLATE_SET:
        return list(records or [])
    if scope_type == SELECTED_EXPORT_SCOPE_OBJECTS:
        selected_objects = list(scope.get("selected_objects") or [])
        selected_ids = {
            record_id
            for item in selected_objects
            for record_id in item.get("record_ids", set())
        }
        selected_names = {
            str(item.get("name") or "") for item in selected_objects
            if str(item.get("name") or "")
        }
        matches = []
        for record in records or []:
            record_id = str(record.get("record_id") or "")
            source_name = str(record.get("source_name") or "")
            source_names = set(filter(None, source_name.replace("::", "+").split("+")))
            semantic_match = any(
                _selected_export_record_matches_object_metadata(record, item)
                for item in selected_objects
            )
            if (
                (record_id and record_id in selected_ids)
                or (source_names & selected_names)
                or semantic_match
            ):
                matches.append(record)
        # A visible FreeCAD part can have separate hidden source records for its
        # 2D and 3D export representations. Expand only those representations of
        # the same semantic physical item so selecting the visible part works for
        # every compatible chosen format.
        return _expand_selected_object_representations(records, matches)

    route_records = [
        record for record in records or []
        if _selected_export_route_key(record) == route_id
    ]
    if scope_type == SELECTED_EXPORT_SCOPE_ROUTE:
        return route_records
    if scope_type == SELECTED_EXPORT_SCOPE_SECTION:
        number = int(scope.get("section_number") or 0)
        return [
            record for record in route_records
            if int(record.get("section_number") or 0) == number
        ]
    if scope_type == SELECTED_EXPORT_SCOPE_TRACK:
        number = int(scope.get("track_number") or 0)
        return [
            record for record in route_records
            if int(record.get("track_number") or 0) == number
        ]
    if scope_type == SELECTED_EXPORT_SCOPE_PLATFORM:
        number = int(scope.get("platform_number") or 0)
        return [
            record for record in route_records
            if int(record.get("platform_number") or 0) == number
        ]
    if scope_type == SELECTED_EXPORT_SCOPE_FORMATION:
        return [record for record in route_records if _selected_export_is_formation_record(record)]
    return []


def selected_export_records_for_formats(records, config):
    export_records = []
    skipped = []
    for record in records or []:
        supported = _supported_formats_for_category(record.get("category"))
        if not supported:
            export_records.append(record)
            continue
        compatible = record_compatible_formats(record, config)
        if compatible:
            export_records.append(record)
        else:
            skipped.append({
                "record": record,
                "format": "",
                "reason": "No selected export format is compatible with this production record.",
            })
    return export_records, skipped


def selected_export_validation_records(catalogue_records, selected_records, scope):
    if str(scope.get("scope_type") or "") == SELECTED_EXPORT_SCOPE_TEMPLATE_SET:
        return list(catalogue_records or [])
    route_ids = {
        _selected_export_route_key(record) for record in selected_records or []
    }
    if not route_ids:
        route_ids.add(str(scope.get("route_id") or ""))
    return [
        record for record in catalogue_records or []
        if _selected_export_route_key(record) in route_ids
    ]


def _selected_export_desired_path(task, config, set_id, scope):
    output_directory = str(config.get("output_directory") or "")
    format_key = str(task.get("format") or "")
    if not task.get("combined", False):
        record = (task.get("records") or [{}])[0]
        stem = record_filename_stem(record, config, set_id)
        return os.path.join(output_directory, "{}.{}".format(stem, format_key))
    scope_token = selected_export_scope_token(scope)
    if not scope_token:
        stem = combined_filename_stem(task.get("category"), set_id)
    else:
        stem = "Curve_{}_{}_{}".format(
            export_set_filename_token(set_id),
            scope_token,
            EXPORT_CATEGORY_COMBINED_NAMES.get(
                task.get("category"), "Combined_Output"
            ),
        )
    return os.path.join(output_directory, "{}.{}".format(stem, format_key))


def plan_selected_production_export(records, config, set_id, scope):
    plan = plan_production_export(records, config, set_id)
    overwrite = bool(config.get("overwrite_existing", False))
    reserved = set()
    desired_counts = {}
    desired_paths = []
    for task in plan.get("tasks", []):
        desired = os.path.abspath(_selected_export_desired_path(
            task, config, set_id, scope
        ))
        task["desired_path"] = desired
        task["path"] = allocate_export_path(
            desired, overwrite, reserved, desired_counts
        )
        reserved.add(task["path"])
        desired_paths.append(desired)

    manifest_path = ""
    manifest_desired = ""
    if config.get("create_manifest", True):
        scope_token = selected_export_scope_token(scope)
        if scope_token:
            filename = "Curve_{}_{}_Export_Manifest.csv".format(
                export_set_filename_token(set_id), scope_token
            )
        else:
            filename = "Curve_{}_Export_Manifest.csv".format(
                export_set_filename_token(set_id)
            )
        manifest_desired = os.path.abspath(os.path.join(
            str(config.get("output_directory") or ""), filename
        ))
        manifest_path = allocate_export_path(
            manifest_desired, overwrite, reserved, desired_counts
        )
        reserved.add(manifest_path)
        desired_paths.append(manifest_desired)
    plan["manifest_path"] = manifest_path
    plan["manifest_desired_path"] = manifest_desired
    plan["reserved_paths"] = reserved
    plan["desired_paths"] = desired_paths
    plan["selected_scope"] = dict(scope)
    return plan


def selected_export_filename_issues(plan, config, set_id):
    issues = []
    by_desired = {}
    for task in plan.get("tasks", []):
        desired = str(task.get("desired_path") or task.get("path") or "")
        by_desired.setdefault(os.path.abspath(desired), []).append(task)
    manifest_desired = str(plan.get("manifest_desired_path") or "")
    if manifest_desired:
        by_desired.setdefault(os.path.abspath(manifest_desired), []).append({
            "format": "csv", "records": [], "combined": True,
            "path": plan.get("manifest_path", ""),
        })

    overwrite = bool(config.get("overwrite_existing", False))
    for desired, tasks in sorted(by_desired.items()):
        if len(tasks) > 1:
            record = (tasks[0].get("records") or [None])[0]
            issues.append(make_preflight_issue(
                "DUPLICATE_PROPOSED_FILENAME",
                PRODUCTION_PREFLIGHT_SEVERITY_ERROR,
                "{} selected export tasks propose the same filename before revision allocation.".format(len(tasks)),
                set_id,
                record,
                tasks[0].get("format", ""),
                desired,
            ))
            continue
        task = tasks[0]
        record = (task.get("records") or [None])[0]
        actual = str(task.get("path") or desired)
        if os.path.exists(desired):
            if overwrite:
                issues.append(make_preflight_issue(
                    "EXISTING_FILE_OVERWRITE",
                    PRODUCTION_PREFLIGHT_SEVERITY_WARNING,
                    "The existing selected-export file will be overwritten only after every staged output succeeds.",
                    set_id,
                    record,
                    task.get("format", ""),
                    desired,
                    blocks_export=False,
                ))
            else:
                issues.append(make_preflight_issue(
                    "EXISTING_FILE_REVISION",
                    PRODUCTION_PREFLIGHT_SEVERITY_INFORMATION,
                    "The existing file will be preserved; selected export will use '{}'.".format(os.path.basename(actual)),
                    set_id,
                    record,
                    task.get("format", ""),
                    desired,
                    blocks_export=False,
                ))
    return issues


def selected_export_preflight_config(config, plan):
    """Limit exporter availability checks to formats actually present in the selected plan."""
    effective = clone_production_export_config(config)
    used_formats = {
        str(task.get("format") or "")
        for task in (plan or {}).get("tasks", [])
        if str(task.get("format") or "")
    }
    effective["formats"] = {
        format_key: format_key in used_formats
        for format_key in (
            EXPORT_FORMAT_DXF, EXPORT_FORMAT_SVG,
            EXPORT_FORMAT_STL, EXPORT_FORMAT_STEP,
        )
    }
    return effective


def selected_export_plan_rows(plan, config):
    rows = []
    overwrite = bool(config.get("overwrite_existing", False))
    for task in plan.get("tasks", []):
        desired = str(task.get("desired_path") or task.get("path") or "")
        actual = str(task.get("path") or "")
        if os.path.exists(desired):
            action = "Overwrite existing" if overwrite else "Create revision"
        else:
            action = "Create"
        rows.append({
            "Filename": os.path.basename(actual),
            "Format": EXPORT_FORMAT_LABELS.get(
                task.get("format"), str(task.get("format") or "").upper()
            ),
            "Output type": "Combined" if task.get("combined", False) else "Individual",
            "Records": str(len(task.get("records") or [])),
            "File action": action,
            "Full path": actual,
        })
    manifest_path = str(plan.get("manifest_path") or "")
    if manifest_path:
        desired = str(plan.get("manifest_desired_path") or manifest_path)
        if os.path.exists(desired):
            action = "Overwrite existing" if overwrite else "Create revision"
        else:
            action = "Create"
        rows.append({
            "Filename": os.path.basename(manifest_path),
            "Format": "CSV",
            "Output type": "Manifest",
            "Records": "0",
            "File action": action,
            "Full path": manifest_path,
        })
    return rows


def _selected_export_stage_path(staging_directory, index, final_path):
    basename = os.path.basename(final_path)
    stem, extension = os.path.splitext(basename)
    return os.path.join(
        staging_directory,
        "{:04d}_{}{}".format(index, safe_filename_component(stem, "Output"), extension),
    )


def commit_staged_export_entries(entries, overwrite_existing):
    entries = list(entries or [])
    final_paths = [os.path.abspath(str(item["final_path"])) for item in entries]
    if len(final_paths) != len(set(final_paths)):
        raise ValueError("The selected export contains duplicate final paths.")
    for item, final_path in zip(entries, final_paths):
        staged_path = str(item.get("staged_path") or "")
        if not os.path.isfile(staged_path) or os.path.getsize(staged_path) <= 0:
            raise ValueError("A staged export file is missing or empty: {}".format(staged_path))
        if os.path.exists(final_path) and not overwrite_existing:
            raise ValueError(
                "The planned filename appeared after preflight and was not overwritten: {}".format(final_path)
            )

    staging_directory = os.path.dirname(str(entries[0]["staged_path"])) if entries else ""
    backup_directory = os.path.join(staging_directory, ".backups")
    if entries:
        os.makedirs(backup_directory, exist_ok=True)
    backups = []
    committed = []
    try:
        for index, (item, final_path) in enumerate(zip(entries, final_paths), 1):
            if os.path.exists(final_path):
                backup_path = os.path.join(
                    backup_directory,
                    "{:04d}_{}".format(index, os.path.basename(final_path)),
                )
                os.replace(final_path, backup_path)
                backups.append((final_path, backup_path))
            os.replace(str(item["staged_path"]), final_path)
            committed.append(final_path)
    except Exception as error:
        rollback_errors = []
        for final_path in reversed(committed):
            if os.path.exists(final_path):
                try:
                    os.remove(final_path)
                except Exception as rollback_error:
                    rollback_errors.append(str(rollback_error))
        for final_path, backup_path in reversed(backups):
            if os.path.exists(backup_path):
                try:
                    os.replace(backup_path, final_path)
                except Exception as rollback_error:
                    rollback_errors.append(str(rollback_error))
        message = "Selected export commit failed and was rolled back: {}".format(error)
        if rollback_errors:
            message += " Rollback diagnostics: {}".format("; ".join(rollback_errors))
        raise RuntimeError(message)


def _selected_export_summary_failure(config, plan, extra_skipped, error, failed_task=None):
    skipped = list(plan.get("skipped") or []) + list(extra_skipped or [])
    if failed_task is not None:
        item = {"task": failed_task, "error": str(error)}
        summary, detail = _failed_export_report(item)
    else:
        summary = "Selected export transaction: {}".format(error)
        detail = "No destination export file was changed.\nReason: {}".format(error)
    skipped_outputs = []
    skipped_details = []
    for item in skipped:
        skip_summary, skip_detail = _skipped_export_report(item)
        skipped_outputs.append(skip_summary)
        skipped_details.append(skip_detail)
    return {
        "output_directory": config.get("output_directory", ""),
        "successful_files": 0,
        "failed_files": 1,
        "skipped_objects": len(skipped),
        "formats": [],
        "manifest_path": "",
        "manifest_requested": bool(config.get("create_manifest", True)),
        "failures": [summary],
        "failure_details": [detail],
        "skipped_outputs": skipped_outputs,
        "skipped_details": skipped_details,
    }


def run_selected_production_export(
    doc,
    plan,
    config,
    set_id,
    platform_config,
    formation_config,
    registration_config,
    template_assembly_config,
    extra_skipped=None,
    exporter_override=None,
):
    output_directory = str(config.get("output_directory") or "")
    staging_directory = tempfile.mkdtemp(
        prefix=".railway_selected_export_", dir=output_directory
    )
    entries = []
    results = []
    failed_task = None
    try:
        for index, task in enumerate(plan.get("tasks", []), 1):
            failed_task = task
            staged_path = _selected_export_stage_path(
                staging_directory, index, task.get("path", "")
            )
            if exporter_override is None:
                dispatch_freecad_export(doc, task, staged_path)
            else:
                exporter_override(doc, task, staged_path)
            if not os.path.isfile(staged_path) or os.path.getsize(staged_path) <= 0:
                raise ValueError("The exporter produced no valid file data.")
            entries.append({
                "staged_path": staged_path,
                "final_path": task["path"],
            })
            results.append({"task": task, "success": True, "error": ""})

        skipped = list(plan.get("skipped") or []) + list(extra_skipped or [])
        manifest_rows = build_manifest_rows(
            results,
            skipped,
            set_id,
            platform_config,
            formation_config,
            registration_config,
            template_assembly_config,
        )
        manifest_path = str(plan.get("manifest_path") or "")
        if manifest_path:
            failed_task = None
            staged_manifest = _selected_export_stage_path(
                staging_directory, len(entries) + 1, manifest_path
            )
            write_export_manifest(staged_manifest, manifest_rows)
            entries.append({
                "staged_path": staged_manifest,
                "final_path": manifest_path,
            })

        failed_task = None
        commit_staged_export_entries(
            entries, bool(config.get("overwrite_existing", False))
        )

        skipped_outputs = []
        skipped_details = []
        for item in skipped:
            skip_summary, skip_detail = _skipped_export_report(item)
            skipped_outputs.append(skip_summary)
            skipped_details.append(skip_detail)
        return {
            "output_directory": output_directory,
            "successful_files": len(entries),
            "failed_files": 0,
            "skipped_objects": len(skipped),
            "formats": sorted({
                str(task.get("format") or "").upper()
                for task in plan.get("tasks", [])
                if str(task.get("format") or "")
            }),
            "manifest_path": manifest_path,
            "manifest_requested": bool(config.get("create_manifest", True)),
            "failures": [],
            "failure_details": [],
            "skipped_outputs": skipped_outputs,
            "skipped_details": skipped_details,
        }
    except Exception as error:
        return _selected_export_summary_failure(
            config, plan, extra_skipped, error, failed_task
        )
    finally:
        try:
            shutil.rmtree(staging_directory)
        except Exception:
            pass


def confirm_selected_export_operation(
    scope,
    matching_count,
    export_count,
    plan,
    config,
    issues,
    skipped,
):
    if Gui is None:
        return False
    warning_count = sum(
        1 for issue in issues or []
        if issue.get("severity") == PRODUCTION_PREFLIGHT_SEVERITY_WARNING
    )
    overwrite_paths = sorted({
        str(issue.get("proposed_path") or "")
        for issue in issues or []
        if issue.get("issue_code") == "EXISTING_FILE_OVERWRITE"
        and str(issue.get("proposed_path") or "")
    })
    formats = sorted({
        EXPORT_FORMAT_LABELS.get(task.get("format"), str(task.get("format") or "").upper())
        for task in plan.get("tasks", [])
    })
    all_skipped = list(plan.get("skipped") or []) + list(skipped or [])
    informative = (
        "Scope: {scope}\n"
        "Production records selected for this operation: {matching}\n"
        "Records with compatible selected formats: {exportable}\n"
        "Files to produce: {files}\n"
        "Formats: {formats}\n"
        "Output folder: {folder}\n"
        "Files to overwrite: {overwrites}\n"
        "Records to skip: {skipped}\n"
        "Preflight warnings: {warnings}\n\n"
        "Every file will be staged first. Destination files change only when the complete export succeeds."
    ).format(
        scope=selected_export_scope_description(scope),
        matching=matching_count,
        exportable=export_count,
        files=len(plan.get("tasks", [])) + (1 if plan.get("manifest_path") else 0),
        formats=", ".join(formats) or "None",
        folder=config.get("output_directory", ""),
        overwrites=len(overwrite_paths),
        skipped=len(all_skipped),
        warnings=warning_count,
    )
    detail_lines = ["PLANNED FILES"]
    for row in selected_export_plan_rows(plan, config):
        detail_lines.append("- {} [{}] — {}".format(
            row["Full path"], row["Format"], row["File action"]
        ))
    if overwrite_paths:
        detail_lines.append("\nFILES TO OVERWRITE")
        detail_lines.extend("- {}".format(path) for path in overwrite_paths)
    if all_skipped:
        detail_lines.append("\nSKIPPED RECORDS")
        for item in all_skipped:
            detail_lines.append("- {}: {}".format(
                _export_record_report_name(item.get("record") or {}),
                item.get("reason") or "No reason recorded",
            ))
    warnings = [
        issue for issue in issues or []
        if issue.get("severity") == PRODUCTION_PREFLIGHT_SEVERITY_WARNING
    ]
    if warnings:
        detail_lines.append("\nPREFLIGHT WARNINGS")
        detail_lines.extend(
            "- {}: {}".format(issue.get("issue_code", "WARNING"), issue.get("message", ""))
            for issue in warnings
        )

    try:
        yes_button = QtWidgets.QMessageBox.Yes
        no_button = QtWidgets.QMessageBox.No
        question_icon = QtWidgets.QMessageBox.Question
    except AttributeError:
        yes_button = QtWidgets.QMessageBox.StandardButton.Yes
        no_button = QtWidgets.QMessageBox.StandardButton.No
        question_icon = QtWidgets.QMessageBox.Icon.Question
    box = QtWidgets.QMessageBox()
    box.setWindowTitle(versioned_dialog_title("Confirm selected production export"))
    box.setIcon(question_icon)
    box.setText("Export the selected production items?")
    box.setInformativeText(informative)
    box.setDetailedText("\n".join(detail_lines))
    box.setStandardButtons(yes_button | no_button)
    box.setDefaultButton(no_button)
    return dialog_exec(box) == yes_button


class SelectedProductionExportDialog(QtWidgets.QDialog):
    def __init__(self, doc, parent=None):
        super(SelectedProductionExportDialog, self).__init__(parent)
        self.doc = doc
        self.index_payload = {}
        self.catalogue_records = []
        self.preview_records = []
        self.matching_records = []
        self.export_records = []
        self.preliminary_skipped = []
        self.plan = None
        self.issues = []
        self.scope = {}
        self.route_options = []
        self.target_options = []
        self._loading_export_controls = False
        self._row_selection_help_text = (
            "Choose a scope, then optionally highlight rows to export only those records. "
            "With no highlighted rows, all matching records are exported. The export button "
            "always states which mode will run."
        )
        self.setWindowTitle(versioned_dialog_title("Export selected production items"))
        self.resize(1640, 920)

        layout = QtWidgets.QVBoxLayout(self)
        selection_group = QtWidgets.QGroupBox("Selection scope")
        selection_layout = QtWidgets.QGridLayout(selection_group)
        selection_layout.addWidget(QtWidgets.QLabel("Template set:"), 0, 0)
        self.set_box = QtWidgets.QComboBox()
        self.set_box.addItems(generated_template_set_ids(doc))
        selection_layout.addWidget(self.set_box, 0, 1)
        selection_layout.addWidget(QtWidgets.QLabel("Scope:"), 0, 2)
        self.scope_box = QtWidgets.QComboBox()
        self.scope_box.addItems(SELECTED_EXPORT_SCOPES)
        selection_layout.addWidget(self.scope_box, 0, 3)
        selection_layout.addWidget(QtWidgets.QLabel("Route:"), 1, 0)
        self.route_box = QtWidgets.QComboBox()
        selection_layout.addWidget(self.route_box, 1, 1)
        self.target_label = QtWidgets.QLabel("Target:")
        selection_layout.addWidget(self.target_label, 1, 2)
        self.target_box = QtWidgets.QComboBox()
        selection_layout.addWidget(self.target_box, 1, 3)
        self.selection_note = QtWidgets.QLabel("")
        self.selection_note.setWordWrap(True)
        selection_layout.addWidget(self.selection_note, 2, 0, 1, 4)
        self.row_selection_note = QtWidgets.QLabel(self._row_selection_help_text)
        self.row_selection_note.setWordWrap(True)
        selection_layout.addWidget(self.row_selection_note, 3, 0, 1, 4)
        layout.addWidget(selection_group)

        export_group = QtWidgets.QGroupBox("Selected export settings")
        export_layout = QtWidgets.QGridLayout(export_group)
        export_layout.addWidget(QtWidgets.QLabel("Output folder:"), 0, 0)
        self.output_box = QtWidgets.QLineEdit()
        export_layout.addWidget(self.output_box, 0, 1, 1, 5)
        self.browse_button = QtWidgets.QPushButton("Browse...")
        export_layout.addWidget(self.browse_button, 0, 6)
        self.format_boxes = {}
        for column, format_key in enumerate(
            (EXPORT_FORMAT_DXF, EXPORT_FORMAT_SVG, EXPORT_FORMAT_STL, EXPORT_FORMAT_STEP)
        ):
            box = QtWidgets.QCheckBox(EXPORT_FORMAT_LABELS[format_key])
            self.format_boxes[format_key] = box
            export_layout.addWidget(box, 1, column)
        self.export_each_section_box = QtWidgets.QCheckBox("Individual section files")
        self.combined_box = QtWidgets.QCheckBox("Combined files for this scope")
        self.manifest_box = QtWidgets.QCheckBox("CSV manifest")
        self.overwrite_box = QtWidgets.QCheckBox("Overwrite existing files")
        export_layout.addWidget(self.export_each_section_box, 2, 0, 1, 2)
        export_layout.addWidget(self.combined_box, 2, 2, 1, 2)
        export_layout.addWidget(self.manifest_box, 2, 4)
        export_layout.addWidget(self.overwrite_box, 2, 5, 1, 2)
        self.probe_box = QtWidgets.QCheckBox("Run temporary SVG/DXF exporter-bound probes")
        self.probe_box.setChecked(True)
        export_layout.addWidget(self.probe_box, 3, 0, 1, 4)
        self.select_visible_rows_button = QtWidgets.QPushButton("Highlight visible rows")
        self.select_visible_rows_button.setToolTip(
            "Highlights every record currently shown in Matching records. Use Ctrl-click to refine the selection afterwards."
        )
        export_layout.addWidget(self.select_visible_rows_button, 3, 4)
        self.clear_row_filter_button = QtWidgets.QPushButton("Use all matching records")
        self.clear_row_filter_button.setToolTip(
            "Clears row highlighting and returns the export to every record in the selected scope."
        )
        export_layout.addWidget(self.clear_row_filter_button, 3, 5)
        self.refresh_button = QtWidgets.QPushButton("Refresh preview")
        self.refresh_button.setToolTip(
            "Rebuilds the planned-file and preflight preview using the current scope, formats and row selection."
        )
        export_layout.addWidget(self.refresh_button, 3, 6)
        layout.addWidget(export_group)

        self.summary_label = QtWidgets.QLabel("")
        self.summary_label.setWordWrap(True)
        layout.addWidget(self.summary_label)

        tabs = QtWidgets.QTabWidget()
        self.records_table = QtWidgets.QTableWidget(0, len(SELECTED_EXPORT_RECORD_FIELDS))
        self.records_table.setHorizontalHeaderLabels(SELECTED_EXPORT_RECORD_FIELDS)
        self.plan_table = QtWidgets.QTableWidget(0, len(SELECTED_EXPORT_PLAN_FIELDS))
        self.plan_table.setHorizontalHeaderLabels(SELECTED_EXPORT_PLAN_FIELDS)
        self.issues_table = QtWidgets.QTableWidget(0, len(PRODUCTION_PREFLIGHT_FIELDS))
        self.issues_table.setHorizontalHeaderLabels(PRODUCTION_PREFLIGHT_FIELDS)
        for table in (self.records_table, self.plan_table, self.issues_table):
            try:
                table.setEditTriggers(QtWidgets.QAbstractItemView.NoEditTriggers)
                table.setSelectionBehavior(QtWidgets.QAbstractItemView.SelectRows)
            except AttributeError:
                table.setEditTriggers(QtWidgets.QAbstractItemView.EditTrigger.NoEditTriggers)
                table.setSelectionBehavior(QtWidgets.QAbstractItemView.SelectionBehavior.SelectRows)
            table.setAlternatingRowColors(True)
        try:
            self.records_table.setSelectionMode(QtWidgets.QAbstractItemView.ExtendedSelection)
        except AttributeError:
            self.records_table.setSelectionMode(
                QtWidgets.QAbstractItemView.SelectionMode.ExtendedSelection
            )
        tabs.addTab(self.records_table, "Matching records")
        tabs.addTab(self.plan_table, "Planned files")
        tabs.addTab(self.issues_table, "Preflight diagnostics")
        layout.addWidget(tabs, 1)

        button_layout = QtWidgets.QHBoxLayout()
        self.export_button = QtWidgets.QPushButton("Export all matching records")
        close_button = QtWidgets.QPushButton("Close")
        button_layout.addWidget(self.export_button)
        button_layout.addStretch(1)
        button_layout.addWidget(close_button)
        layout.addLayout(button_layout)

        self.set_box.currentIndexChanged.connect(self._set_changed)
        self.scope_box.currentIndexChanged.connect(self._scope_changed)
        self.route_box.currentIndexChanged.connect(self._route_changed)
        self.target_box.currentIndexChanged.connect(self.refresh_preview)
        self.browse_button.clicked.connect(self._browse)
        self.select_visible_rows_button.clicked.connect(self._select_visible_rows)
        self.clear_row_filter_button.clicked.connect(self._clear_highlighted_rows)
        self.refresh_button.clicked.connect(self.refresh_preview)
        self.records_table.itemSelectionChanged.connect(self._record_selection_changed)
        self.output_box.editingFinished.connect(self._export_settings_changed)
        for box in self.format_boxes.values():
            box.toggled.connect(self._export_settings_changed)
        self.export_each_section_box.toggled.connect(self._export_settings_changed)
        self.combined_box.toggled.connect(self._export_settings_changed)
        self.manifest_box.toggled.connect(self._export_settings_changed)
        self.overwrite_box.toggled.connect(self._export_settings_changed)
        self.probe_box.toggled.connect(self._export_settings_changed)
        self.export_button.clicked.connect(self.export_selected)
        close_button.clicked.connect(self.accept)

        if self.set_box.count() > 0:
            selected_set = ""
            if Gui is not None:
                try:
                    for obj in reversed(Gui.Selection.getSelection()):
                        candidate = object_string_property(obj, "TemplateSetID", "")
                        if candidate:
                            selected_set = candidate
                            break
                except Exception:
                    pass
            if selected_set:
                index = self.set_box.findText(selected_set)
                if index >= 0:
                    self.set_box.setCurrentIndex(index)
            self._set_changed()
        else:
            self.summary_label.setText(
                "No recognised generated template sets exist in this document."
            )
            self.export_button.setEnabled(False)

    def current_set_id(self):
        return str(self.set_box.currentText() or "").strip()

    def _set_changed(self, *_args):
        set_id = self.current_set_id()
        if not set_id:
            return
        self.index_payload = production_record_index_for_set(self.doc, set_id)
        self.catalogue_records = hydrate_production_index_records(
            self.doc, self.index_payload
        )
        settings = settings_for_template_set(self.doc, set_id)
        config = read_production_export_config(settings)
        self._loading_export_controls = True
        try:
            self.output_box.setText(str(config.get("output_directory") or ""))
            for format_key, box in self.format_boxes.items():
                box.setChecked(bool(config.get("formats", {}).get(format_key, False)))
            self.export_each_section_box.setChecked(bool(config.get("export_each_section", True)))
            self.combined_box.setChecked(bool(config.get("create_combined_files", True)))
            self.manifest_box.setChecked(bool(config.get("create_manifest", True)))
            self.overwrite_box.setChecked(bool(config.get("overwrite_existing", False)))
        finally:
            self._loading_export_controls = False
        self.route_options = selected_export_route_options(self.catalogue_records)
        self.route_box.blockSignals(True)
        self.route_box.clear()
        for option in self.route_options:
            self.route_box.addItem(option["label"])
        self.route_box.blockSignals(False)
        self._scope_changed()

    def _scope_changed(self, *_args):
        scope_type = str(self.scope_box.currentText() or "")
        route_required = scope_type in (
            SELECTED_EXPORT_SCOPE_SECTION,
            SELECTED_EXPORT_SCOPE_TRACK,
            SELECTED_EXPORT_SCOPE_PLATFORM,
            SELECTED_EXPORT_SCOPE_FORMATION,
            SELECTED_EXPORT_SCOPE_ROUTE,
        )
        target_required = scope_type in (
            SELECTED_EXPORT_SCOPE_SECTION,
            SELECTED_EXPORT_SCOPE_TRACK,
            SELECTED_EXPORT_SCOPE_PLATFORM,
        )
        self.route_box.setEnabled(route_required)
        self.target_box.setEnabled(target_required)
        self.target_label.setEnabled(target_required)
        self._route_changed()

    def _route_changed(self, *_args):
        route_index = max(0, self.route_box.currentIndex())
        route_id = (
            self.route_options[route_index]["value"]
            if self.route_options and route_index < len(self.route_options)
            else ""
        )
        scope_type = str(self.scope_box.currentText() or "")
        self.target_options = selected_export_target_options(
            self.catalogue_records, scope_type, route_id
        )
        self.target_box.blockSignals(True)
        self.target_box.clear()
        for option in self.target_options:
            self.target_box.addItem(option["label"])
        self.target_box.blockSignals(False)
        self.refresh_preview()

    def _browse(self):
        start = str(self.output_box.text() or "").strip() or os.path.expanduser("~")
        selected = QtWidgets.QFileDialog.getExistingDirectory(
            self, versioned_dialog_title("Select selected-export directory"), start
        )
        if selected:
            self.output_box.setText(str(selected))
            self.refresh_preview()

    def _current_config(self):
        settings = settings_for_template_set(self.doc, self.current_set_id())
        config = read_production_export_config(settings)
        config["enabled"] = True
        output_text = str(self.output_box.text() or "").strip()
        config["output_directory"] = (
            os.path.abspath(os.path.expanduser(output_text)) if output_text else ""
        )
        config["formats"] = {
            key: bool(box.isChecked()) for key, box in self.format_boxes.items()
        }
        config["export_each_section"] = bool(self.export_each_section_box.isChecked())
        config["create_combined_files"] = bool(self.combined_box.isChecked())
        config["create_manifest"] = bool(self.manifest_box.isChecked())
        config["overwrite_existing"] = bool(self.overwrite_box.isChecked())
        config["open_output_directory"] = False
        return config

    def _current_scope(self):
        scope_type = str(self.scope_box.currentText() or "")
        route_index = max(0, self.route_box.currentIndex())
        route_option = (
            self.route_options[route_index]
            if self.route_options and route_index < len(self.route_options)
            else {"value": "", "label": "Curve route"}
        )
        target_index = max(0, self.target_box.currentIndex())
        target_value = (
            self.target_options[target_index]["value"]
            if self.target_options and target_index < len(self.target_options)
            else 0
        )
        scope = {
            "scope_type": scope_type,
            "route_id": str(route_option.get("value") or ""),
            "route_label": str(route_option.get("label") or "Curve route"),
            "selected_objects": selected_export_selection_snapshot(
                self.doc, self.current_set_id()
            ),
        }
        if scope_type == SELECTED_EXPORT_SCOPE_SECTION:
            scope["section_number"] = int(target_value or 0)
        elif scope_type == SELECTED_EXPORT_SCOPE_TRACK:
            scope["track_number"] = int(target_value or 0)
        elif scope_type == SELECTED_EXPORT_SCOPE_PLATFORM:
            scope["platform_number"] = int(target_value or 0)
        return scope

    def _record_row(self, record, config):
        route = _selected_export_route_label(record)
        track_number = int(record.get("track_number") or 0)
        track = ""
        if track_number:
            track = "{:02d} {}".format(track_number, str(record.get("track_name") or ""))
        platform_number = int(record.get("platform_number") or 0)
        platform = ""
        if platform_number:
            platform = "{:02d} {}".format(platform_number, str(record.get("platform_name") or ""))
        formats = ", ".join(
            EXPORT_FORMAT_LABELS.get(value, value.upper())
            for value in record_compatible_formats(record, config)
        )
        return {
            "Source object": record.get("source_label") or record.get("source_name") or "",
            "Route": route,
            "Track": track,
            "Platform": platform,
            "Section": record.get("section_number") or "",
            "Travel order": record.get("travel_order_number") or "",
            "Object type": record.get("role") or "",
            "Export subtype": record.get("subtype") or "",
            "Category": record.get("category") or "",
            "Compatible formats": formats,
            "Production-record ID": record.get("record_id") or "",
        }

    def _highlighted_record_ids(self):
        record_ids = set()
        id_column = SELECTED_EXPORT_RECORD_FIELDS.index("Production-record ID")
        try:
            selected_rows = list(self.records_table.selectionModel().selectedRows())
        except Exception:
            selected_rows = []
        if selected_rows:
            row_numbers = {int(index.row()) for index in selected_rows}
        else:
            row_numbers = set()
            try:
                row_numbers = {int(item.row()) for item in self.records_table.selectedItems()}
            except Exception:
                pass
        for row_number in row_numbers:
            item = self.records_table.item(row_number, id_column)
            if item is None:
                continue
            record_id = str(item.text() or "").strip()
            if record_id:
                record_ids.add(record_id)
        return record_ids

    def _has_selected_export_format(self):
        return any(bool(box.isChecked()) for box in self.format_boxes.values())

    def _update_export_action(self):
        highlighted_count = len(self._highlighted_record_ids())
        if highlighted_count:
            noun = "row" if highlighted_count == 1 else "rows"
            self.export_button.setText(
                "Export {} highlighted {}".format(highlighted_count, noun)
            )
            self.export_button.setToolTip(
                "Validates and exports only the highlighted production records."
            )
            self.export_button.setEnabled(self._has_selected_export_format())
            self.row_selection_note.setText(
                "{} highlighted {}. Choose Export to validate only this selection, or choose Use all matching records to clear it.".format(
                    highlighted_count, noun
                )
            )
            return
        self.export_button.setText("Export all matching records")
        self.export_button.setToolTip(
            "Validates and exports every production record matching the selected scope."
        )
        counts = summarise_preflight(self.issues)
        self.export_button.setEnabled(bool(
            self.plan
            and self.plan.get("tasks")
            and counts.get("blocking", 0) == 0
        ))
        self.row_selection_note.setText(self._row_selection_help_text)

    def _record_selection_changed(self):
        self._update_export_action()

    def _select_visible_rows(self):
        try:
            self.records_table.selectAll()
        except Exception:
            pass
        self._update_export_action()

    def _export_settings_changed(self, *_args):
        if self._loading_export_controls:
            return
        self.refresh_preview()

    def _clear_highlighted_rows(self):
        try:
            self.records_table.clearSelection()
        except Exception:
            pass
        self.refresh_preview()

    def refresh_preview(self, *_args):
        highlighted_record_ids = self._highlighted_record_ids()
        self.records_table.setRowCount(0)
        self.plan_table.setRowCount(0)
        self.issues_table.setRowCount(0)
        self.export_button.setEnabled(False)
        set_id = self.current_set_id()
        if not set_id:
            return
        try:
            config = self._current_config()
            scope = self._current_scope()
            if highlighted_record_ids:
                scope["highlighted_record_ids"] = sorted(highlighted_record_ids)
            self.scope = scope
            scope_records = filter_production_records_by_selected_scope(
                self.catalogue_records, scope
            )
            candidate_records = list(scope_records)
            if (
                scope.get("scope_type") == SELECTED_EXPORT_SCOPE_OBJECTS
                and not scope.get("selected_objects")
            ):
                # The macro dialogue is modal, so a user may not have been able
                # to change the FreeCAD viewport selection after opening it.
                # Show the complete catalogue as selectable candidates, but do
                # not export anything until one or more rows are highlighted.
                candidate_records = list(self.catalogue_records)
            if highlighted_record_ids:
                highlighted = [
                    record for record in candidate_records
                    if str(record.get("record_id") or "") in highlighted_record_ids
                ]
                self.matching_records = _expand_selected_object_representations(
                    candidate_records, highlighted
                )
                self.preview_records = list(self.matching_records)
            else:
                self.matching_records = list(scope_records)
                self.preview_records = list(candidate_records)
            self.export_records, self.preliminary_skipped = selected_export_records_for_formats(
                self.matching_records, config
            )
            self.plan = None
            self.issues = []
            if self.export_records:
                self.plan = plan_selected_production_export(
                    self.export_records, config, set_id, scope
                )
                validation_records = selected_export_validation_records(
                    self.catalogue_records, self.matching_records, scope
                )
                filename_issues = selected_export_filename_issues(
                    self.plan, config, set_id
                )
                settings = settings_for_template_set(self.doc, set_id)
                preflight_config = selected_export_preflight_config(
                    config, self.plan
                )
                self.issues = run_production_preflight(
                    self.doc,
                    validation_records,
                    self.export_records,
                    preflight_config,
                    set_id,
                    read_section_config(settings),
                    read_registration_config(settings),
                    read_template_assembly_config(settings),
                    settings_obj=settings,
                    plan=self.plan,
                    include_export_checks=True,
                    probe_export_bounds=bool(self.probe_box.isChecked()),
                    filename_issues_override=filename_issues,
                )
            elif self.matching_records:
                self.issues = [make_preflight_issue(
                    "NO_COMPATIBLE_SCOPE_RECORDS",
                    PRODUCTION_PREFLIGHT_SEVERITY_ERROR,
                    "The selected scope contains production records, but none supports the selected export formats.",
                    set_id,
                )]
            else:
                if (
                    scope.get("scope_type") == SELECTED_EXPORT_SCOPE_OBJECTS
                    and not scope.get("selected_objects")
                    and not highlighted_record_ids
                ):
                    issue_code = "NO_SELECTED_PRODUCTION_ITEMS"
                    issue_message = (
                        "No FreeCAD object was pre-selected. Highlight one or more rows in "
                        "Matching records, then press Export selected items."
                    )
                else:
                    issue_code = "NO_MATCHING_PRODUCTION_RECORDS"
                    issue_message = "No production records match the selected scope."
                self.issues = [make_preflight_issue(
                    issue_code,
                    PRODUCTION_PREFLIGHT_SEVERITY_ERROR,
                    issue_message,
                    set_id,
                )]

            self.records_table.setRowCount(len(self.preview_records))
            for row_index, record in enumerate(self.preview_records):
                row = self._record_row(record, config)
                for column_index, field in enumerate(SELECTED_EXPORT_RECORD_FIELDS):
                    self.records_table.setItem(
                        row_index, column_index,
                        QtWidgets.QTableWidgetItem(str(row.get(field, ""))),
                    )

            plan_rows = selected_export_plan_rows(self.plan or {}, config)
            self.plan_table.setRowCount(len(plan_rows))
            for row_index, row in enumerate(plan_rows):
                for column_index, field in enumerate(SELECTED_EXPORT_PLAN_FIELDS):
                    self.plan_table.setItem(
                        row_index, column_index,
                        QtWidgets.QTableWidgetItem(str(row.get(field, ""))),
                    )

            self.issues_table.setRowCount(len(self.issues))
            for row_index, issue in enumerate(self.issues):
                row = preflight_issue_row(issue)
                for column_index, field in enumerate(PRODUCTION_PREFLIGHT_FIELDS):
                    self.issues_table.setItem(
                        row_index, column_index,
                        QtWidgets.QTableWidgetItem(str(row.get(field, ""))),
                    )
            for table in (self.records_table, self.plan_table, self.issues_table):
                try:
                    table.resizeColumnsToContents()
                except Exception:
                    pass
            if highlighted_record_ids and self.preview_records:
                try:
                    self.records_table.selectAll()
                except Exception:
                    pass

            counts = summarise_preflight(self.issues)
            task_count = len((self.plan or {}).get("tasks", []))
            file_count = task_count + (1 if (self.plan or {}).get("manifest_path") else 0)
            skip_count = len(self.preliminary_skipped) + len((self.plan or {}).get("skipped", []))
            selection_text = ""
            if scope.get("scope_type") == SELECTED_EXPORT_SCOPE_OBJECTS:
                names = [item.get("label") or item.get("name") for item in scope.get("selected_objects") or []]
                selection_text = " Current FreeCAD selection: {}.".format(
                    ", ".join(names) if names else "none"
                )
            if highlighted_record_ids:
                selection_text += " Highlighted production records: {}.".format(
                    len(self.matching_records)
                )
            legacy_text = (
                " Legacy metadata scan in use; ambiguous legacy records will remain blocked."
                if self.index_payload.get("legacy_scan", False) else ""
            )
            self.selection_note.setText(
                "Scope: {}.{}".format(selected_export_scope_description(scope), selection_text)
            )
            self.summary_label.setText(
                "{} candidate record(s); {} selected matching record(s); {} record(s) with compatible formats; "
                "{} planned file(s); {} skipped record(s); {} error(s); {} warning(s).{}".format(
                    len(self.preview_records),
                    len(self.matching_records),
                    len(self.export_records),
                    file_count,
                    skip_count,
                    counts.get(PRODUCTION_PREFLIGHT_SEVERITY_ERROR, 0),
                    counts.get(PRODUCTION_PREFLIGHT_SEVERITY_WARNING, 0),
                    legacy_text,
                )
            )
            self._update_export_action()
        except Exception as error:
            self.summary_label.setText("Selected export preview failed: {}".format(error))
            self.export_button.setEnabled(False)
            self.export_button.setText("Export unavailable")

    def export_selected(self):
        self.refresh_preview()
        if not self.plan or not self.plan.get("tasks"):
            QtWidgets.QMessageBox.critical(
                self,
                versioned_dialog_title("Selected export unavailable"),
                "No valid production export task matches the selected scope and formats.",
            )
            return
        blocking = preflight_blocking_report(self.issues)
        if blocking:
            QtWidgets.QMessageBox.critical(
                self,
                versioned_dialog_title("Selected export blocked"),
                blocking,
            )
            return
        config = self._current_config()
        if not confirm_selected_export_operation(
            self.scope,
            len(self.matching_records),
            len(self.export_records),
            self.plan,
            config,
            self.issues,
            self.preliminary_skipped,
        ):
            return
        confirmed_paths = {
            str(task.get("path") or "") for task in self.plan.get("tasks", [])
        }
        if self.plan.get("manifest_path"):
            confirmed_paths.add(str(self.plan.get("manifest_path")))
        confirmed_warnings = {
            (str(issue.get("issue_code") or ""), str(issue.get("proposed_path") or ""))
            for issue in self.issues
            if issue.get("severity") == PRODUCTION_PREFLIGHT_SEVERITY_WARNING
        }
        try:
            ensure_production_export_directory(config)
            # Rebuild and recheck after folder creation so late filename changes cannot be hidden.
            self.plan = plan_selected_production_export(
                self.export_records, config, self.current_set_id(), self.scope
            )
            filename_issues = selected_export_filename_issues(
                self.plan, config, self.current_set_id()
            )
            settings = settings_for_template_set(self.doc, self.current_set_id())
            validation_records = selected_export_validation_records(
                self.catalogue_records, self.matching_records, self.scope
            )
            preflight_config = selected_export_preflight_config(
                config, self.plan
            )
            final_issues = run_production_preflight(
                self.doc,
                validation_records,
                self.export_records,
                preflight_config,
                self.current_set_id(),
                read_section_config(settings),
                read_registration_config(settings),
                read_template_assembly_config(settings),
                settings_obj=settings,
                plan=self.plan,
                include_export_checks=True,
                probe_export_bounds=False,
                filename_issues_override=filename_issues,
            )
            blocking = preflight_blocking_report(final_issues)
            if blocking:
                raise ValueError(blocking)
            final_paths = {
                str(task.get("path") or "") for task in self.plan.get("tasks", [])
            }
            if self.plan.get("manifest_path"):
                final_paths.add(str(self.plan.get("manifest_path")))
            final_warnings = {
                (str(issue.get("issue_code") or ""), str(issue.get("proposed_path") or ""))
                for issue in final_issues
                if issue.get("severity") == PRODUCTION_PREFLIGHT_SEVERITY_WARNING
            }
            if (
                final_paths != confirmed_paths
                or not final_warnings.issubset(confirmed_warnings)
            ):
                if not confirm_selected_export_operation(
                    self.scope,
                    len(self.matching_records),
                    len(self.export_records),
                    self.plan,
                    config,
                    final_issues,
                    self.preliminary_skipped,
                ):
                    return
            summary = run_selected_production_export(
                self.doc,
                self.plan,
                config,
                self.current_set_id(),
                read_platform_configs(settings)[0] if read_platform_configs(settings) else default_platform_config(),
                read_formation_config(settings),
                read_registration_config(settings),
                read_template_assembly_config(settings),
                extra_skipped=self.preliminary_skipped,
            )
            show_production_export_summary(summary)
            self.refresh_preview()
        except Exception as error:
            QtWidgets.QMessageBox.critical(
                self,
                versioned_dialog_title("Selected export error"),
                "{}\n\nNo destination export file was deliberately left partially updated.".format(error),
            )


class AssemblyLabelDialog(QtWidgets.QDialog):
    PREVIEW_FIELDS = ["Production part", "Label text", "Status", "Placement or diagnostic"]

    def __init__(self, doc, parent=None):
        super(AssemblyLabelDialog, self).__init__(parent)
        self.doc = doc
        self.setWindowTitle(versioned_dialog_title("Assembly labels"))
        self.resize(1180, 760)
        layout = QtWidgets.QVBoxLayout(self)

        selection_group = QtWidgets.QGroupBox("Template set")
        selection_layout = QtWidgets.QGridLayout(selection_group)
        self.set_box = QtWidgets.QComboBox()
        for set_id in generated_template_set_ids(doc):
            self.set_box.addItem(set_id, set_id)
        selection_layout.addWidget(QtWidgets.QLabel("Template set:"), 0, 0)
        selection_layout.addWidget(self.set_box, 0, 1)
        selection_note = QtWidgets.QLabel(
            "Labels are separate production geometry. Applying or removing them does not alter the visible "
            "track, platform or formation-board objects."
        )
        selection_note.setWordWrap(True)
        selection_layout.addWidget(selection_note, 1, 0, 1, 2)
        layout.addWidget(selection_group)

        config_group = QtWidgets.QGroupBox("Label configuration")
        config_layout = QtWidgets.QGridLayout(config_group)
        self.enabled_box = QtWidgets.QCheckBox()
        self.format_box = QtWidgets.QComboBox()
        self.format_box.addItems([ASSEMBLY_LABEL_FORMAT_AUTOMATIC, ASSEMBLY_LABEL_FORMAT_CUSTOM])
        self.custom_format_box = QtWidgets.QLineEdit()
        self.text_height_box = QtWidgets.QDoubleSpinBox()
        self.text_height_box.setRange(1.0, 20.0)
        self.text_height_box.setDecimals(2)
        self.text_height_box.setSuffix(" mm")
        self.stroke_width_box = QtWidgets.QDoubleSpinBox()
        self.stroke_width_box.setRange(0.08, 2.0)
        self.stroke_width_box.setDecimals(2)
        self.stroke_width_box.setSuffix(" mm")
        self.depth_box = QtWidgets.QDoubleSpinBox()
        self.depth_box.setRange(0.05, 5.0)
        self.depth_box.setDecimals(2)
        self.depth_box.setSuffix(" mm")
        self.margin_box = QtWidgets.QDoubleSpinBox()
        self.margin_box.setRange(0.0, 50.0)
        self.margin_box.setDecimals(2)
        self.margin_box.setSuffix(" mm")
        self.placement_box = QtWidgets.QComboBox()
        self.placement_box.addItems(ASSEMBLY_LABEL_PLACEMENTS)
        self.include_set_box = QtWidgets.QCheckBox()
        self.include_track_box = QtWidgets.QCheckBox()
        self.include_track_name_box = QtWidgets.QCheckBox()
        self.include_section_box = QtWidgets.QCheckBox()
        self.include_travel_box = QtWidgets.QCheckBox()
        self.include_platform_box = QtWidgets.QCheckBox()
        self.include_formation_box = QtWidgets.QCheckBox()

        fields = [
            ("Enable assembly labels:", self.enabled_box, "Creates label engraving only after a safe placement has been validated."),
            ("Label format:", self.format_box, "Automatic compact uses the inclusion controls. Custom format uses safe text tokens only."),
            ("Custom token format:", self.custom_format_box, "Allowed tokens: {SET}, {IDENTITY}, {TRACK}, {TRACK_NAME}, {SECTION}, {TRAVEL}, {PLATFORM}, {FORMATION}, {ROUTE}."),
            ("Text height:", self.text_height_box, "Overall height of the compact internal stroke font."),
            ("Stroke width:", self.stroke_width_box, "Width used for 3D engraved stroke cutters."),
            ("Engraving depth:", self.depth_box, "Shallow depth removed from the chosen top or underside surface."),
            ("Edge and feature margin:", self.margin_box, "Minimum clearance from part edges, fixing holes and joint geometry."),
            ("Preferred placement:", self.placement_box, "The placement solver tries this location and surface first, then safe fallbacks."),
            ("Include template-set ID:", self.include_set_box, "Adds SET-001 or the current set identity."),
            ("Include track number:", self.include_track_box, "Adds T01, T02 and so on for track-template parts."),
            ("Use track name instead:", self.include_track_name_box, "Uses the stored track name when one exists."),
            ("Include section number:", self.include_section_box, "Adds S01, S02 and so on for sectioned parts."),
            ("Include travel-order number:", self.include_travel_box, "Adds O01, O02 and so on."),
            ("Include platform identity:", self.include_platform_box, "Adds PLAT-01 and the relevant platform number."),
            ("Include formation identity:", self.include_formation_box, "Adds FB to formation-board parts."),
        ]
        for index, (label_text, widget, tooltip) in enumerate(fields):
            row = index // 2
            column = (index % 2) * 2
            label = QtWidgets.QLabel(label_text)
            label.setToolTip(tooltip)
            widget.setToolTip(tooltip)
            config_layout.addWidget(label, row, column)
            config_layout.addWidget(widget, row, column + 1)
        layout.addWidget(config_group)

        preview_bar = QtWidgets.QHBoxLayout()
        self.refresh_button = QtWidgets.QPushButton("Refresh preview")
        self.apply_button = QtWidgets.QPushButton("Apply labels to selected set")
        preview_bar.addWidget(self.refresh_button)
        preview_bar.addWidget(self.apply_button)
        preview_bar.addStretch(1)
        layout.addLayout(preview_bar)

        self.summary_label = QtWidgets.QLabel("")
        self.summary_label.setWordWrap(True)
        layout.addWidget(self.summary_label)
        self.table = QtWidgets.QTableWidget(0, len(self.PREVIEW_FIELDS))
        self.table.setHorizontalHeaderLabels(self.PREVIEW_FIELDS)
        self.table.setSelectionBehavior(QtWidgets.QAbstractItemView.SelectRows)
        self.table.setEditTriggers(QtWidgets.QAbstractItemView.NoEditTriggers)
        try:
            self.table.horizontalHeader().setSectionResizeMode(QtWidgets.QHeaderView.ResizeToContents)
            self.table.horizontalHeader().setStretchLastSection(True)
        except Exception:
            pass
        layout.addWidget(self.table, 1)

        buttons = QtWidgets.QDialogButtonBox(QtWidgets.QDialogButtonBox.Close)
        buttons.rejected.connect(self.reject)
        layout.addWidget(buttons)

        self.set_box.currentIndexChanged.connect(self._set_changed)
        self.format_box.currentIndexChanged.connect(self._update_controls)
        self.enabled_box.toggled.connect(self._update_controls)
        self.text_height_box.valueChanged.connect(self._update_controls)
        self.refresh_button.clicked.connect(self.refresh_preview)
        self.apply_button.clicked.connect(self.apply_labels)
        self._set_changed()

    def current_set_id(self):
        value = self.set_box.currentData()
        return str(value if value is not None else self.set_box.currentText())

    def _current_config(self):
        return validate_assembly_label_config({
            "enabled": bool(self.enabled_box.isChecked()),
            "label_format": str(self.format_box.currentText()),
            "custom_format": str(self.custom_format_box.text()),
            "text_height": float(self.text_height_box.value()),
            "stroke_width": float(self.stroke_width_box.value()),
            "engraving_depth": float(self.depth_box.value()),
            "edge_margin": float(self.margin_box.value()),
            "preferred_placement": str(self.placement_box.currentText()),
            "include_template_set_id": bool(self.include_set_box.isChecked()),
            "include_track_number": bool(self.include_track_box.isChecked()),
            "include_track_name": bool(self.include_track_name_box.isChecked()),
            "include_section_number": bool(self.include_section_box.isChecked()),
            "include_travel_order_number": bool(self.include_travel_box.isChecked()),
            "include_platform_identity": bool(self.include_platform_box.isChecked()),
            "include_formation_identity": bool(self.include_formation_box.isChecked()),
        })

    def _load_config(self, config):
        config = clone_assembly_label_config(config)
        self.enabled_box.setChecked(config["enabled"])
        index = self.format_box.findText(config["label_format"])
        self.format_box.setCurrentIndex(max(0, index))
        self.custom_format_box.setText(config["custom_format"])
        self.text_height_box.setValue(config["text_height"])
        self.stroke_width_box.setValue(config["stroke_width"])
        self.depth_box.setValue(config["engraving_depth"])
        self.margin_box.setValue(config["edge_margin"])
        index = self.placement_box.findText(config["preferred_placement"])
        self.placement_box.setCurrentIndex(max(0, index))
        self.include_set_box.setChecked(config["include_template_set_id"])
        self.include_track_box.setChecked(config["include_track_number"])
        self.include_track_name_box.setChecked(config["include_track_name"])
        self.include_section_box.setChecked(config["include_section_number"])
        self.include_travel_box.setChecked(config["include_travel_order_number"])
        self.include_platform_box.setChecked(config["include_platform_identity"])
        self.include_formation_box.setChecked(config["include_formation_identity"])
        self._update_controls()

    def _set_changed(self, *_args):
        settings = settings_for_template_set(self.doc, self.current_set_id())
        self._load_config(read_assembly_label_config(settings))
        self.refresh_preview()

    def _update_controls(self, *_args):
        enabled = bool(self.enabled_box.isChecked())
        custom = str(self.format_box.currentText()) == ASSEMBLY_LABEL_FORMAT_CUSTOM
        self.custom_format_box.setEnabled(enabled and custom)
        safe_stroke_maximum = max(
            0.08, min(2.0, float(self.text_height_box.value()) / 7.0)
        )
        self.stroke_width_box.setMaximum(safe_stroke_maximum)
        if float(self.stroke_width_box.value()) > safe_stroke_maximum:
            self.stroke_width_box.setValue(safe_stroke_maximum)
        self.apply_button.setText(
            "Apply labels to selected set" if enabled else "Remove labels from selected set"
        )
        for widget in (
            self.format_box, self.text_height_box, self.stroke_width_box,
            self.depth_box, self.margin_box, self.placement_box,
            self.include_set_box, self.include_track_box, self.include_track_name_box,
            self.include_section_box, self.include_travel_box,
            self.include_platform_box, self.include_formation_box,
        ):
            widget.setEnabled(enabled)

    def refresh_preview(self, *_args):
        self.table.setRowCount(0)
        set_id = self.current_set_id()
        if not set_id:
            self.summary_label.setText("No generated template set is available.")
            self.apply_button.setEnabled(False)
            return
        try:
            config = self._current_config()
            base_records = assembly_label_records_from_index(self.doc, set_id)
            _records, diagnostics = apply_assembly_labels_to_records(base_records, config, set_id)
            self.table.setRowCount(len(diagnostics))
            for row_index, item in enumerate(diagnostics):
                detail = item.get("reason") or item.get("surface") or ""
                values = [
                    item.get("target_label") or item.get("target_key") or "",
                    item.get("label_text") or "",
                    item.get("status") or "",
                    detail,
                ]
                for column_index, value in enumerate(values):
                    self.table.setItem(row_index, column_index, QtWidgets.QTableWidgetItem(str(value)))
            placed = sum(1 for item in diagnostics if item.get("status") == "Placed")
            skipped = sum(1 for item in diagnostics if item.get("status") == "Skipped")
            if not config.get("enabled", False):
                self.summary_label.setText(
                    "Labels are disabled. Applying this configuration will remove only label-derived hidden production sources."
                )
            else:
                self.summary_label.setText(
                    "{} eligible production part(s): {} label(s) can be placed; {} will be safely skipped.".format(
                        len(diagnostics), placed, skipped
                    )
                )
            self.apply_button.setEnabled(True)
        except Exception as error:
            self.summary_label.setText(str(error))
            self.apply_button.setEnabled(False)

    def apply_labels(self):
        try:
            set_id = self.current_set_id()
            config = self._current_config()
            index_payload, diagnostics = rebuild_assembly_labels_for_set(
                self.doc, set_id, config
            )
            placed = sum(1 for item in diagnostics if item.get("status") == "Placed")
            skipped = sum(1 for item in diagnostics if item.get("status") == "Skipped")
            warnings = [
                str(item.get("reason") or "") for item in diagnostics
                if item.get("status") == "Warning" and str(item.get("reason") or "")
            ]
            self.refresh_preview()
            message = (
                "Assembly labels updated for {}.\n\nPlaced: {}\nSafely skipped: {}\nProduction records: {}"
            ).format(set_id, placed, skipped, len(index_payload.get("records", [])))
            if warnings:
                message += "\n\nReport refresh warning{}:\n{}".format(
                    "s" if len(warnings) != 1 else "",
                    "\n".join("- {}".format(value) for value in warnings),
                )
            QtWidgets.QMessageBox.information(
                self, versioned_dialog_title("Assembly labels updated"), message
            )
        except Exception as error:
            QtWidgets.QMessageBox.critical(
                self, versioned_dialog_title("Assembly-label error"), str(error)
            )

def _dialog_preview(items, limit=6):
    items = list(items or [])
    if not items:
        return "None"
    lines = []
    for index, item in enumerate(items[:limit], 1):
        text = str(item).replace("\n", " ").strip()
        if len(text) > 280:
            text = text[:277] + "..."
        lines.append("{}. {}".format(index, text))
    if len(items) > limit:
        lines.append("... and {} more; use Show Details for the complete list.".format(
            len(items) - limit
        ))
    return "\n".join(lines)


def show_production_export_summary(summary):
    failures = list(summary.get("failures") or [])
    skipped_outputs = list(summary.get("skipped_outputs") or [])
    manifest_path = str(summary.get("manifest_path") or "")
    if manifest_path:
        manifest_text = manifest_path
    elif summary.get("manifest_requested", False):
        manifest_text = "Requested but not created"
    else:
        manifest_text = "Not requested"

    informative_text = (
        "Output directory: {directory}\n"
        "Successful files: {successful}\n"
        "Failed files: {failed}\n"
        "Skipped outputs: {skipped}\n"
        "Formats produced: {formats}\n"
        "Manifest: {manifest}\n\n"
        "Failed outputs:\n{failures}\n\n"
        "Skipped outputs:\n{skips}"
    ).format(
        directory=summary.get("output_directory", ""),
        successful=summary.get("successful_files", 0),
        failed=summary.get("failed_files", 0),
        skipped=summary.get("skipped_objects", 0),
        formats=", ".join(summary.get("formats", [])) or "None",
        manifest=manifest_text,
        failures=_dialog_preview(failures),
        skips=_dialog_preview(skipped_outputs),
    )

    detail_sections = []
    failure_details = list(summary.get("failure_details") or failures)
    skipped_details = list(summary.get("skipped_details") or skipped_outputs)
    if failure_details:
        detail_sections.append(
            "FAILED OUTPUTS\n\n" + "\n\n".join(
                "{}. {}".format(index, detail)
                for index, detail in enumerate(failure_details, 1)
            )
        )
    if skipped_details:
        detail_sections.append(
            "SKIPPED OUTPUTS\n\n" + "\n\n".join(
                "{}. {}".format(index, detail)
                for index, detail in enumerate(skipped_details, 1)
            )
        )

    box = QtWidgets.QMessageBox()
    box.setWindowTitle(versioned_dialog_title("Production export complete"))
    try:
        warning_icon = QtWidgets.QMessageBox.Warning
        information_icon = QtWidgets.QMessageBox.Information
    except AttributeError:
        warning_icon = QtWidgets.QMessageBox.Icon.Warning
        information_icon = QtWidgets.QMessageBox.Icon.Information
    has_warnings = bool(failures or skipped_outputs)
    box.setIcon(warning_icon if has_warnings else information_icon)
    box.setText(
        "Production export completed with warnings."
        if has_warnings
        else "Production export completed successfully."
    )
    box.setInformativeText(informative_text)
    if detail_sections:
        box.setDetailedText("\n\n".join(detail_sections))
    dialog_exec(box)


def open_export_directory(path):
    if not path:
        return
    try:
        url = QtCore.QUrl.fromLocalFile(path)
        if QtGui.QDesktopServices.openUrl(url):
            return
    except Exception:
        pass
    try:
        if sys.platform.startswith("win"):
            os.startfile(path)
        elif sys.platform == "darwin":
            subprocess.Popen(["open", path])
        else:
            subprocess.Popen(["xdg-open", path])
    except Exception:
        pass



class PresetDetailsDialog(QtWidgets.QDialog):
    def __init__(self, title, name="", description="", parent=None):
        super(PresetDetailsDialog, self).__init__(parent)
        self.setWindowTitle(versioned_dialog_title(title))
        self.resize(620, 300)
        layout = QtWidgets.QVBoxLayout(self)
        form = QtWidgets.QFormLayout()
        self.name_box = QtWidgets.QLineEdit(str(name or ""))
        self.name_box.setMaxLength(PRESET_MAX_NAME_LENGTH)
        self.description_box = QtWidgets.QPlainTextEdit()
        self.description_box.setPlainText(str(description or ""))
        form.addRow("Preset name:", self.name_box)
        form.addRow("Description:", self.description_box)
        layout.addLayout(form)
        note = QtWidgets.QLabel(
            "The preset stores reusable dialogue configuration only. It does not contain generated FreeCAD shapes, object names or executable content."
        )
        note.setWordWrap(True)
        layout.addWidget(note)
        try:
            ok_button = QtWidgets.QDialogButtonBox.Ok
            cancel_button = QtWidgets.QDialogButtonBox.Cancel
        except AttributeError:
            ok_button = QtWidgets.QDialogButtonBox.StandardButton.Ok
            cancel_button = QtWidgets.QDialogButtonBox.StandardButton.Cancel
        buttons = QtWidgets.QDialogButtonBox(ok_button | cancel_button)
        buttons.accepted.connect(self._accept_checked)
        buttons.rejected.connect(self.reject)
        layout.addWidget(buttons)

    def _accept_checked(self):
        name = str(self.name_box.text() or "").strip()
        description = str(self.description_box.toPlainText() or "")
        if not name:
            QtWidgets.QMessageBox.warning(self, versioned_dialog_title("Preset name required"), "Enter a preset name.")
            return
        if len(description) > PRESET_MAX_DESCRIPTION_LENGTH:
            QtWidgets.QMessageBox.warning(
                self,
                versioned_dialog_title("Description too long"),
                "The description must not exceed {} characters.".format(PRESET_MAX_DESCRIPTION_LENGTH),
            )
            return
        if _configuration_string_looks_executable(name) or _configuration_string_looks_executable(description):
            QtWidgets.QMessageBox.warning(
                self,
                versioned_dialog_title("Unsafe preset text"),
                "Preset names and descriptions must contain plain non-executable text.",
            )
            return
        self.accept()

    def values(self):
        return str(self.name_box.text() or "").strip(), str(self.description_box.toPlainText() or "")


class NamedPresetManagerDialog(QtWidgets.QDialog):
    def __init__(self, main_dialog, parent=None):
        super(NamedPresetManagerDialog, self).__init__(parent)
        self.main_dialog = main_dialog
        self.library_load_result = getattr(
            main_dialog,
            "_preset_library_load_result",
            {"valid": True, "presets": main_dialog._configuration_presets, "message": ""},
        )
        self.presets = normalise_named_preset_collection(main_dialog._configuration_presets)
        saved_at_open = (
            self.library_load_result.get("presets", [])
            if self.library_load_result.get("valid")
            else []
        )
        self._saved_library_signature = self._preset_signature(saved_at_open)
        self.setWindowTitle(versioned_dialog_title("Named preset manager"))
        self.resize(1180, 720)

        layout = QtWidgets.QVBoxLayout(self)
        note = QtWidgets.QLabel(
            "Presets capture the complete reusable settings currently shown in the main dialogue. Applying a preset only populates controls; it never regenerates geometry. Changes remain in the working library until Save preset library is deliberately selected."
        )
        note.setWordWrap(True)
        layout.addWidget(note)

        self.table = QtWidgets.QTableWidget(0, 7)
        self.table.setHorizontalHeaderLabels([
            "Name", "Description", "Modified UTC", "Curve tracks", "Straight routes", "Platforms", "Preset ID"
        ])
        self.table.setEditTriggers(QtWidgets.QAbstractItemView.NoEditTriggers)
        self.table.setSelectionBehavior(QtWidgets.QAbstractItemView.SelectRows)
        self.table.setSelectionMode(QtWidgets.QAbstractItemView.SingleSelection)
        self.table.setAlternatingRowColors(True)
        layout.addWidget(self.table, 1)

        controls = QtWidgets.QGridLayout()
        self.new_button = QtWidgets.QPushButton("Save current as new...")
        self.update_button = QtWidgets.QPushButton("Update selected from dialogue")
        self.edit_button = QtWidgets.QPushButton("Rename or edit description...")
        self.duplicate_button = QtWidgets.QPushButton("Duplicate selected")
        self.delete_button = QtWidgets.QPushButton("Delete selected")
        self.apply_button = QtWidgets.QPushButton("Apply selected to dialogue")
        self.summary_button = QtWidgets.QPushButton("Show selected summary")
        self.save_library_button = QtWidgets.QPushButton("Save preset library")
        self.reload_button = QtWidgets.QPushButton("Reload saved library")
        widgets = [
            self.new_button, self.update_button, self.edit_button,
            self.duplicate_button, self.delete_button, self.apply_button,
            self.summary_button, self.save_library_button, self.reload_button,
        ]
        for index, widget in enumerate(widgets):
            controls.addWidget(widget, index // 3, index % 3)
        layout.addLayout(controls)

        self.status_label = QtWidgets.QLabel("")
        self.status_label.setWordWrap(True)
        layout.addWidget(self.status_label)
        try:
            close_button = QtWidgets.QDialogButtonBox.Close
        except AttributeError:
            close_button = QtWidgets.QDialogButtonBox.StandardButton.Close
        buttons = QtWidgets.QDialogButtonBox(close_button)
        buttons.rejected.connect(self.reject)
        layout.addWidget(buttons)

        self.new_button.clicked.connect(self._new_preset)
        self.update_button.clicked.connect(self._update_selected)
        self.edit_button.clicked.connect(self._edit_selected)
        self.duplicate_button.clicked.connect(self._duplicate_selected)
        self.delete_button.clicked.connect(self._delete_selected)
        self.apply_button.clicked.connect(self._apply_selected)
        self.summary_button.clicked.connect(self._show_summary)
        self.save_library_button.clicked.connect(self._save_library)
        self.reload_button.clicked.connect(self._reload_library)
        self.table.itemSelectionChanged.connect(self._selection_changed)
        self._refresh()
        if not self.library_load_result.get("valid", True):
            self.status_label.setText(
                "The saved preset library could not be loaded: {} The working library starts empty. "
                "Saving will require a separate confirmation before the stored value is replaced.".format(
                    self.library_load_result.get("message", "validation failed")
                )
            )

    @staticmethod
    def _preset_signature(presets):
        try:
            normalised = normalise_named_preset_collection(presets or [])
            return json.dumps(normalised, ensure_ascii=False, sort_keys=True, separators=(",", ":"))
        except Exception:
            return "<invalid>"

    def _has_unsaved_library_changes(self):
        return self._preset_signature(self.presets) != self._saved_library_signature

    def reject(self):
        if self._has_unsaved_library_changes():
            try:
                yes_button = QtWidgets.QMessageBox.Yes
                no_button = QtWidgets.QMessageBox.No
            except AttributeError:
                yes_button = QtWidgets.QMessageBox.StandardButton.Yes
                no_button = QtWidgets.QMessageBox.StandardButton.No
            answer = QtWidgets.QMessageBox.question(
                self,
                versioned_dialog_title("Close with unsaved preset changes"),
                "Close the preset manager without saving the persistent library? The working presets will remain available in the open main dialogue and configuration export, but will not survive a later macro restart unless saved.",
                yes_button | no_button,
                no_button,
            )
            if answer != yes_button:
                return
        super(NamedPresetManagerDialog, self).reject()

    def _selected_index(self):
        row = self.table.currentRow()
        return row if 0 <= row < len(self.presets) else -1

    def _selected(self):
        index = self._selected_index()
        return self.presets[index] if index >= 0 else None

    def _set_working_presets(self, presets):
        self.presets = normalise_named_preset_collection(presets)
        self.main_dialog._configuration_presets = _configuration_json_copy(self.presets)
        self._refresh()

    def _refresh(self, preferred_id=None):
        self.presets = normalise_named_preset_collection(self.presets)
        ordered = sorted(self.presets, key=lambda item: (item["name"].casefold(), item["preset_id"]))
        self.presets = ordered
        self.main_dialog._configuration_presets = _configuration_json_copy(self.presets)
        self.table.setRowCount(len(self.presets))
        selected_row = -1
        for row, preset in enumerate(self.presets):
            config = preset["configuration"]
            values = [
                preset["name"], preset.get("description", ""), preset["modified_utc"],
                str(1 + len(config.get("tracks", []))),
                str(len(config.get("straight_routes", []))),
                str(len(config.get("platforms", []))),
                preset["preset_id"],
            ]
            for column, value in enumerate(values):
                self.table.setItem(row, column, QtWidgets.QTableWidgetItem(value))
            if preferred_id and preset["preset_id"] == preferred_id:
                selected_row = row
        try:
            self.table.horizontalHeader().setStretchLastSection(True)
            self.table.resizeColumnsToContents()
        except Exception:
            pass
        if selected_row >= 0:
            self.table.selectRow(selected_row)
        elif self.presets:
            self.table.selectRow(0)
        state = "unsaved working changes" if self._has_unsaved_library_changes() else "matches the saved library"
        self.status_label.setText(
            "Working library: {} preset(s); {}. Use Save preset library to persist changes beyond this macro session.".format(
                len(self.presets), state
            )
        )
        self._selection_changed()

    def _selection_changed(self):
        enabled = self._selected() is not None
        for button in (
            self.update_button, self.edit_button, self.duplicate_button,
            self.delete_button, self.apply_button, self.summary_button,
        ):
            button.setEnabled(enabled)

    def _name_available(self, name, ignore_id=None):
        key = str(name or "").strip().casefold()
        return all(
            preset["preset_id"] == ignore_id or preset["name"].casefold() != key
            for preset in self.presets
        )

    def _new_preset(self):
        if len(self.presets) >= CONFIGURATION_MAX_PRESETS:
            QtWidgets.QMessageBox.warning(
                self,
                versioned_dialog_title("Preset limit reached"),
                "The working library already contains the maximum of {} presets.".format(CONFIGURATION_MAX_PRESETS),
            )
            return
        dialog = PresetDetailsDialog("Create named preset", parent=self)
        accepted_code = getattr(QtWidgets.QDialog, "Accepted", None)
        if accepted_code is None:
            accepted_code = QtWidgets.QDialog.DialogCode.Accepted
        if dialog_exec(dialog) != accepted_code:
            return
        name, description = dialog.values()
        if not self._name_available(name):
            QtWidgets.QMessageBox.warning(self, versioned_dialog_title("Duplicate preset name"), "A preset with that name already exists.")
            return
        preset = build_named_preset(name, description, self.main_dialog.build_current_configuration_payload())
        self.presets.append(preset)
        self._refresh(preset["preset_id"])

    def _update_selected(self):
        preset = self._selected()
        if preset is None:
            return
        try:
            yes_button = QtWidgets.QMessageBox.Yes
            no_button = QtWidgets.QMessageBox.No
        except AttributeError:
            yes_button = QtWidgets.QMessageBox.StandardButton.Yes
            no_button = QtWidgets.QMessageBox.StandardButton.No
        answer = QtWidgets.QMessageBox.question(
            self,
            versioned_dialog_title("Update named preset"),
            "Replace the stored configuration snapshot for '{}'? The preset name and description will remain unchanged.".format(preset["name"]),
            yes_button | no_button,
            no_button,
        )
        if answer != yes_button:
            return
        replacement = build_named_preset(
            preset["name"], preset.get("description", ""),
            self.main_dialog.build_current_configuration_payload(),
            preset_id=preset["preset_id"], created_utc=preset["created_utc"],
        )
        self.presets[self._selected_index()] = replacement
        self._refresh(replacement["preset_id"])

    def _edit_selected(self):
        preset = self._selected()
        if preset is None:
            return
        dialog = PresetDetailsDialog(
            "Edit named preset", preset["name"], preset.get("description", ""), self
        )
        accepted_code = getattr(QtWidgets.QDialog, "Accepted", None)
        if accepted_code is None:
            accepted_code = QtWidgets.QDialog.DialogCode.Accepted
        if dialog_exec(dialog) != accepted_code:
            return
        name, description = dialog.values()
        if not self._name_available(name, ignore_id=preset["preset_id"]):
            QtWidgets.QMessageBox.warning(self, versioned_dialog_title("Duplicate preset name"), "A preset with that name already exists.")
            return
        preset["name"] = name
        preset["description"] = description
        preset["modified_utc"] = _preset_utc_now()
        self._refresh(preset["preset_id"])

    def _duplicate_selected(self):
        source = self._selected()
        if source is None:
            return
        if len(self.presets) >= CONFIGURATION_MAX_PRESETS:
            QtWidgets.QMessageBox.warning(
                self,
                versioned_dialog_title("Preset limit reached"),
                "The working library already contains the maximum of {} presets.".format(CONFIGURATION_MAX_PRESETS),
            )
            return
        names = {item["name"] for item in self.presets}
        duplicate = _configuration_json_copy(source)
        duplicate["preset_id"] = uuid.uuid4().hex
        duplicate["name"] = _unique_preset_name(source["name"] + " copy", names)
        duplicate["created_utc"] = _preset_utc_now()
        duplicate["modified_utc"] = duplicate["created_utc"]
        duplicate["source_macro_version"] = MACRO_VERSION_NUMBER
        self.presets.append(duplicate)
        self._refresh(duplicate["preset_id"])

    def _delete_selected(self):
        preset = self._selected()
        index = self._selected_index()
        if preset is None or index < 0:
            return
        try:
            yes_button = QtWidgets.QMessageBox.Yes
            no_button = QtWidgets.QMessageBox.No
        except AttributeError:
            yes_button = QtWidgets.QMessageBox.StandardButton.Yes
            no_button = QtWidgets.QMessageBox.StandardButton.No
        answer = QtWidgets.QMessageBox.question(
            self,
            versioned_dialog_title("Delete named preset"),
            "Remove '{}' from the working preset library?".format(preset["name"]),
            yes_button | no_button,
            no_button,
        )
        if answer == yes_button:
            self.presets.pop(index)
            self._refresh()

    def _apply_selected(self):
        preset = self._selected()
        if preset is None:
            return
        payload = preset_configuration_payload(preset, presets=self.presets)
        current = self.main_dialog.build_current_configuration_payload()
        changes = configuration_change_summary(current, payload)
        preview = configuration_summary(payload)
        try:
            yes_button = QtWidgets.QMessageBox.Yes
            no_button = QtWidgets.QMessageBox.No
        except AttributeError:
            yes_button = QtWidgets.QMessageBox.StandardButton.Yes
            no_button = QtWidgets.QMessageBox.StandardButton.No
        answer = QtWidgets.QMessageBox.question(
            self,
            versioned_dialog_title("Apply named preset"),
            "Apply '{}' to the open dialogue?\n\n{}\n\n{} setting value(s) will change. Generated geometry and stored document settings will remain unchanged.".format(
                preset["name"], preview, len(changes)
            ),
            yes_button | no_button,
            no_button,
        )
        if answer != yes_button:
            return
        self.main_dialog.apply_configuration_payload(payload)
        self.presets = normalise_named_preset_collection(self.main_dialog._configuration_presets)
        self._refresh(preset["preset_id"])
        self.status_label.setText(
            "Applied '{}'. Review the populated controls, then use the normal Generate action only when ready.".format(preset["name"])
        )

    def _show_summary(self):
        preset = self._selected()
        if preset is None:
            return
        payload = preset_configuration_payload(preset, presets=self.presets)
        QtWidgets.QMessageBox.information(
            self,
            versioned_dialog_title("Named preset summary"),
            "{}\n\nDescription: {}\n\n{}".format(
                preset["name"], preset.get("description", "") or "(none)", configuration_summary(payload)
            ),
        )

    def _save_library(self):
        if not self.library_load_result.get("valid", True):
            try:
                yes_button = QtWidgets.QMessageBox.Yes
                no_button = QtWidgets.QMessageBox.No
            except AttributeError:
                yes_button = QtWidgets.QMessageBox.StandardButton.Yes
                no_button = QtWidgets.QMessageBox.StandardButton.No
            answer = QtWidgets.QMessageBox.question(
                self,
                versioned_dialog_title("Replace damaged preset library"),
                "The existing saved preset library could not be validated. Replace it with the current working library?",
                yes_button | no_button,
                no_button,
            )
            if answer != yes_button:
                return
        try:
            saved = write_named_preset_library(self.presets)
            self.presets = saved
            self.library_load_result = {
                "valid": True,
                "presets": _configuration_json_copy(saved),
                "diagnostics": [],
                "message": "Loaded {} saved preset(s).".format(len(saved)),
            }
            self.main_dialog._preset_library_load_result = _configuration_json_copy(self.library_load_result)
            self.main_dialog._configuration_presets = _configuration_json_copy(saved)
            self._saved_library_signature = self._preset_signature(saved)
            self._refresh()
            self.status_label.setText("Saved {} preset(s) to the persistent user library.".format(len(saved)))
        except Exception as error:
            show_error(str(error))

    def _reload_library(self):
        result = load_named_preset_library()
        if not result.get("valid"):
            QtWidgets.QMessageBox.warning(
                self,
                versioned_dialog_title("Preset library unavailable"),
                result.get("message", "The saved preset library could not be loaded."),
            )
            return
        try:
            yes_button = QtWidgets.QMessageBox.Yes
            no_button = QtWidgets.QMessageBox.No
        except AttributeError:
            yes_button = QtWidgets.QMessageBox.StandardButton.Yes
            no_button = QtWidgets.QMessageBox.StandardButton.No
        answer = QtWidgets.QMessageBox.question(
            self,
            versioned_dialog_title("Reload saved preset library"),
            "Replace the current working library with the saved library? Unsaved working changes will be discarded.",
            yes_button | no_button,
            no_button,
        )
        if answer == yes_button:
            self.presets = result["presets"]
            self.library_load_result = result
            self.main_dialog._preset_library_load_result = _configuration_json_copy(result)
            self._saved_library_signature = self._preset_signature(result["presets"])
            self._refresh()
            self.status_label.setText(result.get("message", "Saved library reloaded."))

class ConfigurationImportExportDialog(QtWidgets.QDialog):
    def __init__(self, main_dialog, parent=None):
        super(ConfigurationImportExportDialog, self).__init__(parent)
        self.main_dialog = main_dialog
        self.validated_payload = None
        self.validated_path = ""
        self.setWindowTitle(versioned_dialog_title("Configuration import and export"))
        self.resize(1180, 760)

        layout = QtWidgets.QVBoxLayout(self)
        note = QtWidgets.QLabel(
            "Export the complete reusable macro configuration as readable JSON, or select a JSON file "
            "for full in-memory validation. Applying an import changes only the open dialogue. It does not "
            "regenerate geometry, alter generated objects or store document settings. Transported presets are merged "
            "into the working library and remain unsaved until the Preset Manager explicitly saves them. Use the main Generate "
            "button afterwards when the reviewed values are ready."
        )
        note.setWordWrap(True)
        layout.addWidget(note)

        controls = QtWidgets.QHBoxLayout()
        self.export_button = QtWidgets.QPushButton("Export current configuration...")
        self.import_button = QtWidgets.QPushButton("Import and validate...")
        self.validate_button = QtWidgets.QPushButton("Validate file only...")
        self.summary_button = QtWidgets.QPushButton("Show current summary")
        controls.addWidget(self.export_button)
        controls.addWidget(self.import_button)
        controls.addWidget(self.validate_button)
        controls.addWidget(self.summary_button)
        controls.addStretch(1)
        layout.addLayout(controls)

        self.status_label = QtWidgets.QLabel("No configuration file selected.")
        self.status_label.setWordWrap(True)
        layout.addWidget(self.status_label)

        splitter = QtWidgets.QSplitter(QtCore.Qt.Vertical)
        diagnostics_group = QtWidgets.QGroupBox("Validation and migration diagnostics")
        diagnostics_layout = QtWidgets.QVBoxLayout(diagnostics_group)
        self.diagnostics_table = QtWidgets.QTableWidget(0, 7)
        self.diagnostics_table.setHorizontalHeaderLabels([
            "Severity", "Field path", "Supplied value", "Expected", "Message", "Migration/default", "Blocks import"
        ])
        self.diagnostics_table.setEditTriggers(QtWidgets.QAbstractItemView.NoEditTriggers)
        self.diagnostics_table.setSelectionBehavior(QtWidgets.QAbstractItemView.SelectRows)
        self.diagnostics_table.setAlternatingRowColors(True)
        diagnostics_layout.addWidget(self.diagnostics_table)
        splitter.addWidget(diagnostics_group)

        changes_group = QtWidgets.QGroupBox("Settings that will change")
        changes_layout = QtWidgets.QVBoxLayout(changes_group)
        self.summary_box = QtWidgets.QPlainTextEdit()
        self.summary_box.setReadOnly(True)
        self.summary_box.setMaximumBlockCount(10000)
        changes_layout.addWidget(self.summary_box)
        self.changes_table = QtWidgets.QTableWidget(0, 3)
        self.changes_table.setHorizontalHeaderLabels([
            "Field path", "Current dialogue value", "Imported value"
        ])
        self.changes_table.setEditTriggers(QtWidgets.QAbstractItemView.NoEditTriggers)
        self.changes_table.setSelectionBehavior(QtWidgets.QAbstractItemView.SelectRows)
        self.changes_table.setAlternatingRowColors(True)
        changes_layout.addWidget(self.changes_table)
        splitter.addWidget(changes_group)
        layout.addWidget(splitter, 1)

        try:
            close_button = QtWidgets.QDialogButtonBox.Close
        except AttributeError:
            close_button = QtWidgets.QDialogButtonBox.StandardButton.Close
        buttons = QtWidgets.QDialogButtonBox(close_button)
        self.apply_button = buttons.addButton(
            "Copy validated settings into main dialogue",
            QtWidgets.QDialogButtonBox.ActionRole,
        )
        self.apply_button.setEnabled(False)
        buttons.rejected.connect(self.reject)
        self.apply_button.clicked.connect(self._apply_validated)
        layout.addWidget(buttons)

        self.export_button.clicked.connect(self._export_current)
        self.import_button.clicked.connect(lambda: self._select_and_validate(True))
        self.validate_button.clicked.connect(lambda: self._select_and_validate(False))
        self.summary_button.clicked.connect(self._show_current_summary)
        self._resize_tables()

    def _resize_tables(self):
        try:
            for table in (self.diagnostics_table, self.changes_table):
                table.horizontalHeader().setStretchLastSection(True)
                table.resizeColumnsToContents()
        except Exception:
            pass

    @staticmethod
    def _file_dialog_path(result):
        if isinstance(result, (tuple, list)):
            return str(result[0] or "")
        return str(result or "")

    def _current_payload(self):
        return self.main_dialog.build_current_configuration_payload()

    def _export_current(self):
        try:
            payload = self._current_payload()
            production_directory = payload["configuration"]["production_export"]["output_directory"]
            start_directory = production_directory if os.path.isdir(production_directory) else os.path.expanduser("~")
            suggested = os.path.join(
                start_directory,
                "model_railway_configuration_{}.json".format(MACRO_VERSION_NUMBER.lower()),
            )
            selected = self._file_dialog_path(
                QtWidgets.QFileDialog.getSaveFileName(
                    self,
                    "Export model railway configuration",
                    suggested,
                    "JSON configuration (*.json)",
                )
            )
            if not selected:
                return
            target = selected if selected.lower().endswith(".json") else selected + ".json"
            overwrite = False
            if os.path.exists(target):
                try:
                    yes_button = QtWidgets.QMessageBox.Yes
                    no_button = QtWidgets.QMessageBox.No
                except AttributeError:
                    yes_button = QtWidgets.QMessageBox.StandardButton.Yes
                    no_button = QtWidgets.QMessageBox.StandardButton.No
                answer = QtWidgets.QMessageBox.question(
                    self,
                    versioned_dialog_title("Replace configuration file"),
                    "The file already exists:\n\n{}\n\nReplace it atomically?".format(target),
                    yes_button | no_button,
                    no_button,
                )
                if answer != yes_button:
                    return
                overwrite = True
            written = export_configuration_json_atomic(target, payload, overwrite=overwrite)
            self.status_label.setText("Exported configuration: {}".format(written))
            QtWidgets.QMessageBox.information(
                self,
                versioned_dialog_title("Configuration exported"),
                "The complete reusable configuration was written atomically to:\n\n{}".format(written),
            )
        except Exception as error:
            show_error(str(error))

    def _select_and_validate(self, allow_apply):
        selected = self._file_dialog_path(
            QtWidgets.QFileDialog.getOpenFileName(
                self,
                "Select model railway configuration",
                os.path.expanduser("~"),
                "JSON configuration (*.json)",
            )
        )
        if selected:
            self._load_validation(selected, allow_apply)

    def _load_validation(self, path, allow_apply):
        result = import_configuration_json(path)
        self.validated_payload = result.get("payload") if result.get("valid") and allow_apply else None
        self.validated_path = str(path)
        diagnostics = result.get("diagnostics", [])
        self._populate_diagnostics(diagnostics)
        self.apply_button.setEnabled(self.validated_payload is not None)
        if result.get("valid"):
            imported = result["payload"]
            current = self._current_payload()
            changes = configuration_change_summary(current, imported)
            self._populate_changes(changes)
            self.summary_box.setPlainText(
                configuration_summary(imported)
                + "\n\n{} setting value(s) differ from the open dialogue.".format(len(changes))
                + ("\n\nValidation only: no settings can be applied from this pass." if not allow_apply else "")
            )
            self.status_label.setText(
                "Validated successfully: {}. {} diagnostic item(s); {} change(s).{}".format(
                    path,
                    len(diagnostics),
                    len(changes),
                    " Ready to copy into the main dialogue." if allow_apply else " No changes were applied.",
                )
            )
        else:
            self._populate_changes([])
            error_count = sum(1 for item in diagnostics if item.get("blocks_import"))
            self.summary_box.setPlainText(
                "Import blocked. {} error(s) must be corrected. The current dialogue, stored settings and generated geometry are unchanged.".format(error_count)
            )
            self.status_label.setText("Validation failed: {}".format(path))
        self._resize_tables()

    def _populate_diagnostics(self, diagnostics):
        self.diagnostics_table.setRowCount(len(diagnostics))
        for row, item in enumerate(diagnostics):
            values = [
                item.get("severity", ""),
                item.get("field_path", ""),
                _configuration_display_value(item.get("supplied_value")),
                item.get("expected", ""),
                item.get("message", ""),
                item.get("migration_action", "") or ("Default applied" if item.get("default_applied") else ""),
                "Yes" if item.get("blocks_import") else "No",
            ]
            for column, value in enumerate(values):
                self.diagnostics_table.setItem(row, column, QtWidgets.QTableWidgetItem(str(value)))

    def _populate_changes(self, changes):
        self.changes_table.setRowCount(len(changes))
        for row, item in enumerate(changes):
            values = [
                item.get("field_path", ""),
                _configuration_display_value(item.get("current_value")),
                _configuration_display_value(item.get("imported_value")),
            ]
            for column, value in enumerate(values):
                self.changes_table.setItem(row, column, QtWidgets.QTableWidgetItem(str(value)))

    def _show_current_summary(self):
        try:
            payload = self._current_payload()
            self.summary_box.setPlainText(configuration_summary(payload))
            self._populate_changes([])
            self._populate_diagnostics([])
            self.validated_payload = None
            self.apply_button.setEnabled(False)
            self.status_label.setText("Showing the current open-dialogue configuration.")
        except Exception as error:
            show_error(str(error))

    def _apply_validated(self):
        if self.validated_payload is None:
            return
        changes = configuration_change_summary(
            self._current_payload(), self.validated_payload
        )
        transported = len(self.validated_payload.get("presets", []))
        preset_notice = ""
        if transported:
            preset_notice = (
                "\n\nThis configuration also carries {} named preset(s). They will be merged into "
                "the working library, with conflicting imported names safely renamed. The persistent "
                "user library will not change until Save preset library is selected."
            ).format(transported)
        try:
            yes_button = QtWidgets.QMessageBox.Yes
            no_button = QtWidgets.QMessageBox.No
        except AttributeError:
            yes_button = QtWidgets.QMessageBox.StandardButton.Yes
            no_button = QtWidgets.QMessageBox.StandardButton.No
        answer = QtWidgets.QMessageBox.question(
            self,
            versioned_dialog_title("Apply imported configuration"),
            (
                "Copy {} changed setting value(s) into the open main dialogue?\n\n"
                "This will not regenerate geometry, alter existing objects or store document settings. "
                "Review the populated controls, then use the normal Generate action deliberately.{}"
            ).format(len(changes), preset_notice),
            yes_button | no_button,
            no_button,
        )
        if answer != yes_button:
            return
        apply_configuration_to_dialog(self.main_dialog, self.validated_payload)
        report = getattr(self.main_dialog, "_last_preset_merge_report", None) or {}
        preset_result = ""
        if transported:
            preset_result = " Preset merge: {} added, {} renamed and {} identical skipped.".format(
                report.get("added", 0), report.get("renamed", 0), report.get("skipped_identical", 0)
            )
        self.status_label.setText(
            "Validated settings copied into the main dialogue. No geometry has been regenerated." + preset_result
        )
        QtWidgets.QMessageBox.information(
            self,
            versioned_dialog_title("Configuration copied"),
            "The validated values now populate the main dialogue. Existing geometry and stored document settings remain unchanged until the normal Generate action is accepted." + preset_result,
        )
        self.accept()

def store_parameters(
    obj,
    transition,
    radius,
    angle,
    main_width,
    track_configs,
    straight_configs,
    straight_route_results,
    turn_sign,
    main_alignment,
    track_alignments,
    platform_configs,
    platform_results,
    formation_config,
    formation_geometry,
    section_config,
    section_plan,
    registration_config,
    template_assembly_config,
    production_export_config,
    template_assembly_summary,
    output_mode,
    production_record_index=None,
):
    input_properties = [
        ensure_property(obj, "App::PropertyLength", "TransitionLength", "Inputs used", "Length of each main-track Euler easement"),
        ensure_property(obj, "App::PropertyLength", "CurveRadius", "Inputs used", "Main-track constant curve radius"),
        ensure_property(obj, "App::PropertyAngle", "TotalTurnAngle", "Inputs used", "Total direction change; positive left and negative right"),
        ensure_property(obj, "App::PropertyLength", "MainTemplateWidth", "Inputs used", "Printable strip width for the main track"),
        ensure_property(obj, "App::PropertyInteger", "ParallelTrackCount", "Inputs used", "Number of additional independent tracks"),
        ensure_property(obj, "App::PropertyString", "TrackConfigurationJSON", "Inputs used", "Stored individual curve-track settings"),
        ensure_property(obj, "App::PropertyString", STRAIGHT_CONFIGS_PROPERTY, "Inputs used", "Stored Straight Track Manager definitions"),
        ensure_property(obj, "App::PropertyString", PLATFORM_CONFIGS_PROPERTY, "Inputs used", "Stored ordered platform definitions"),
        ensure_property(obj, "App::PropertyString", "PlatformConfigurationJSON", "Inputs used", "Version 8 compatibility mirror of the first platform definition"),
        ensure_property(obj, "App::PropertyString", "FormationConfigurationJSON", "Inputs used", "Stored simple formation-board settings"),
        ensure_property(obj, "App::PropertyString", "SectionConfigurationJSON", "Inputs used", "Stored universal sectioning settings"),
        ensure_property(obj, "App::PropertyString", "RegistrationConfigurationJSON", "Inputs used", "Stored formation-board registration and joint settings"),
        ensure_property(obj, "App::PropertyString", "TrackTemplateAssemblyConfigurationJSON", "Inputs used", "Stored track-template joint and fixing-hole settings"),
        ensure_property(obj, "App::PropertyString", PRODUCTION_EXPORT_SETTINGS_PROPERTY, "Inputs used", "Stored production-export settings"),
        ensure_property(obj, "App::PropertyString", MATERIAL_REPORT_SETTINGS_PROPERTY, "Production utilities", "Stored material and sheet-estimate settings"),
        ensure_property(obj, "App::PropertyString", "OutputBehaviour", "Inputs used", "Output mode selected when this set was generated"),
    ]

    calculated_properties = [
        ensure_property(obj, "App::PropertyString", "TurnDirection", "Calculated", "Direction of the curve"),
        ensure_property(obj, "App::PropertyAngle", "TransitionAngleEach", "Calculated", "Direction change through each main-track easement"),
        ensure_property(obj, "App::PropertyAngle", "CircularArcAngle", "Calculated", "Direction change through the main constant-radius section"),
        ensure_property(obj, "App::PropertyLength", "CircularArcLength", "Calculated", "Main-track constant-curve length"),
        ensure_property(obj, "App::PropertyLength", "TotalCentrelineLength", "Calculated", "Main-track total centreline length including alignment straights"),
        ensure_property(obj, "App::PropertyLength", "AutomaticEntryStraight", "Calculated", "Automatic main-track entry straight used to align all track starts"),
        ensure_property(obj, "App::PropertyLength", "AutomaticExitStraight", "Calculated", "Automatic main-track exit straight used to align all track ends"),
        ensure_property(obj, "App::PropertyLength", "TemplateThickness", "Calculated", "Fixed printable template thickness"),
        ensure_property(obj, "App::PropertyInteger", "StraightRouteCount", "Calculated", "Number of enabled straight routes"),
        ensure_property(obj, "App::PropertyInteger", "StraightTrackCount", "Calculated", "Number of generated straight track alignments"),
        ensure_property(obj, "App::PropertyString", "StraightTrackSummary", "Calculated", "Straight route geometry summary"),
        ensure_property(obj, "App::PropertyInteger", "PlatformDefinitionCount", "Calculated", "Number of stored platform definitions"),
        ensure_property(obj, "App::PropertyInteger", "EnabledPlatformCount", "Calculated", "Number of generated platform definitions"),
        ensure_property(obj, "App::PropertyString", "TrackSummary", "Calculated", "Independent radius, spacing and easement summary"),
        ensure_property(obj, "App::PropertyString", "GeometryMethod", "Calculated", "Geometry method used by the macro"),
        ensure_property(obj, "App::PropertyString", "PlatformSummary", "Calculated", "Multiple-platform geometry summary"),
        ensure_property(obj, "App::PropertyString", "PlatformSTLPath", "Calculated", "Deprecated Version 8 platform-only STL path; production export is used"),
        ensure_property(obj, "App::PropertyString", "FormationSummary", "Calculated", "Simple formation-board summary"),
        ensure_property(obj, "App::PropertyString", "SectionSummary", "Calculated", "Universal sectioning summary"),
        ensure_property(obj, "App::PropertyString", "RegistrationSummary", "Calculated", "Registration feature summary"),
        ensure_property(obj, "App::PropertyString", "TrackTemplateAssemblySummary", "Calculated", "Track-template joint and fixing-hole summary"),
    ]

    normalised_platforms = clone_platform_configs(platform_configs)
    legacy_platform = normalised_platforms[0]

    obj.TransitionLength = transition
    obj.CurveRadius = radius
    obj.TotalTurnAngle = angle
    obj.MainTemplateWidth = main_width
    obj.ParallelTrackCount = len(track_configs)
    obj.TrackConfigurationJSON = json.dumps(track_configs, sort_keys=True)
    setattr(
        obj,
        STRAIGHT_CONFIGS_PROPERTY,
        json.dumps(clone_straight_configs(straight_configs), sort_keys=True),
    )
    setattr(
        obj,
        PLATFORM_CONFIGS_PROPERTY,
        json.dumps(normalised_platforms, sort_keys=True),
    )
    obj.PlatformConfigurationJSON = json.dumps(
        legacy_platform, sort_keys=True
    )
    obj.FormationConfigurationJSON = json.dumps(formation_config, sort_keys=True)
    obj.SectionConfigurationJSON = json.dumps(section_config, sort_keys=True)
    obj.RegistrationConfigurationJSON = json.dumps(registration_config, sort_keys=True)
    obj.TrackTemplateAssemblyConfigurationJSON = json.dumps(template_assembly_config, sort_keys=True)
    setattr(
        obj,
        PRODUCTION_EXPORT_SETTINGS_PROPERTY,
        json.dumps(production_export_config, sort_keys=True),
    )
    setattr(
        obj,
        MATERIAL_REPORT_SETTINGS_PROPERTY,
        json.dumps(read_last_material_report_config(), sort_keys=True),
    )
    if isinstance(production_record_index, dict):
        record_property = ensure_property(
            obj,
            "App::PropertyString",
            PRODUCTION_RECORD_INDEX_PROPERTY,
            "Production utilities",
            "Metadata-only catalogue of recognised production records",
        )
        input_properties.append(record_property)
        setattr(
            obj,
            PRODUCTION_RECORD_INDEX_PROPERTY,
            json.dumps(production_record_index, sort_keys=True),
        )
    obj.OutputBehaviour = output_mode

    obj.TurnDirection = "Left" if turn_sign > 0.0 else "Right"
    obj.TransitionAngleEach = math.degrees(main_alignment["entry_angle"]) * turn_sign
    obj.CircularArcAngle = math.degrees(main_alignment["circular_angle"]) * turn_sign
    obj.CircularArcLength = main_alignment["circular_length"]
    obj.TotalCentrelineLength = main_alignment["total_length"]
    obj.AutomaticEntryStraight = main_alignment.get("entry_extension", 0.0)
    obj.AutomaticExitStraight = main_alignment.get("exit_extension", 0.0)
    obj.TemplateThickness = TEMPLATE_THICKNESS
    obj.StraightRouteCount = len(straight_route_results)
    obj.StraightTrackCount = sum(
        len(route.get("alignments", [])) for route in straight_route_results
    )
    straight_summary_lines = []
    for route in straight_route_results:
        config = route["config"]
        thickness_text = (
            "inherited {:.3f} mm".format(TEMPLATE_THICKNESS)
            if route["connection_mode"] != STRAIGHT_CONNECTION_INDEPENDENT
            else "{:.3f} mm".format(config["template_thickness"])
        )
        straight_summary_lines.append(
            "{name}: {mode}; length {length:.3f} mm; {tracks} track(s); thickness {thickness}; sections {sections}; formation {formation}".format(
                name=route["name"],
                mode=route["connection_mode"],
                length=route["length"],
                tracks=len(route["alignments"]),
                thickness=thickness_text,
                sections=route.get("section_count", 1),
                formation="yes" if route.get("formation_enabled", False) else "no",
            )
        )
    obj.StraightTrackSummary = (
        "\n".join(straight_summary_lines)
        if straight_summary_lines
        else "Straight-track output disabled"
    )
    obj.PlatformDefinitionCount = len(normalised_platforms)
    obj.EnabledPlatformCount = len(platform_results)
    obj.GeometryMethod = (
        "Independent Euler or same-direction platform transitions with concentric "
        "constant-radius curves; exact independent or curve-connected straight routes; "
        "route-local shared section boundaries, template assembly and formation-board "
        "extensions; multiple independent curved platforms; direct simple swept boards"
    )

    if not platform_results:
        obj.PlatformSummary = "Platform output disabled"
    else:
        platform_lines = []
        for result in platform_results:
            config = result["config"]
            geometry = result["geometry"]
            platform_lines.append(
                (
                    "Platform {number:02d} {name}: {description}; coverage {coverage}; "
                    "length {length:.3f} mm; centre offset {centre:.3f} mm; "
                    "full-width minimum {width:.3f} mm; entry/exit ends "
                    "{entry}/{exit}; trackbed ramps {ramps}; matched ends {matched}; "
                    "output {output}; edge objects {edges}"
                ).format(
                    number=result["platform_number"],
                    name=geometry["name"],
                    description=geometry["description"],
                    coverage=config["coverage"],
                    length=geometry["length"],
                    centre=geometry["centre_offset"],
                    width=geometry["minimum_width"],
                    entry=config["entry_end_style"],
                    exit=config["exit_end_style"],
                    ramps=(
                        "yes"
                        if config["body_output"] == PLATFORM_SOLID
                        and config["vertical_end_ramps"]
                        else "no"
                    ),
                    matched="yes" if config["match_end_profiles"] else "no",
                    output=config["body_output"],
                    edges="yes" if config["create_edges"] else "no",
                )
            )
        obj.PlatformSummary = "\n".join(platform_lines)
    obj.PlatformSTLPath = ""

    if formation_geometry is None:
        obj.FormationSummary = "Formation-board output disabled"
    else:
        obj.FormationSummary = (
            "Simple swept board; output {output}; margin {margin:.3f} mm; minimum width "
            "{neck:.3f} mm; thickness {thickness:.3f} mm; plan area {area:.3f} mm2"
        ).format(
            output=formation_config["output_type"],
            margin=formation_config["outer_margin"],
            neck=formation_config["minimum_neck_width"],
            thickness=formation_config["board_thickness"],
            area=formation_geometry.get("area", 0.0),
        )
    if section_plan is None or len(section_plan.get("ranges", [])) <= 1:
        obj.SectionSummary = "Sectioning disabled; complete objects retained"
    else:
        lengths = [finish - start for start, finish in section_plan["ranges"]]
        obj.SectionSummary = (
            "{count} sections in travel order; lengths {lengths}; shared main-alignment boundaries"
        ).format(
            count=len(lengths),
            lengths=", ".join("{:.3f} mm".format(value) for value in lengths),
        )
    obj.RegistrationSummary = registration_config["joint_type"]
    obj.TrackTemplateAssemblySummary = template_assembly_summary

    summary_lines = []
    for alignment in track_alignments:
        summary_lines.append(
            (
                "{name}: {side}, {mode}; spacing {entry:.3f} / {curve:.3f} / "
                "{exit:.3f} mm; radius {radius:.3f} mm; entry/exit easements "
                "{entry_ease:.3f} / {exit_ease:.3f} mm; minimum radius "
                "{minimum:.3f} mm; length {length:.3f} mm"
            ).format(
                name=alignment["name"],
                side=alignment["side"],
                mode=alignment["alignment_mode"],
                entry=alignment["start_spacing"],
                curve=alignment["curve_spacing"],
                exit=alignment["finish_spacing"],
                radius=alignment["radius"],
                entry_ease=alignment["entry_transition"],
                exit_ease=alignment["exit_transition"],
                minimum=alignment["minimum_radius"],
                length=alignment["total_length"],
            )
        )
    obj.TrackSummary = "\n".join(summary_lines) if summary_lines else "No added tracks"

    set_read_only(obj, input_properties + calculated_properties)



# =============================================================================
# Version 10.2A8A3 - complete curve-inheriting REA C10 common-crossing geometry
# =============================================================================


def _turnout_wrap_angle(angle):
    value = float(angle)
    while value <= -math.pi:
        value += 2.0 * math.pi
    while value > math.pi:
        value -= 2.0 * math.pi
    return value


def _turnout_unwrap_angle(angle, reference):
    value = float(angle)
    while value - reference > math.pi:
        value -= 2.0 * math.pi
    while value - reference < -math.pi:
        value += 2.0 * math.pi
    return value


def _turnout_polyline_headings(points):
    if len(points) < 2:
        raise ValueError("A turnout polyline requires at least two points.")
    segment_headings = []
    previous = None
    for point_a, point_b in zip(points[:-1], points[1:]):
        dx = float(point_b.x) - float(point_a.x)
        dy = float(point_b.y) - float(point_a.y)
        if math.hypot(dx, dy) <= GEOMETRY_TOLERANCE:
            angle = previous if previous is not None else 0.0
        else:
            angle = math.atan2(dy, dx)
            if previous is not None:
                angle = _turnout_unwrap_angle(angle, previous)
        segment_headings.append(angle)
        previous = angle
    headings = [segment_headings[0]]
    for before, after in zip(segment_headings[:-1], segment_headings[1:]):
        after = _turnout_unwrap_angle(after, before)
        headings.append(0.5 * (before + after))
    headings.append(segment_headings[-1])
    return headings


def _turnout_clean_points(points):
    clean = []
    for point in points:
        candidate = vector_xy(point.x, point.y)
        if not clean or _xy_distance(clean[-1], candidate) > 1.0e-7:
            clean.append(candidate)
    if len(clean) < 2:
        raise ValueError("The selected host centreline contains too few distinct points.")
    return clean


def turnout_host_alignment(obj):
    """Build ordered station data from the actual generated centreline shape."""
    shape = getattr(obj, "Shape", None)
    if _shape_is_null(shape):
        raise ValueError("The selected host centreline has no usable shape.")

    # Generated centrelines are normally sampled polygon wires already. Prefer
    # an ordered wire discretisation so the turnout also remains reliable if a
    # future compatible set stores an analytic curve rather than every sample
    # as a vertex. Fall back cautiously to the shape and then its vertices.
    points = []
    try:
        wires = list(getattr(shape, "Wires", []) or [])
    except Exception:
        wires = []
    if wires:
        try:
            points = list(wires[0].discretize(Distance=TURNOUT_SAMPLE_SPACING))
        except Exception:
            points = []
    if not points:
        try:
            points = list(shape.discretize(Distance=TURNOUT_SAMPLE_SPACING))
        except Exception:
            points = []
    if not points:
        try:
            points = [vertex.Point for vertex in shape.Vertexes]
        except Exception:
            points = []

    points = _turnout_clean_points(points)
    headings = _turnout_polyline_headings(points)
    return alignment_station_data({
        "points": points,
        "headings": headings,
        "entry_extension": 0.0,
        "exit_extension": 0.0,
    })


def is_turnout_host_centreline(obj):
    if obj is None:
        return False
    if object_string_property(obj, "GeneratedBy", "") != GENERATOR_ID:
        return False
    role = object_string_property(obj, "GeneratedRole", "")
    subtype = object_string_property(obj, "ExportSubtype", "")
    if role not in ("Centreline", "StraightTrackCentreline") and subtype != "TrackCentreline":
        return False
    try:
        return turnout_host_alignment(obj)["total"] > GEOMETRY_TOLERANCE
    except Exception:
        return False


def turnout_host_objects(doc):
    hosts = [obj for obj in list(doc.Objects) if is_turnout_host_centreline(obj)]
    def key(obj):
        set_id = object_string_property(obj, "TemplateSetID", "")
        route_name = object_string_property(obj, "RouteName", "") or "Curve"
        track_number = _integer_object_property(obj, "TrackNumber", 0)
        return (set_id, route_name, track_number, str(getattr(obj, "Label", obj.Name)))
    return sorted(hosts, key=key)


def turnout_host_label(obj):
    set_id = object_string_property(obj, "TemplateSetID", "") or "Unidentified set"
    route_name = object_string_property(obj, "RouteName", "") or "Curve route"
    track_number = _integer_object_property(obj, "TrackNumber", 0)
    track_name = object_string_property(obj, "TrackName", "")
    if not track_name:
        track_name = "Track {}".format(track_number) if track_number > 0 else str(getattr(obj, "Label", obj.Name))
    length = turnout_host_alignment(obj)["total"]
    return "{} | {} | {} | {:.1f} mm".format(set_id, route_name, track_name, length)


def rea_c10_dimensions(track_gauge=TURNOUT_DEFAULT_GAUGE, flangeway=TURNOUT_DEFAULT_FLANGEWAY, model_scale=TURNOUT_DEFAULT_SCALE):
    """Calculate the source-driven straight REA C10 canonical geometry."""
    gauge = float(track_gauge)
    flange = float(flangeway)
    scale_ratio = float(model_scale)
    if not TURNOUT_MIN_GAUGE <= gauge <= TURNOUT_MAX_GAUGE:
        raise ValueError("Track gauge must be between {:.1f} and {:.1f} mm.".format(TURNOUT_MIN_GAUGE, TURNOUT_MAX_GAUGE))
    if not TURNOUT_MIN_FLANGEWAY <= flange <= TURNOUT_MAX_FLANGEWAY:
        raise ValueError("Flangeway must be between {:.2f} and {:.2f} mm.".format(TURNOUT_MIN_FLANGEWAY, TURNOUT_MAX_FLANGEWAY))
    if scale_ratio <= 0.0:
        raise ValueError("Model scale must be greater than zero.")

    inch = 25.4 / scale_ratio
    planing = 110.0 * inch
    heel_lead = 329.0 * inch
    switch_radius = 11520.0 * inch
    switch_front = 65.0 * inch
    switch_rail_length = 342.0 * inch
    stock_rail_length = 432.0 * inch
    k1 = math.atan(1.0 / 40.0)
    k3n = 10.0
    k3 = math.atan(1.0 / k3n)
    planing_x = planing * math.cos(k1)
    argument = ((heel_lead - planing_x) / switch_radius) + math.sin(k1)
    if abs(argument) > 1.0:
        raise ValueError("The REA C switch data cannot be resolved at the selected scale.")
    k2 = math.asin(argument)
    heel_offset = (
        (planing_x / 40.0)
        + switch_radius * math.cos(k1)
        - switch_radius * math.cos(k2)
    )

    # Templot regular-crossing minimum entry straight: 2 flangeways at N times.
    entry_straight = 2.0 * flange * k3n
    offset_at_curve_end = gauge - (entry_straight / k3n)
    denominator = math.cos(k2) - math.cos(k3)
    if abs(denominator) <= 1.0e-12:
        raise ValueError("The C10 turnout-radius calculation is singular.")
    turnout_radius = (offset_at_curve_end - heel_offset) / denominator
    if turnout_radius <= 0.0:
        raise ValueError("The selected gauge and flangeway produce an invalid turnout radius.")
    turnout_curve_length = turnout_radius * (math.sin(k3) - math.sin(k2))
    switch_curve_end_x = heel_lead + turnout_curve_length
    fine_point_x = switch_curve_end_x + entry_straight
    turnout_origin_x = heel_lead - turnout_radius * math.sin(k2)
    turnout_origin_y = heel_offset + turnout_radius * math.cos(k2)

    # Templot5 REA/BH regular-crossing defaults. Values expressed in model mm.
    rail_head_width = 2.75 * inch
    blunt_nose_width = 0.75 * inch
    blunt_nose_x = fine_point_x + (0.5 * blunt_nose_width) / math.sin(0.5 * k3)
    blunt_nose_splice_x = blunt_nose_x - blunt_nose_width * math.sin(0.5 * k3)
    blunt_nose_outer_x = fine_point_x + rail_head_width / math.tan(0.5 * k3)
    a_timber_x = blunt_nose_x + 4.0 * inch

    flare_length = 36.0 * inch
    flare_end_gap = flange + 1.75 * inch
    flare_difference = max(0.0, flare_end_gap - flange)
    if flare_length <= flare_difference:
        raise ValueError("The crossing flare length is too short for the requested flangeway end gap.")
    flare_angle = math.asin(flare_difference / flare_length)
    rail_bend_width = rail_head_width / math.cos(0.5 * flare_angle)

    wing_reach = 48.0 * inch
    wing_end_main_x = a_timber_x + wing_reach
    wing_flare_main_x = wing_end_main_x - flare_length
    wing_flare_main_outer_x = wing_flare_main_x - rail_head_width * math.tan(0.5 * flare_angle)
    wing_end_main_outer_x = wing_end_main_x - rail_head_width * math.sin(flare_angle)

    check_working_length = 108.0 * inch
    check_extension_length = 48.0 * inch
    check_total_length = check_working_length + check_extension_length
    check_main_end_x = a_timber_x + check_extension_length
    check_main_flare_out_x = check_main_end_x - flare_length
    check_main_start_x = check_main_end_x - check_total_length
    check_main_flare_in_x = check_main_start_x + flare_length
    check_main_outer_start_x = check_main_start_x + rail_head_width * math.sin(flare_angle)
    check_main_outer_flare_in_x = check_main_flare_in_x + rail_head_width * math.tan(0.5 * flare_angle)
    check_main_outer_flare_out_x = check_main_flare_out_x - rail_head_width * math.tan(0.5 * flare_angle)
    check_main_outer_end_x = check_main_end_x - rail_head_width * math.sin(flare_angle)

    # Virtual knuckles and the normal Templot knuckle radius.
    wing_turnout_x = fine_point_x - flange * k3n
    wing_turnout_outer_x = wing_turnout_x + rail_head_width * math.tan(0.5 * k3)
    wing_main_x = fine_point_x - flange / math.sin(k3)
    wing_main_outer_x = wing_main_x - rail_head_width * math.tan(0.5 * k3)
    scale_mm_per_foot = 304.8 / scale_ratio
    knuckle_radius = k3n * scale_mm_per_foot
    knuckle_tangent_x = abs(knuckle_radius * math.tan(0.5 * k3))
    knuckle_maximum_x = abs(fine_point_x - wing_turnout_x - inch)
    if knuckle_tangent_x > knuckle_maximum_x:
        knuckle_tangent_x = knuckle_maximum_x
        knuckle_radius = knuckle_tangent_x / math.tan(0.5 * k3)
    knuckle_crossing_x = knuckle_tangent_x * math.cos(k3)
    wing_bend_offset = knuckle_tangent_x * math.sin(k3)
    wing_turnout_plus_x = wing_turnout_x + knuckle_tangent_x
    wing_turnout_minus_x = wing_turnout_x - knuckle_crossing_x
    wing_turnout_outer_plus_x = wing_turnout_plus_x
    wing_turnout_outer_minus_x = wing_turnout_minus_x + rail_head_width * math.sin(k3)
    wing_main_plus_x = wing_main_x + knuckle_crossing_x
    wing_main_minus_x = wing_main_x - knuckle_tangent_x
    wing_main_outer_plus_x = wing_main_plus_x - rail_head_width * math.sin(k3)
    wing_main_outer_minus_x = wing_main_minus_x

    # Turnout-side wing rail, following the opposite running rail before its flare.
    wing_fine_point_x = fine_point_x - flange * math.sin(k3)
    wing_to_flare_length = (a_timber_x - fine_point_x) + wing_reach - flare_length
    wing_flare_turnout_base_x = fine_point_x + wing_to_flare_length * math.cos(k3)
    wing_flare_turnout_x = wing_fine_point_x + wing_to_flare_length * math.cos(k3)
    wing_flare_turnout_outer_x = wing_flare_turnout_x - rail_bend_width * math.sin(k3 + 0.5 * flare_angle)
    wing_end_turnout_x = wing_flare_turnout_x + flare_length * math.cos(k3 + flare_angle)
    wing_end_turnout_outer_x = wing_end_turnout_x - rail_head_width * math.sin(k3 + flare_angle)

    # Turnout-side check rail centred on the A timber, using the regular-crossing branch.
    check_turnout_fine_point_x = fine_point_x - (gauge - flange) * math.sin(k3)
    check_turnout_mid_offset = (a_timber_x - check_turnout_fine_point_x) / math.cos(k3)
    check_turnout_length_after_fp = check_turnout_mid_offset + check_extension_length - flare_length
    check_turnout_length_before_fp = (
        check_total_length - check_turnout_length_after_fp - flare_length - flare_length
    )
    angled_entry_length = entry_straight / max(math.cos(k3), 1.0e-12)
    curved_stock_radius = turnout_radius - gauge
    check_turnout_radius = curved_stock_radius + flange
    check_turnout_flare_radius = curved_stock_radius + flare_end_gap
    if check_turnout_length_before_fp < angled_entry_length:
        check_turnout_working_mode = "straight crossing leg"
        check_turnout_flare_in_x = (
            check_turnout_fine_point_x - check_turnout_length_before_fp * math.cos(k3)
        )
        check_turnout_start_x = (
            check_turnout_flare_in_x
            - (flare_length / math.cos(flare_angle)) * math.cos(k3 + flare_angle)
        )
    else:
        if check_turnout_radius <= 0.0 or check_turnout_flare_radius <= 0.0:
            raise ValueError("The selected gauge and flangeway produce an invalid turnout-side check-rail radius.")
        check_curve_angle = (check_turnout_length_before_fp - angled_entry_length) / check_turnout_radius
        check_flare_curve_angle = flare_length / check_turnout_radius
        if check_curve_angle < k3:
            check_turnout_flare_in_x = (
                turnout_origin_x + check_turnout_radius * math.sin(k3 - check_curve_angle)
            )
        else:
            check_turnout_flare_in_x = (
                turnout_origin_x
                - (check_turnout_length_before_fp - angled_entry_length - check_turnout_radius * k3)
            )
        if (check_curve_angle + check_flare_curve_angle) < k3:
            check_turnout_start_x = (
                turnout_origin_x
                + check_turnout_flare_radius * math.sin(k3 - check_curve_angle - check_flare_curve_angle)
            )
        else:
            check_turnout_start_x = check_turnout_flare_in_x - flare_length
        check_turnout_working_mode = "turnout curve and crossing leg"
    check_turnout_flare_out_x = (
        check_turnout_fine_point_x + check_turnout_length_after_fp * math.cos(k3)
    )
    check_turnout_end_x = (
        check_turnout_flare_out_x
        + (flare_length / math.cos(flare_angle)) * math.cos(k3 - flare_angle)
    )

    # REA/BH vee-joint position used by the established module extent.
    vee_joint_length = (4.0 + 12.5 + (6.0 - 1.0) * 30.0) * inch
    vee_joint_x = blunt_nose_x + vee_joint_length
    exit_extension = 60.0 * inch
    module_start_x = -switch_front
    module_end_x = vee_joint_x + exit_extension

    switch_origin_x = heel_lead - switch_radius * math.sin(k2)
    switch_origin_y = heel_offset + switch_radius * math.cos(k2)
    turnout_origin_x = heel_lead - turnout_radius * math.sin(k2)
    turnout_origin_y = heel_offset + turnout_radius * math.cos(k2)

    return {
        "size": TURNOUT_SIZE_C10,
        "gauge": gauge,
        "flangeway": flange,
        "model_scale": scale_ratio,
        "inch": inch,
        "planing": planing,
        "planing_x": planing_x,
        "heel_lead": heel_lead,
        "heel_offset": heel_offset,
        "switch_radius": switch_radius,
        "switch_front": switch_front,
        "switch_rail_length": switch_rail_length,
        "stock_rail_length": stock_rail_length,
        "k1": k1,
        "k2": k2,
        "k3": k3,
        "crossing_n": k3n,
        "entry_straight": entry_straight,
        "curve_end_offset": offset_at_curve_end,
        "turnout_radius": turnout_radius,
        "turnout_curve_length": turnout_curve_length,
        "switch_curve_end_x": switch_curve_end_x,
        "fine_point_x": fine_point_x,
        "rail_head_width": rail_head_width,
        "blunt_nose_width": blunt_nose_width,
        "blunt_nose_x": blunt_nose_x,
        "blunt_nose_splice_x": blunt_nose_splice_x,
        "blunt_nose_outer_x": blunt_nose_outer_x,
        "a_timber_x": a_timber_x,
        "flare_length": flare_length,
        "flare_end_gap": flare_end_gap,
        "flare_angle": flare_angle,
        "rail_bend_width": rail_bend_width,
        "wing_reach": wing_reach,
        "wing_end_main_x": wing_end_main_x,
        "wing_flare_main_x": wing_flare_main_x,
        "wing_flare_main_outer_x": wing_flare_main_outer_x,
        "wing_end_main_outer_x": wing_end_main_outer_x,
        "check_working_length": check_working_length,
        "check_extension_length": check_extension_length,
        "check_total_length": check_total_length,
        "check_main_end_x": check_main_end_x,
        "check_main_flare_out_x": check_main_flare_out_x,
        "check_main_start_x": check_main_start_x,
        "check_main_flare_in_x": check_main_flare_in_x,
        "check_main_outer_start_x": check_main_outer_start_x,
        "check_main_outer_flare_in_x": check_main_outer_flare_in_x,
        "check_main_outer_flare_out_x": check_main_outer_flare_out_x,
        "check_main_outer_end_x": check_main_outer_end_x,
        "wing_turnout_x": wing_turnout_x,
        "wing_turnout_outer_x": wing_turnout_outer_x,
        "wing_main_x": wing_main_x,
        "wing_main_outer_x": wing_main_outer_x,
        "knuckle_radius": knuckle_radius,
        "wing_bend_offset": wing_bend_offset,
        "wing_turnout_plus_x": wing_turnout_plus_x,
        "wing_turnout_minus_x": wing_turnout_minus_x,
        "wing_turnout_outer_plus_x": wing_turnout_outer_plus_x,
        "wing_turnout_outer_minus_x": wing_turnout_outer_minus_x,
        "wing_main_plus_x": wing_main_plus_x,
        "wing_main_minus_x": wing_main_minus_x,
        "wing_main_outer_plus_x": wing_main_outer_plus_x,
        "wing_main_outer_minus_x": wing_main_outer_minus_x,
        "wing_fine_point_x": wing_fine_point_x,
        "wing_to_flare_length": wing_to_flare_length,
        "wing_flare_turnout_base_x": wing_flare_turnout_base_x,
        "wing_flare_turnout_x": wing_flare_turnout_x,
        "wing_flare_turnout_outer_x": wing_flare_turnout_outer_x,
        "wing_end_turnout_x": wing_end_turnout_x,
        "wing_end_turnout_outer_x": wing_end_turnout_outer_x,
        "check_turnout_fine_point_x": check_turnout_fine_point_x,
        "check_turnout_length_after_fp": check_turnout_length_after_fp,
        "check_turnout_length_before_fp": check_turnout_length_before_fp,
        "check_turnout_working_mode": check_turnout_working_mode,
        "curved_stock_radius": curved_stock_radius,
        "check_turnout_radius": check_turnout_radius,
        "check_turnout_flare_radius": check_turnout_flare_radius,
        "check_turnout_flare_in_x": check_turnout_flare_in_x,
        "check_turnout_start_x": check_turnout_start_x,
        "check_turnout_flare_out_x": check_turnout_flare_out_x,
        "check_turnout_end_x": check_turnout_end_x,
        "vee_joint_x": vee_joint_x,
        "module_start_x": module_start_x,
        "module_end_x": module_end_x,
        "switch_origin_x": switch_origin_x,
        "switch_origin_y": switch_origin_y,
        "turnout_origin_x": turnout_origin_x,
        "turnout_origin_y": turnout_origin_y,
    }

def _rea_c10_inner_gauge_face(dimensions, x_value):
    x = float(x_value)
    if x <= 0.0:
        return x, 0.0, 0.0
    if x <= dimensions["planing_x"]:
        return x, x * math.tan(dimensions["k1"]), dimensions["k1"]
    if x <= dimensions["heel_lead"]:
        radius = dimensions["switch_radius"]
        dx = x - dimensions["switch_origin_x"]
        root = max(0.0, radius * radius - dx * dx)
        y = dimensions["switch_origin_y"] - math.sqrt(root)
        theta = math.asin(max(-1.0, min(1.0, dx / radius)))
        return x, y, theta
    if x <= dimensions["switch_curve_end_x"]:
        radius = dimensions["turnout_radius"]
        dx = x - dimensions["turnout_origin_x"]
        root = max(0.0, radius * radius - dx * dx)
        y = dimensions["turnout_origin_y"] - math.sqrt(root)
        theta = math.asin(max(-1.0, min(1.0, dx / radius)))
        return x, y, theta
    start_y = dimensions["curve_end_offset"]
    y = start_y + (x - dimensions["switch_curve_end_x"]) * math.tan(dimensions["k3"])
    return x, y, dimensions["k3"]


def _rea_c10_local_point(dimensions, x_value, lateral_kind):
    x, inner_y, theta = _rea_c10_inner_gauge_face(dimensions, x_value)
    gauge = dimensions["gauge"]
    if lateral_kind == "main_centre":
        return x, 0.0
    if lateral_kind == "main_lower":
        return x, -0.5 * gauge
    if lateral_kind == "main_upper":
        return x, 0.5 * gauge
    if lateral_kind == "turnout_inner":
        return x, inner_y - 0.5 * gauge
    if lateral_kind == "turnout_outer":
        return (
            x - gauge * math.sin(theta),
            inner_y + gauge * math.cos(theta) - 0.5 * gauge,
        )
    if lateral_kind == "turnout_centre":
        return (
            x - 0.5 * gauge * math.sin(theta),
            inner_y + 0.5 * gauge * math.cos(theta) - 0.5 * gauge,
        )
    raise ValueError("Unknown C10 local geometry kind: {}".format(lateral_kind))



def _turnout_range_values(start_value, finish_value, spacing=TURNOUT_RAIL_SAMPLE_SPACING, extra_values=None):
    """Return a deterministic inclusive coordinate range with important values retained."""
    start = float(start_value)
    finish = float(finish_value)
    if not math.isfinite(start) or not math.isfinite(finish):
        raise ValueError("Turnout rail coordinate ranges must be finite.")
    if finish < start:
        start, finish = finish, start
    interval = max(0.10, float(spacing))
    count = max(1, int(math.ceil((finish - start) / interval)))
    values = [start + (finish - start) * index / float(count) for index in range(count + 1)]
    for value in extra_values or ():
        numeric = float(value)
        if start - 1.0e-9 <= numeric <= finish + 1.0e-9:
            values.append(numeric)
    return sorted(set(round(value, 9) for value in values))


def _turnout_straight_segment(point_a, point_b, spacing=TURNOUT_RAIL_SAMPLE_SPACING):
    """Sample a straight local rail segment, retaining both exact endpoints."""
    ax, ay = float(point_a[0]), float(point_a[1])
    bx, by = float(point_b[0]), float(point_b[1])
    length = math.hypot(bx - ax, by - ay)
    count = max(1, int(math.ceil(length / max(0.10, float(spacing)))))
    return [
        (ax + (bx - ax) * index / float(count), ay + (by - ay) * index / float(count))
        for index in range(count + 1)
    ]


def _turnout_join_local_segments(*segments):
    """Join local segments without duplicated adjacent points."""
    joined = []
    for segment in segments:
        for point in segment or ():
            current = (float(point[0]), float(point[1]))
            if joined and math.hypot(current[0] - joined[-1][0], current[1] - joined[-1][1]) <= 1.0e-8:
                continue
            joined.append(current)
    return joined


def _rea_c10_offset_from_inner(dimensions, x_value, left_normal_offset):
    """Offset from the turnout-road inner gauge face by its local left normal."""
    x, inner_y, theta = _rea_c10_inner_gauge_face(dimensions, x_value)
    offset = float(left_normal_offset)
    return (
        x - offset * math.sin(theta),
        inner_y - 0.5 * dimensions["gauge"] + offset * math.cos(theta),
    )


def _rea_c10_main_knuckle_polyline(dimensions, outer_face=False):
    width = dimensions["rail_head_width"] if outer_face else 0.0
    radius = dimensions["knuckle_radius"] - width
    if radius <= 0.0:
        raise ValueError("The rail-head width is too large for the C10 knuckle radius.")
    if outer_face:
        start = dimensions["wing_main_outer_minus_x"]
        finish = dimensions["wing_main_outer_plus_x"]
    else:
        start = dimensions["wing_main_minus_x"]
        finish = dimensions["wing_main_plus_x"]
    base_y = 0.5 * dimensions["gauge"] + width
    points = []
    for x in _turnout_range_values(start, finish, 0.25):
        root = max(0.0, radius * radius - (x - start) * (x - start))
        points.append((x, base_y + radius - math.sqrt(root)))
    return points


def _rea_c10_turnout_knuckle_polyline(dimensions, outer_face=False):
    width = dimensions["rail_head_width"] if outer_face else 0.0
    radius = dimensions["knuckle_radius"] - width
    if radius <= 0.0:
        raise ValueError("The rail-head width is too large for the C10 knuckle radius.")
    if outer_face:
        start = dimensions["wing_turnout_outer_minus_x"]
        finish = dimensions["wing_turnout_outer_plus_x"]
    else:
        start = dimensions["wing_turnout_minus_x"]
        finish = dimensions["wing_turnout_plus_x"]
    base_y = 0.5 * dimensions["gauge"] - dimensions["flangeway"] - width
    points = []
    for x in _turnout_range_values(start, finish, 0.25):
        root = max(0.0, radius * radius - (finish - x) * (finish - x))
        points.append((x, base_y - radius + math.sqrt(root)))
    return points


def _rea_c10_straight_crossing_offset_point(dimensions, actual_x, offset):
    """Point on a normal offset to the straight 1:10 turnout-road crossing leg."""
    theta = dimensions["k3"]
    base_x = float(actual_x) + float(offset) * math.sin(theta)
    return _rea_c10_offset_from_inner(dimensions, base_x, offset)


def _rea_c10_offset_point_at_actual_x(dimensions, actual_x, offset):
    """Invert a normal-offset rail path to an exact local x coordinate."""
    target = float(actual_x)
    low = float(dimensions["module_start_x"])
    high = float(dimensions["module_end_x"])
    low_x = _rea_c10_offset_from_inner(dimensions, low, offset)[0]
    high_x = _rea_c10_offset_from_inner(dimensions, high, offset)[0]
    if target < low_x - 1.0e-7 or target > high_x + 1.0e-7:
        raise ValueError("A crossing rail offset falls outside the complete C10 module.")
    for _index in range(70):
        middle = 0.5 * (low + high)
        point = _rea_c10_offset_from_inner(dimensions, middle, offset)
        if point[0] < target:
            low = middle
        else:
            high = middle
    return _rea_c10_offset_from_inner(dimensions, 0.5 * (low + high), offset)


def rea_c10_complete_rail_polylines(dimensions):
    """Return named local polylines for complete REA C10 crossing construction.

    The geometry follows the regular-crossing equations used by Templot5 for the
    REA/BH default rail head, normal knuckle, wing reaches, check lengths and
    bent 3-foot wing/check flares. Each physical rail head is represented by a
    gauge face and an outer face.
    """
    gauge = dimensions["gauge"]
    flange = dimensions["flangeway"]
    width = dimensions["rail_head_width"]
    flare_gap = dimensions["flare_end_gap"]
    flare_angle = dimensions["flare_angle"]
    k3 = dimensions["k3"]
    start = dimensions["module_start_x"]
    finish = dimensions["module_end_x"]
    key_x = (
        0.0,
        dimensions["planing_x"],
        dimensions["heel_lead"],
        dimensions["switch_curve_end_x"],
        dimensions["fine_point_x"],
        dimensions["blunt_nose_x"],
        dimensions["vee_joint_x"],
    )
    full_x = _turnout_range_values(start, finish, TURNOUT_RAIL_SAMPLE_SPACING, key_x)
    rails = []

    # The two uninterrupted stock rails.
    rails.append(("main-side stock rail gauge face", [(x, -0.5 * gauge) for x in full_x]))
    rails.append(("main-side stock rail outer face", [(x, -0.5 * gauge - width) for x in full_x]))
    rails.append(("turnout-side stock rail gauge face", [_rea_c10_offset_from_inner(dimensions, x, gauge) for x in full_x]))
    rails.append(("turnout-side stock rail outer face", [_rea_c10_offset_from_inner(dimensions, x, gauge + width) for x in full_x]))

    # Straight switch/closure rail into the turnout-side wing rail.
    straight_switch_x = _turnout_range_values(
        0.0,
        dimensions["wing_main_minus_x"],
        TURNOUT_RAIL_SAMPLE_SPACING,
        key_x,
    )
    rails.append(("straight switch and closure rail gauge face", [(x, 0.5 * gauge) for x in straight_switch_x]))
    rails.append(("straight switch and closure rail outer face", [(x, 0.5 * gauge + width) for x in straight_switch_x]))
    main_knuckle_gauge = _rea_c10_main_knuckle_polyline(dimensions, False)
    main_knuckle_outer = _rea_c10_main_knuckle_polyline(dimensions, True)
    rails.append(("turnout-side wing knuckle gauge face", main_knuckle_gauge))
    rails.append(("turnout-side wing knuckle outer face", main_knuckle_outer))

    wing_flare_base = dimensions["wing_flare_turnout_base_x"]
    turnout_wing_flare_start_gauge = _rea_c10_offset_from_inner(dimensions, wing_flare_base, flange)
    turnout_wing_parallel_gauge = _turnout_straight_segment(
        main_knuckle_gauge[-1], turnout_wing_flare_start_gauge, 0.50
    )
    wing_flare_start_outer = (
        turnout_wing_flare_start_gauge[0]
        - width * math.sin(k3 + 0.5 * flare_angle),
        turnout_wing_flare_start_gauge[1]
        + width * math.cos(k3 + 0.5 * flare_angle),
    )
    turnout_wing_parallel_outer = _turnout_straight_segment(
        main_knuckle_outer[-1], wing_flare_start_outer, 0.50
    )
    wing_flare_end_gauge = (
        turnout_wing_flare_start_gauge[0] + dimensions["flare_length"] * math.cos(k3 + flare_angle),
        turnout_wing_flare_start_gauge[1] + dimensions["flare_length"] * math.sin(k3 + flare_angle),
    )
    wing_flare_end_outer = (
        wing_flare_end_gauge[0] - width * math.sin(k3 + flare_angle),
        wing_flare_end_gauge[1] + width * math.cos(k3 + flare_angle),
    )
    rails.append(("turnout-side wing rail gauge face", turnout_wing_parallel_gauge))
    rails.append(("turnout-side wing rail outer face", turnout_wing_parallel_outer))
    rails.append(("turnout-side wing flare gauge face", _turnout_straight_segment(turnout_wing_flare_start_gauge, wing_flare_end_gauge, 0.50)))
    rails.append(("turnout-side wing flare outer face", _turnout_straight_segment(wing_flare_start_outer, wing_flare_end_outer, 0.50)))

    # Curved switch/closure rail into the main-side wing rail.
    curved_switch_x = _turnout_range_values(
        0.0,
        dimensions["wing_turnout_minus_x"],
        TURNOUT_RAIL_SAMPLE_SPACING,
        key_x,
    )
    rails.append(("curved switch and closure rail gauge face", [_rea_c10_offset_from_inner(dimensions, x, 0.0) for x in curved_switch_x]))
    rails.append(("curved switch and closure rail outer face", [_rea_c10_offset_from_inner(dimensions, x, -width) for x in curved_switch_x]))
    turnout_knuckle_gauge = _rea_c10_turnout_knuckle_polyline(dimensions, False)
    turnout_knuckle_outer = _rea_c10_turnout_knuckle_polyline(dimensions, True)
    rails.append(("main-side wing knuckle gauge face", turnout_knuckle_gauge))
    rails.append(("main-side wing knuckle outer face", turnout_knuckle_outer))

    main_wing_flare_start_gauge = (
        dimensions["wing_flare_main_x"], 0.5 * gauge - flange
    )
    main_wing_flare_start_outer = (
        dimensions["wing_flare_main_outer_x"], 0.5 * gauge - flange - width
    )
    rails.append((
        "main-side wing rail gauge face",
        _turnout_straight_segment(turnout_knuckle_gauge[-1], main_wing_flare_start_gauge, 0.50),
    ))
    rails.append((
        "main-side wing rail outer face",
        _turnout_straight_segment(turnout_knuckle_outer[-1], main_wing_flare_start_outer, 0.50),
    ))
    main_wing_flare_end_gauge = (
        dimensions["wing_end_main_x"], 0.5 * gauge - flare_gap
    )
    main_wing_flare_end_outer = (
        dimensions["wing_end_main_outer_x"],
        main_wing_flare_end_gauge[1] - width * math.cos(flare_angle),
    )
    rails.append(("main-side wing flare gauge face", _turnout_straight_segment(main_wing_flare_start_gauge, main_wing_flare_end_gauge, 0.50)))
    rails.append(("main-side wing flare outer face", _turnout_straight_segment(main_wing_flare_start_outer, main_wing_flare_end_outer, 0.50)))

    # Point and splice rails form the crossing vee from the blunt nose onwards.
    point_gauge_x = _turnout_range_values(dimensions["blunt_nose_x"], finish, 0.75, (dimensions["vee_joint_x"],))
    point_outer_x = _turnout_range_values(dimensions["blunt_nose_outer_x"], finish, 0.75, (dimensions["vee_joint_x"],))
    splice_gauge_x = _turnout_range_values(dimensions["blunt_nose_splice_x"], finish, 0.75, (dimensions["vee_joint_x"],))
    splice_outer_x = _turnout_range_values(dimensions["blunt_nose_outer_x"], finish, 0.75, (dimensions["vee_joint_x"],))
    rails.append(("vee point rail gauge face", [(x, 0.5 * gauge) for x in point_gauge_x]))
    rails.append(("vee point rail outer face", [(x, 0.5 * gauge + width) for x in point_outer_x]))
    rails.append((
        "vee splice rail gauge face",
        [
            (
                x,
                0.5 * gauge
                + (dimensions["blunt_nose_x"] - dimensions["fine_point_x"] + x - dimensions["blunt_nose_splice_x"])
                / dimensions["crossing_n"],
            )
            for x in splice_gauge_x
        ],
    ))
    rails.append((
        "vee splice rail outer face",
        [
            (
                x,
                0.5 * gauge + width + (x - dimensions["blunt_nose_outer_x"]) / dimensions["crossing_n"],
            )
            for x in splice_outer_x
        ],
    ))

    # Main-side check rail opposite the vee.
    main_check_start_gauge = (dimensions["check_main_start_x"], -0.5 * gauge + flare_gap)
    main_check_flare_in_gauge = (dimensions["check_main_flare_in_x"], -0.5 * gauge + flange)
    main_check_flare_out_gauge = (dimensions["check_main_flare_out_x"], -0.5 * gauge + flange)
    main_check_end_gauge = (dimensions["check_main_end_x"], -0.5 * gauge + flare_gap)
    main_check_gauge = _turnout_join_local_segments(
        _turnout_straight_segment(main_check_start_gauge, main_check_flare_in_gauge, 0.50),
        _turnout_straight_segment(main_check_flare_in_gauge, main_check_flare_out_gauge, 0.50),
        _turnout_straight_segment(main_check_flare_out_gauge, main_check_end_gauge, 0.50),
    )
    main_check_start_outer = (
        dimensions["check_main_outer_start_x"],
        main_check_start_gauge[1] + width * math.cos(flare_angle),
    )
    main_check_flare_in_outer = (
        dimensions["check_main_outer_flare_in_x"], -0.5 * gauge + flange + width
    )
    main_check_flare_out_outer = (
        dimensions["check_main_outer_flare_out_x"], -0.5 * gauge + flange + width
    )
    main_check_end_outer = (
        dimensions["check_main_outer_end_x"],
        main_check_end_gauge[1] + width * math.cos(flare_angle),
    )
    main_check_outer = _turnout_join_local_segments(
        _turnout_straight_segment(main_check_start_outer, main_check_flare_in_outer, 0.50),
        _turnout_straight_segment(main_check_flare_in_outer, main_check_flare_out_outer, 0.50),
        _turnout_straight_segment(main_check_flare_out_outer, main_check_end_outer, 0.50),
    )
    rails.append(("main-side check rail gauge face", main_check_gauge))
    rails.append(("main-side check rail outer face", main_check_outer))

    # Turnout-side check rail opposite the vee. Templot allows the working
    # end to extend from the straight crossing leg back onto the turnout curve;
    # exact-x inversion keeps both cases on the correctly offset running rail.
    def turnout_check_polyline(outer_face=False):
        rail_width = width if outer_face else 0.0
        points = []
        segments = (
            (
                dimensions["check_turnout_start_x"],
                dimensions["check_turnout_flare_in_x"],
                flare_gap,
                flange,
            ),
            (
                dimensions["check_turnout_flare_in_x"],
                dimensions["check_turnout_flare_out_x"],
                flange,
                flange,
            ),
            (
                dimensions["check_turnout_flare_out_x"],
                dimensions["check_turnout_end_x"],
                flange,
                flare_gap,
            ),
        )
        for segment_index, (segment_start, segment_finish, gap_start, gap_finish) in enumerate(segments):
            x_values = _turnout_range_values(segment_start, segment_finish, 0.40)
            for index, actual_x in enumerate(x_values):
                if segment_index > 0 and index == 0:
                    continue
                fraction = 0.0 if abs(segment_finish - segment_start) <= 1.0e-12 else (
                    (actual_x - segment_start) / (segment_finish - segment_start)
                )
                gap = gap_start + (gap_finish - gap_start) * fraction
                offset = gauge - gap - rail_width
                points.append(_rea_c10_offset_point_at_actual_x(dimensions, actual_x, offset))
        return points

    rails.append(("turnout-side check rail gauge face", turnout_check_polyline(False)))
    rails.append(("turnout-side check rail outer face", turnout_check_polyline(True)))

    # Construction centrelines remain available as separate engraving references.
    rails.append(("main-road centreline", [(x, 0.0) for x in full_x]))
    branch_centre_x = _turnout_range_values(dimensions["heel_lead"], finish, TURNOUT_RAIL_SAMPLE_SPACING, key_x)
    rails.append(("turnout-road centreline", [_rea_c10_offset_from_inner(dimensions, x, 0.5 * gauge) for x in branch_centre_x]))

    for name, points in rails:
        if len(points) < 2:
            raise ValueError("{} contains too few local points.".format(name.capitalize()))
        for index, point in enumerate(points):
            if not math.isfinite(float(point[0])) or not math.isfinite(float(point[1])):
                raise ValueError("{} contains a non-finite point at sample {}.".format(name.capitalize(), index + 1))
        for point_a, point_b in zip(points[:-1], points[1:]):
            if math.hypot(point_b[0] - point_a[0], point_b[1] - point_a[1]) <= 1.0e-8:
                raise ValueError("{} contains a collapsed local segment.".format(name.capitalize()))
    return rails

def _turnout_sample_x_values(dimensions, spacing=TURNOUT_SAMPLE_SPACING):
    start = dimensions["module_start_x"]
    finish = dimensions["module_end_x"]
    count = max(2, int(math.ceil((finish - start) / max(0.25, float(spacing)))))
    values = [start + (finish - start) * index / float(count) for index in range(count + 1)]
    values.extend([
        0.0,
        dimensions["planing_x"],
        dimensions["heel_lead"],
        dimensions["switch_curve_end_x"],
        dimensions["fine_point_x"],
        dimensions["blunt_nose_x"],
        dimensions["vee_joint_x"],
    ])
    return sorted(set(round(value, 9) for value in values))


def _turnout_orientation_sign(orientation):
    return -1.0 if str(orientation) == TURNOUT_ORIENTATION_TRAILING else 1.0


def _turnout_hand_sign(handing):
    return -1.0 if str(handing) == TURNOUT_HAND_RIGHT else 1.0


def map_turnout_local_point(host_data, toe_chainage, orientation, handing, local_x, local_y):
    direction = _turnout_orientation_sign(orientation)
    hand = _turnout_hand_sign(handing)
    station = float(toe_chainage) + direction * float(local_x)
    if station < -1.0e-7 or station > host_data["total"] + 1.0e-7:
        raise ValueError(
            "The turnout requires host chainage {:.3f} mm, outside the available 0.000 to {:.3f} mm range.".format(
                station, host_data["total"]
            )
        )
    point, host_heading = interpolate_alignment_station(host_data, station)
    travel_heading = host_heading if direction > 0.0 else host_heading + math.pi
    normal_x, normal_y = left_normal(travel_heading)
    signed_y = hand * float(local_y)
    return vector_xy(point.x + signed_y * normal_x, point.y + signed_y * normal_y)


def turnout_valid_toe_range(host_length, dimensions, orientation):
    total = max(0.0, float(host_length))
    start_x = float(dimensions["module_start_x"])
    finish_x = float(dimensions["module_end_x"])
    if _turnout_orientation_sign(orientation) > 0.0:
        minimum = max(0.0, -start_x)
        maximum = min(total, total - finish_x)
    else:
        minimum = max(0.0, finish_x)
        maximum = min(total, total + start_x)
    return minimum, maximum


def turnout_host_station_interval(toe_chainage, dimensions, orientation):
    """Return the occupied host-chainage interval for a complete turnout module."""
    direction = _turnout_orientation_sign(orientation)
    station_a = float(toe_chainage) + direction * float(dimensions["module_start_x"])
    station_b = float(toe_chainage) + direction * float(dimensions["module_end_x"])
    return min(station_a, station_b), max(station_a, station_b)


def nearest_alignment_station(data, point):
    """Project an XY point to the nearest sampled host segment and return chainage."""
    px = float(point.x)
    py = float(point.y)
    best_station = 0.0
    best_distance = None
    for index, (point_a, point_b) in enumerate(zip(data["points"][:-1], data["points"][1:])):
        dx = float(point_b.x) - float(point_a.x)
        dy = float(point_b.y) - float(point_a.y)
        length_squared = dx * dx + dy * dy
        if length_squared <= GEOMETRY_TOLERANCE * GEOMETRY_TOLERANCE:
            fraction = 0.0
        else:
            fraction = ((px - float(point_a.x)) * dx + (py - float(point_a.y)) * dy) / length_squared
            fraction = min(1.0, max(0.0, fraction))
        projected_x = float(point_a.x) + fraction * dx
        projected_y = float(point_a.y) + fraction * dy
        distance = math.hypot(px - projected_x, py - projected_y)
        if best_distance is None or distance < best_distance:
            best_distance = distance
            segment_length = data["stations"][index + 1] - data["stations"][index]
            best_station = data["stations"][index] + fraction * segment_length
    return min(max(0.0, best_station), float(data["total"]))


def _turnout_polyline_minimum_radius(points, sample_window=5):
    """Return a stable sampled XY minimum radius across several polyline segments."""
    minimum = None
    window = max(1, int(sample_window))
    if len(points) < (2 * window + 1):
        window = 1
    for index in range(window, len(points) - window):
        point_a = points[index - window]
        point_b = points[index]
        point_c = points[index + window]
        ab = _xy_distance(point_a, point_b)
        bc = _xy_distance(point_b, point_c)
        ac = _xy_distance(point_a, point_c)
        # Spanning several source segments avoids falsely reporting half-radius
        # values at the tiny corners of a sampled circular/Euler polyline.
        if min(ab, bc) < 3.0 or ac <= 1.0e-7:
            continue
        twice_area = abs(
            (float(point_b.x) - float(point_a.x)) * (float(point_c.y) - float(point_a.y))
            - (float(point_b.y) - float(point_a.y)) * (float(point_c.x) - float(point_a.x))
        )
        if twice_area <= 1.0e-8 * max(1.0, ab * bc):
            continue
        radius = (ab * bc * ac) / (2.0 * twice_area)
        if math.isfinite(radius) and radius > GEOMETRY_TOLERANCE:
            minimum = radius if minimum is None else min(minimum, radius)
    return minimum


def _turnout_validate_mapped_polyline(points, description):
    if len(points) < 2:
        raise ValueError("{} contains too few points.".format(description))
    for index, point in enumerate(points):
        if not math.isfinite(float(point.x)) or not math.isfinite(float(point.y)):
            raise ValueError("{} contains a non-finite point at sample {}.".format(description, index + 1))
    for index, (point_a, point_b) in enumerate(zip(points[:-1], points[1:])):
        if _xy_distance(point_a, point_b) <= 1.0e-5:
            raise ValueError(
                "{} collapses at samples {} and {}; choose another placement or host geometry.".format(
                    description, index + 1, index + 2
                )
            )


def turnout_mapping_metrics(host_data, toe_chainage, orientation, handing, dimensions):
    """Validate station-normal mapping and report sampled host/turnout radii."""
    x_values = _turnout_sample_x_values(dimensions)
    main_local = _turnout_local_polyline(dimensions, "main_centre", x_values)
    # The branch template strip starts at the heel. The full main strip already
    # contains the switch area, avoiding a false centreline kink at the blade toe.
    branch_x_values = [x for x in x_values if x >= dimensions["heel_lead"] - 1.0e-9]
    branch_local = _turnout_local_polyline(dimensions, "turnout_centre", branch_x_values)
    main_points = _turnout_map_polyline(host_data, toe_chainage, orientation, handing, main_local)
    turnout_points = _turnout_map_polyline(host_data, toe_chainage, orientation, handing, branch_local)
    _turnout_validate_mapped_polyline(main_points, "Mapped main-road centreline")
    _turnout_validate_mapped_polyline(turnout_points, "Mapped turnout-road centreline")
    return {
        "x_values": x_values,
        "branch_x_values": branch_x_values,
        "main_local": main_local,
        "turnout_local": branch_local,
        "main_points": main_points,
        "turnout_points": turnout_points,
        "host_minimum_radius": _turnout_polyline_minimum_radius(main_points),
        "turnout_minimum_radius": _turnout_polyline_minimum_radius(turnout_points),
    }


def _turnout_find_overlap(doc, host_obj, toe_chainage, dimensions, orientation, ignored_turnout_id=None):
    """Return the first conflicting turnout, optionally excluding one being edited."""
    new_start, new_finish = turnout_host_station_interval(toe_chainage, dimensions, orientation)
    host_name = str(getattr(host_obj, "Name", ""))
    ignored = str(ignored_turnout_id or "").strip()
    for config in existing_turnout_configs(doc):
        if ignored and str(config.get("turnout_id") or "") == ignored:
            continue
        if str(config.get("host_object") or "") != host_name:
            continue
        try:
            old_dimensions = rea_c10_dimensions(
                config.get("track_gauge", TURNOUT_DEFAULT_GAUGE),
                config.get("flangeway", TURNOUT_DEFAULT_FLANGEWAY),
            )
            old_start, old_finish = turnout_host_station_interval(
                config.get("toe_chainage", 0.0),
                old_dimensions,
                config.get("orientation", TURNOUT_ORIENTATION_FACING),
            )
        except Exception:
            continue
        overlap = min(new_finish, old_finish) - max(new_start, old_start)
        if overlap > TURNOUT_OVERLAP_TOLERANCE:
            return config, overlap
    return None, 0.0


def _turnout_local_polyline(dimensions, kind, x_values):
    return [_rea_c10_local_point(dimensions, x, kind) for x in x_values]


def _turnout_map_polyline(host_data, toe_chainage, orientation, handing, local_points):
    return [
        map_turnout_local_point(host_data, toe_chainage, orientation, handing, x, y)
        for x, y in local_points
    ]


def _turnout_wire(points, z_height=0.0):
    clean = _turnout_clean_points(points)
    lifted = [App.Vector(point.x, point.y, float(z_height)) for point in clean]
    wire = Part.makePolygon(lifted)
    if wire.isNull():
        raise ValueError("FreeCAD could not create turnout line geometry.")
    return wire


def _turnout_compound(wires, description):
    valid = [wire for wire in wires if wire is not None and not wire.isNull()]
    if not valid:
        raise ValueError("No {} was created.".format(description))
    if len(valid) == 1:
        return valid[0]
    shape = Part.makeCompound(valid)
    if shape.isNull():
        raise ValueError("FreeCAD could not combine {}.".format(description))
    return shape


def _rea_c10_turnout_outer_gauge_point_at_x(dimensions, x_value):
    """Return the turnout-side outer stock-rail gauge face at a local x station.

    Templot's timber-end calculation uses the separation between the two outer
    stock-rail gauge faces at each timber station. The turnout rail is a normal
    offset from the inner gauge face, so its own x coordinate is slightly
    displaced on curved portions. Resolve that displacement deterministically
    instead of treating the curve parameter as the timber station.
    """
    target = float(x_value)
    gauge = float(dimensions["gauge"])
    if target <= 0.0:
        return target, 0.5 * gauge, 0.0

    def point_for_parameter(parameter):
        base_x, inner_y, theta = _rea_c10_inner_gauge_face(dimensions, parameter)
        return (
            base_x - gauge * math.sin(theta),
            inner_y + gauge * math.cos(theta) - 0.5 * gauge,
            theta,
        )

    lower = target - gauge - 2.0
    upper = target + gauge + 2.0
    for _unused in range(8):
        lower_x = point_for_parameter(lower)[0]
        upper_x = point_for_parameter(upper)[0]
        if lower_x <= target <= upper_x:
            break
        lower -= gauge + 2.0
        upper += gauge + 2.0
    else:
        raise ValueError("The turnout-side stock rail could not be resolved at x {:.3f} mm.".format(target))

    for _unused in range(64):
        middle = 0.5 * (lower + upper)
        middle_x = point_for_parameter(middle)[0]
        if middle_x < target:
            lower = middle
        else:
            upper = middle
    resolved = point_for_parameter(0.5 * (lower + upper))
    return target, resolved[1], resolved[2]


def _turnout_stepped_timber_length(raw_length, increment):
    """Apply the Templot timber-length increment rounding convention."""
    raw = float(raw_length)
    step = max(0.001, float(increment))
    count = int(math.floor(raw / step + 0.67))
    return max(step, count * step)


def _turnout_timber_end_data(dimensions, x_value, template_width):
    gauge = float(dimensions["gauge"])
    base_length = float(template_width)
    if base_length <= gauge + 1.0:
        raise ValueError(
            "The inherited template width {:.3f} mm is too narrow for credible turnout timber shoulders at {:.3f} mm gauge.".format(
                base_length, gauge
            )
        )
    _x, turnout_outer_y, _theta = _rea_c10_turnout_outer_gauge_point_at_x(dimensions, x_value)
    main_outer_y = -0.5 * gauge
    stock_rail_separation = turnout_outer_y - main_outer_y
    raw_length = base_length - gauge + stock_rail_separation
    increment = TURNOUT_TIMBER_LENGTH_INCREMENT_INCHES * dimensions["inch"]
    length = _turnout_stepped_timber_length(raw_length, increment)
    centre_y = 0.5 * (turnout_outer_y + main_outer_y)
    return {
        "main_outer_y": main_outer_y,
        "turnout_outer_y": turnout_outer_y,
        "stock_rail_separation": stock_rail_separation,
        "raw_length": raw_length,
        "length": length,
        "centre_y": centre_y,
        "near_y": centre_y - 0.5 * length,
        "far_y": centre_y + 0.5 * length,
        "length_increment": increment,
    }


def rea_c10_timber_layout(dimensions, template_width):
    """Return deterministic REA C10 timber data in local turnout coordinates.

    The four Templot timbering regions are retained explicitly: the C-switch
    individual centres, the evenly fitted closure region, the fixed wing-front
    and vee-rail crossing-chair regions, and the short exit-joint continuation.
    """
    inch = float(dimensions["inch"])
    module_start = float(dimensions["module_start_x"])
    module_finish = float(dimensions["module_end_x"])
    timber_width = TURNOUT_TIMBER_WIDTH_INCHES * inch
    sleeper_width = TURNOUT_SLEEPER_WIDTH_INCHES * inch
    layout = []

    def add(identifier, section, x_value, width, source_note, crossing_suffix=""):
        x = float(x_value)
        if x < module_start - 1.0e-7 or x > module_finish + 1.0e-7:
            return
        ends = _turnout_timber_end_data(dimensions, x, template_width)
        half_template = 0.5 * float(template_width)
        _cx, branch_centre_y = _rea_c10_local_point(dimensions, x, "turnout_centre")
        main_interval = (-half_template, half_template)
        branch_interval = (branch_centre_y - half_template, branch_centre_y + half_template)
        available_low = min(main_interval[0], branch_interval[0])
        available_high = max(main_interval[1], branch_interval[1])
        void_gap = max(
            0.0,
            branch_interval[0] - main_interval[1],
            main_interval[0] - branch_interval[1],
        )
        outside_by = max(
            0.0,
            available_low - ends["near_y"],
            ends["far_y"] - available_high,
        )
        layout.append({
            "identifier": str(identifier),
            "section": str(section),
            "x": x,
            "width": float(width),
            "near_y": ends["near_y"],
            "far_y": ends["far_y"],
            "centre_y": ends["centre_y"],
            "length": ends["length"],
            "raw_length": ends["raw_length"],
            "length_prototype_inches": ends["length"] / inch,
            "source_note": str(source_note),
            "crossing_suffix": str(crossing_suffix),
            "outside_template_by": outside_by,
            "internal_template_void": void_gap,
        })

    # Switch-front joint sleepers, measured backwards from the switch toe.
    add("J2", "switch front", -52.5 * inch, sleeper_width, "C-switch J2: 28 inches behind J1")
    add("J1", "switch front", -24.5 * inch, sleeper_width, "C-switch J1: 24.5 inches behind toe")

    # Published REA C-size switch timber centres. The final interval places T1,
    # the first closure timber, exactly as in Templot's switchtimbers routine.
    switch_intervals = (3.5, 28.5, 28.5, 28.5, 30.0, 30.0, 30.0, 30.0, 30.0, 30.0, 30.0, 30.0, 26.0, 24.0)
    position = 0.0
    switch_positions = []
    for interval in switch_intervals:
        position += interval * inch
        switch_positions.append(position)
    for index, x_value in enumerate(switch_positions):
        if index == len(switch_positions) - 1:
            identifier = "T1"
            section = "closure"
            note = "first closure timber included in C-switch data at the stock-rail joint"
        else:
            identifier = "S{}".format(index + 1)
            section = "switch"
            note = "published REA C-switch individual centre"
        add(identifier, section, x_value, timber_width, note)

    # The closure region is divided into a whole number of equal spaces not
    # exceeding the Templot default 30-inch maximum. Its final timber is 25
    # inches before the first crossing timber at the wing-rail joint.
    wing_spacing = 30.0 * inch
    wing_joint_spacing = 25.0 * inch
    wing_count = 3
    a_x = float(dimensions["a_timber_x"])
    first_crossing_x = a_x - wing_count * wing_spacing
    closure_finish_x = first_crossing_x - wing_joint_spacing
    closure_start_x = switch_positions[-1]
    closure_length = closure_finish_x - closure_start_x
    if closure_length <= 0.0:
        raise ValueError("The C10 closure region has no positive timbering length.")
    closure_intervals = max(1, int(math.ceil(closure_length / (30.0 * inch) - 1.0e-12)))
    closure_spacing = closure_length / float(closure_intervals)
    for index in range(1, closure_intervals + 1):
        add(
            "T{}".format(index + 1),
            "closure",
            closure_start_x + index * closure_spacing,
            timber_width,
            "closure fill equally divided at {:.3f} prototype inches".format(closure_spacing / inch),
        )

    # Fixed REA regular-crossing spacings. At 1:10 the source calculation uses
    # three wing-front timbers before A and six vee timbers including A.
    wing_suffixes = ("Z", "Y", "X")
    crossing_number = 1
    for index, suffix in enumerate(wing_suffixes):
        add(
            "X{}-{}".format(crossing_number, suffix),
            "crossing wing front",
            first_crossing_x + index * wing_spacing,
            timber_width,
            "REA wing-front crossing-chair spacing: 30 inches",
            suffix,
        )
        crossing_number += 1
    vee_suffixes = ("A", "B", "C", "D", "E", "F")
    for index, suffix in enumerate(vee_suffixes):
        add(
            "X{}-{}".format(crossing_number, suffix),
            "crossing vee",
            a_x + index * 30.0 * inch,
            timber_width,
            "REA vee-rail crossing-chair spacing: 30 inches",
            suffix,
        )
        crossing_number += 1

    # Preserve a balanced joint bay after the point-rail joint within the
    # established 60-inch module extension: 12.5 inches to the first sleeper,
    # then the normal 30-inch spacing.
    first_exit_x = float(dimensions["vee_joint_x"]) + 12.5 * inch
    add("R1", "exit", first_exit_x, sleeper_width, "12.5 inches beyond vee point-rail joint")
    add("R2", "exit", first_exit_x + 30.0 * inch, sleeper_width, "30-inch exit sleeper spacing")

    layout.sort(key=lambda item: (round(float(item["x"]), 9), str(item["identifier"])))
    for sequence, item in enumerate(layout, 1):
        item["sequence"] = sequence
    if len({item["identifier"] for item in layout}) != len(layout):
        raise ValueError("The REA C10 timber layout produced duplicate timber identities.")
    for before, after in zip(layout[:-1], layout[1:]):
        if float(after["x"]) - float(before["x"]) <= 0.01:
            raise ValueError(
                "Timbers {} and {} collide at the same local station.".format(
                    before["identifier"], after["identifier"]
                )
            )
    return layout


def _turnout_timber_outline_local_points(timber):
    x = float(timber["x"])
    half_width = 0.5 * float(timber["width"])
    near_y = float(timber["near_y"])
    far_y = float(timber["far_y"])
    x_values = _turnout_range_values(x - half_width, x + half_width, 0.50)
    return (
        [(value, near_y) for value in x_values]
        + [(value, far_y) for value in reversed(x_values)]
        + [(x - half_width, near_y)]
    )


def _turnout_local_text_segments(text, text_height, origin_x, origin_y):
    segments, text_width, actual_height = _assembly_label_local_segments(text, text_height)
    shifted = [
        (
            (float(origin_x) + start[0], float(origin_y) + start[1]),
            (float(origin_x) + finish[0], float(origin_y) + finish[1]),
        )
        for start, finish in segments
    ]
    return shifted, text_width, actual_height


def _build_rea_c10_timber_shapes(
    host_data,
    toe_chainage,
    orientation,
    handing,
    dimensions,
    template_width,
    engraving_z,
    create_outlines=True,
    create_centres=False,
    create_numbers=True,
    create_length_labels=False,
    create_datums=True,
):
    layout = rea_c10_timber_layout(dimensions, template_width)
    outline_wires = []
    centre_wires = []
    label_wires = []
    datum_wires = []

    for timber in layout:
        if create_outlines:
            local_outline = _turnout_timber_outline_local_points(timber)
            mapped_outline = _turnout_map_polyline(
                host_data, toe_chainage, orientation, handing, local_outline
            )
            _turnout_validate_mapped_polyline(mapped_outline, "Mapped timber {} outline".format(timber["identifier"]))
            outline_wires.append(_turnout_wire(mapped_outline, engraving_z + 0.010))
        if create_centres:
            local_centre = [
                (float(timber["x"]), float(timber["near_y"])),
                (float(timber["x"]), float(timber["far_y"])),
            ]
            mapped_centre = _turnout_map_polyline(
                host_data, toe_chainage, orientation, handing, local_centre
            )
            centre_wires.append(_turnout_wire(mapped_centre, engraving_z + 0.015))
        if create_numbers or create_length_labels:
            height = TURNOUT_TIMBER_LABEL_HEIGHT
            if create_numbers:
                _unused, text_width, actual_height = _turnout_local_text_segments(
                    timber["identifier"], height, 0.0, 0.0
                )
                origin_x = float(timber["x"]) - 0.5 * text_width
                origin_y = float(timber["near_y"]) + TURNOUT_TIMBER_LABEL_CLEARANCE
                local_segments, _w, _h = _turnout_local_text_segments(
                    timber["identifier"], height, origin_x, origin_y
                )
                for local_start, local_finish in local_segments:
                    mapped = _turnout_map_polyline(
                        host_data, toe_chainage, orientation, handing, [local_start, local_finish]
                    )
                    label_wires.append(_turnout_wire(mapped, engraving_z + 0.025))
            if create_length_labels:
                length_text = "{:.0f}MM".format(float(timber["length"]))
                _unused, text_width, actual_height = _turnout_local_text_segments(
                    length_text, height, 0.0, 0.0
                )
                origin_x = float(timber["x"]) - 0.5 * text_width
                origin_y = float(timber["far_y"]) - actual_height - TURNOUT_TIMBER_LABEL_CLEARANCE
                local_segments, _w, _h = _turnout_local_text_segments(
                    length_text, height, origin_x, origin_y
                )
                for local_start, local_finish in local_segments:
                    mapped = _turnout_map_polyline(
                        host_data, toe_chainage, orientation, handing, [local_start, local_finish]
                    )
                    label_wires.append(_turnout_wire(mapped, engraving_z + 0.030))

    if create_datums:
        half_template = 0.5 * float(template_width)
        marker_positions = (
            (0.0, "TOE"),
            (float(dimensions["heel_lead"]), "HEEL"),
            (float(dimensions["fine_point_x"]), "FP"),
            (float(dimensions["blunt_nose_x"]), "BN"),
            (float(dimensions["a_timber_x"]), "A"),
            (float(dimensions["vee_joint_x"]), "VJ"),
        )
        for x_value, marker_text in marker_positions:
            _cx, branch_y = _rea_c10_local_point(dimensions, x_value, "turnout_centre")
            low_y = min(-half_template, branch_y - half_template) - 2.0
            high_y = max(half_template, branch_y + half_template) + 2.0
            mapped = _turnout_map_polyline(
                host_data, toe_chainage, orientation, handing,
                [(x_value, low_y), (x_value, high_y)],
            )
            datum_wires.append(_turnout_wire(mapped, engraving_z + 0.040))
            local_segments, text_width, actual_height = _turnout_local_text_segments(
                marker_text,
                1.20,
                x_value - 0.5 * _assembly_label_local_segments(marker_text, 1.20)[1],
                high_y - 1.20,
            )
            for local_start, local_finish in local_segments:
                mapped_text = _turnout_map_polyline(
                    host_data, toe_chainage, orientation, handing, [local_start, local_finish]
                )
                datum_wires.append(_turnout_wire(mapped_text, engraving_z + 0.045))

    outside = [item for item in layout if float(item["outside_template_by"]) > 0.05]
    internal_voids = [item for item in layout if float(item["internal_template_void"]) > 0.05]
    total_length = sum(float(item["length"]) for item in layout)
    section_counts = {}
    for item in layout:
        section_counts[item["section"]] = section_counts.get(item["section"], 0) + 1

    return {
        "layout": layout,
        "outline_shape": _turnout_compound(outline_wires, "REA C10 timber outlines") if outline_wires else None,
        "centre_shape": _turnout_compound(centre_wires, "REA C10 timber centre lines") if centre_wires else None,
        "label_shape": _turnout_compound(label_wires, "REA C10 timber labels") if label_wires else None,
        "datum_shape": _turnout_compound(datum_wires, "REA C10 construction datums") if datum_wires else None,
        "timber_count": len(layout),
        "total_length": total_length,
        "section_counts": section_counts,
        "outside_template": outside,
        "internal_voids": internal_voids,
    }


def _turnout_timber_x_values(dimensions):
    """Compatibility helper retained for tests and older integrations."""
    return [item["x"] for item in rea_c10_timber_layout(dimensions, DEFAULT_MAIN_TEMPLATE_WIDTH)]

def turnout_host_template_dimensions(doc, host_obj):
    set_id = object_string_property(host_obj, "TemplateSetID", "")
    settings = settings_for_template_set(doc, set_id)
    width = DEFAULT_MAIN_TEMPLATE_WIDTH
    thickness = TEMPLATE_THICKNESS
    track_number = _integer_object_property(host_obj, "TrackNumber", 0)
    route_id = object_string_property(host_obj, "RouteID", "")
    if settings is not None:
        thickness = quantity_value(settings, "TemplateThickness", TEMPLATE_THICKNESS)
        if route_id:
            for config in read_straight_configs(settings):
                if str(config.get("manager_id") or "") == route_id:
                    width = float(config.get("template_width", width))
                    thickness = float(config.get("template_thickness", thickness))
                    break
        elif track_number <= 1:
            width = quantity_value(settings, "MainTemplateWidth", DEFAULT_MAIN_TEMPLATE_WIDTH)
        else:
            configs = read_track_configs(settings, quantity_value(settings, "TransitionLength", DEFAULT_TRANSITION_LENGTH))
            index = track_number - 2
            if 0 <= index < len(configs):
                width = float(configs[index].get("width", width))
    return max(0.001, width), max(0.001, thickness)


def _next_turnout_number(doc):
    used = set()
    for obj in list(doc.Objects):
        value = object_string_property(obj, TURNOUT_ID_PROPERTY, "")
        match = re.search(r"([0-9]+)$", value)
        if match:
            used.add(int(match.group(1)))
    number = 1
    while number in used:
        number += 1
    return number


def _turnout_add_identity_properties(obj, turnout_id, config):
    properties = [
        ensure_property(obj, "App::PropertyString", TURNOUT_ID_PROPERTY, "Turnout identity", "Stable turnout identifier"),
        ensure_property(obj, "App::PropertyString", TURNOUT_HOST_PROPERTY, "Turnout identity", "Generated host centreline object"),
        ensure_property(obj, "App::PropertyString", "TurnoutSize", "Turnout identity", "REA turnout size"),
        ensure_property(obj, "App::PropertyLength", "SwitchToeChainage", "Turnout identity", "Switch-toe chainage along the host centreline"),
        ensure_property(obj, "App::PropertyString", "TurnoutHanding", "Turnout identity", "Turnout hand relative to turnout travel"),
        ensure_property(obj, "App::PropertyString", "TurnoutOrientation", "Turnout identity", "Facing or trailing orientation relative to host travel"),
        ensure_property(obj, "App::PropertyString", TURNOUT_CONFIGURATION_PROPERTY, "Turnout identity", "Validated reusable turnout configuration"),
        ensure_property(obj, "App::PropertyString", "TurnoutGeometrySource", "Turnout identity", "Geometry source and standard"),
        ensure_property(obj, "App::PropertyInteger", "TurnoutTimberGeometryRevision", "Turnout timbering", "REA turnout timbering geometry revision"),
        ensure_property(obj, "App::PropertyInteger", "TurnoutTimberCount", "Turnout timbering", "Number of generated turnout timbers and joint sleepers"),
        ensure_property(obj, "App::PropertyLength", "TurnoutTimberTotalLength", "Turnout timbering", "Combined model length of all generated turnout timbers"),
        ensure_property(obj, "App::PropertyString", "TurnoutTimberBoundaryStatus", "Turnout timbering", "Template-boundary and internal-void result for the turnout timbering"),
        ensure_property(obj, "App::PropertyString", CHAIR_ANALYSIS_STATUS_PROPERTY, "Chair analysis", "Current logical chair-position analysis status"),
        ensure_property(obj, "App::PropertyString", CHAIR_ANALYSIS_SIGNATURE_PROPERTY, "Chair analysis", "Stable rail, timber and chair-setting signature"),
        ensure_property(obj, "App::PropertyInteger", "TurnoutChairPositionCount", "Chair analysis", "Number of logical chair positions in the latest analysis"),
        ensure_property(obj, "App::PropertyInteger", "TurnoutChairCriticalCount", "Chair analysis", "Number of production-critical logical chair findings"),
    ]
    setattr(obj, TURNOUT_ID_PROPERTY, str(turnout_id))
    setattr(obj, TURNOUT_HOST_PROPERTY, str(config.get("host_object") or ""))
    obj.TurnoutSize = TURNOUT_SIZE_C10
    obj.SwitchToeChainage = float(config["toe_chainage"])
    obj.TurnoutHanding = str(config["handing"])
    obj.TurnoutOrientation = str(config["orientation"])
    setattr(obj, TURNOUT_CONFIGURATION_PROPERTY, json.dumps(config, sort_keys=True))
    obj.TurnoutGeometrySource = TURNOUT_SOURCE_NOTE
    obj.TurnoutTimberGeometryRevision = int(config.get("timber_geometry_revision") or 0)
    obj.TurnoutTimberCount = int(config.get("timber_count") or 0)
    obj.TurnoutTimberTotalLength = float(config.get("timber_total_length") or 0.0)
    obj.TurnoutTimberBoundaryStatus = str(config.get("timber_boundary_status") or "Not generated")
    setattr(obj, CHAIR_ANALYSIS_STATUS_PROPERTY, str(config.get("chair_analysis_status") or CHAIR_STATUS_NOT_ANALYSED))
    setattr(obj, CHAIR_ANALYSIS_SIGNATURE_PROPERTY, str(config.get("chair_analysis_signature") or ""))
    chair_summary = dict(config.get("chair_analysis_summary") or {})
    obj.TurnoutChairPositionCount = int(chair_summary.get("chair_position_count") or 0)
    obj.TurnoutChairCriticalCount = int((chair_summary.get("severity_counts") or {}).get(CHAIR_SEVERITY_CRITICAL) or 0)
    set_read_only(obj, properties)


def _turnout_current_catalogue(doc, set_id):
    entries = []
    for obj in list(doc.Objects):
        if object_string_property(obj, "GeneratedBy", "") != GENERATOR_ID:
            continue
        if object_string_property(obj, "TemplateSetID", "") != str(set_id or ""):
            continue
        if object_string_property(obj, "GeneratedRole", "") != TURNOUT_SETTINGS_ROLE:
            continue
        stored = object_string_property(obj, TURNOUT_CONFIGURATION_PROPERTY, "")
        try:
            config = json.loads(stored)
        except Exception:
            config = {}
        if isinstance(config, dict):
            entries.append(config)
    entries.sort(key=lambda item: str(item.get("turnout_id") or ""))
    return entries


def _turnout_store_catalogue(doc, set_id):
    settings = settings_for_template_set(doc, set_id)
    if settings is None:
        raise ValueError("The selected template set has no recognised settings object.")
    prop = ensure_property(
        settings,
        "App::PropertyString",
        TURNOUT_CATALOGUE_PROPERTY,
        "Turnout manager",
        "Validated C10 turnouts placed on this generated template set",
    )
    setattr(settings, TURNOUT_CATALOGUE_PROPERTY, json.dumps(_turnout_current_catalogue(doc, set_id), sort_keys=True))
    set_read_only(settings, [prop])


def _turnout_record(obj, role, subtype, category, selection_key, config, shape, feature_number, template_thickness):
    return {
        "role": role,
        "subtype": subtype,
        "category": category,
        "selection_key": selection_key,
        "route_id": str(config.get("route_id") or ""),
        "route_name": str(config.get("route_name") or ""),
        "track_number": int(config.get("track_number") or 0),
        "track_name": str(config.get("track_name") or ""),
        "platform_number": 0,
        "platform_name": "",
        "section_number": 0,
        "travel_order_number": 0,
        "feature_number": int(feature_number),
        "section_length": float(config.get("module_length") or 0.0),
        "template_thickness": float(template_thickness),
        "source_name": str(obj.Name),
        "source_label": str(getattr(obj, "Label", obj.Name)),
        "shape": shape.copy(),
    }


def _turnout_store_production_records(doc, set_id, new_records, removed_source_names=None):
    settings = settings_for_template_set(doc, set_id)
    if settings is None:
        raise ValueError("The selected template set has no persistent settings object.")
    payload = read_production_record_index(settings)
    records = hydrate_production_index_records(doc, payload) if payload else []
    removed = set(str(name) for name in (removed_source_names or []))
    if removed:
        records = [record for record in records if str(record.get("source_name") or "") not in removed]
    records.extend(new_records or [])
    assign_production_record_ids(records, set_id)
    tag_production_record_bindings(doc, set_id, records)
    index_payload = build_production_record_index(records, set_id)
    prop = ensure_property(
        settings,
        "App::PropertyString",
        PRODUCTION_RECORD_INDEX_PROPERTY,
        "Production utilities",
        "Persistent one-record production catalogue",
    )
    setattr(settings, PRODUCTION_RECORD_INDEX_PROPERTY, json.dumps(index_payload, sort_keys=True))
    set_read_only(settings, [prop])
    return index_payload


def _turnout_group_parent(doc, set_id):
    return production_parent_group_for_set(doc, set_id)


def _turnout_number_from_identifier(turnout_id):
    match = re.search(r"([0-9]+)$", str(turnout_id or ""))
    if not match:
        raise ValueError("The turnout identifier does not contain a stable feature number.")
    return int(match.group(1))


def turnout_config_by_id(doc, turnout_id):
    identifier = str(turnout_id or "").strip()
    for config in existing_turnout_configs(doc):
        if str(config.get("turnout_id") or "") == identifier:
            return dict(config)
    return None


def _turnout_objects_by_role(doc, turnout_id):
    identifier = str(turnout_id or "").strip()
    objects = [
        obj for obj in list(doc.Objects)
        if object_string_property(obj, TURNOUT_ID_PROPERTY, "") == identifier
    ]
    roles = {}
    for obj in objects:
        role = object_string_property(obj, "GeneratedRole", "")
        if role in roles:
            raise ValueError("Turnout {} has duplicate {} objects.".format(identifier, role or "unclassified"))
        roles[role] = obj
    return roles


def turnout_configuration_change_summary(old_config, new_config):
    """Return concise, deterministic user-facing differences for a turnout edit."""
    old = old_config if isinstance(old_config, dict) else {}
    new = new_config if isinstance(new_config, dict) else {}
    changes = []
    specifications = (
        ("toe_chainage", "Switch-toe chainage", "{:.3f} mm"),
        ("handing", "Handing", "{}"),
        ("orientation", "Orientation", "{}"),
        ("track_gauge", "Track gauge", "{:.3f} mm"),
        ("flangeway", "Design flangeway", "{:.3f} mm"),
        ("timber_outlines", "Timber outlines", "{}"),
        ("timber_centres", "Timber centre lines", "{}"),
        ("timber_numbers", "Timber identities", "{}"),
        ("timber_length_labels", "Timber length labels", "{}"),
        ("construction_marks", "Construction datums", "{}"),
    )
    for key, label, pattern in specifications:
        old_value = old.get(key)
        new_value = new.get(key)
        if key in ("toe_chainage", "track_gauge", "flangeway"):
            try:
                unchanged = abs(float(old_value) - float(new_value)) <= 1.0e-9
            except Exception:
                unchanged = old_value == new_value
        else:
            unchanged = old_value == new_value
        if unchanged:
            continue
        if key in ("timber_outlines", "timber_centres", "timber_numbers", "timber_length_labels", "construction_marks"):
            old_text = "enabled" if bool(old_value) else "disabled"
            new_text = "enabled" if bool(new_value) else "disabled"
        elif key in ("toe_chainage", "track_gauge", "flangeway"):
            old_text = pattern.format(float(old_value))
            new_text = pattern.format(float(new_value))
        else:
            old_text = pattern.format(old_value)
            new_text = pattern.format(new_value)
        changes.append("{}: {} -> {}".format(label, old_text, new_text))
    old_revision = int(old.get("rail_geometry_revision") or 0)
    new_revision = int(new.get("rail_geometry_revision") or TURNOUT_RAIL_GEOMETRY_REVISION)
    if old_revision != new_revision:
        changes.append(
            "Rail construction geometry: revision {} -> revision {} (complete common crossing, vee, wing and check rails)".format(
                old_revision, new_revision
            )
        )
    old_timber_revision = int(old.get("timber_geometry_revision") or 0)
    new_timber_revision = int(new.get("timber_geometry_revision") or TURNOUT_TIMBER_GEOMETRY_REVISION)
    if old_timber_revision != new_timber_revision:
        changes.append(
            "Turnout timbering: revision {} -> revision {} (REA switch, closure, crossing and exit timber outlines)".format(
                old_timber_revision, new_timber_revision
            )
        )
    return changes


def _build_curve_inheriting_c10_turnout(
    doc,
    host_obj,
    toe_chainage,
    handing,
    orientation,
    track_gauge,
    flangeway,
    create_timber_references=True,
    create_timber_centres=False,
    create_timber_numbers=True,
    create_timber_length_labels=False,
    create_construction_marks=True,
    turnout_id=None,
    ignored_turnout_id=None,
):
    """Build and validate every replacement shape in memory before document changes."""
    if not is_turnout_host_centreline(host_obj):
        raise ValueError("Select a recognised generated track centreline as the turnout host.")
    handing = str(handing)
    orientation = str(orientation)
    if handing not in (TURNOUT_HAND_LEFT, TURNOUT_HAND_RIGHT):
        raise ValueError("Turnout handing must be Left-hand or Right-hand.")
    if orientation not in (TURNOUT_ORIENTATION_FACING, TURNOUT_ORIENTATION_TRAILING):
        raise ValueError("Turnout orientation is not recognised.")

    host_data = turnout_host_alignment(host_obj)
    dimensions = rea_c10_dimensions(track_gauge, flangeway)
    minimum, maximum = turnout_valid_toe_range(host_data["total"], dimensions, orientation)
    toe = float(toe_chainage)
    if not math.isfinite(toe):
        raise ValueError("Switch-toe chainage must be a finite number.")
    if maximum < minimum - GEOMETRY_TOLERANCE:
        raise ValueError("The selected host is too short for a complete REA C10 turnout module.")
    if toe < minimum - 1.0e-7 or toe > maximum + 1.0e-7:
        raise ValueError(
            "Switch-toe chainage must be between {:.3f} and {:.3f} mm for this orientation.".format(minimum, maximum)
        )
    overlap_config, overlap_length = _turnout_find_overlap(
        doc, host_obj, toe, dimensions, orientation, ignored_turnout_id=ignored_turnout_id
    )
    if overlap_config is not None:
        raise ValueError(
            "This turnout module overlaps {} by {:.3f} mm along the selected host. "
            "Move it clear of the existing turnout first.".format(
                overlap_config.get("turnout_id", "an existing turnout"), overlap_length
            )
        )

    set_id = object_string_property(host_obj, "TemplateSetID", "")
    if not set_id:
        raise ValueError("The selected host has no template-set identity.")
    track_number = _integer_object_property(host_obj, "TrackNumber", 0)
    route_id = object_string_property(host_obj, "RouteID", "")
    route_name = object_string_property(host_obj, "RouteName", "")
    track_name = object_string_property(host_obj, "TrackName", "")
    if not track_name:
        track_name = "Track {}".format(track_number) if track_number > 0 else str(getattr(host_obj, "Label", host_obj.Name))
    template_width, template_thickness = turnout_host_template_dimensions(doc, host_obj)

    if turnout_id is None:
        number = _next_turnout_number(doc)
        identifier = "TO-{:03d}".format(number)
    else:
        identifier = str(turnout_id).strip()
        if not identifier:
            raise ValueError("The turnout edit requires a stable turnout identifier.")
        number = _turnout_number_from_identifier(identifier)

    mapping = turnout_mapping_metrics(host_data, toe, orientation, handing, dimensions)
    x_values = mapping["x_values"]
    main_points = mapping["main_points"]
    turnout_points = mapping["turnout_points"]
    main_headings = _turnout_polyline_headings(main_points)
    turnout_headings = _turnout_polyline_headings(turnout_points)

    main_solid = create_template_shape(main_points, main_headings, template_width, template_thickness)
    turnout_solid = create_template_shape(turnout_points, turnout_headings, template_width, template_thickness)
    combined_solid = _refine_shape(main_solid.fuse(turnout_solid))
    if combined_solid.isNull():
        raise ValueError("FreeCAD could not fuse the main-road and turnout-road template strips.")

    main_face = create_template_plan_face(main_points, main_headings, template_width)
    turnout_face = create_template_plan_face(turnout_points, turnout_headings, template_width)
    combined_face = _refine_shape(main_face.fuse(turnout_face))
    if combined_face.isNull():
        raise ValueError("FreeCAD could not create the turnout cutting footprint.")
    combined_outline = _outline_shape_from_face(combined_face)
    if _shape_is_null(combined_outline):
        raise ValueError("FreeCAD could not extract the turnout cutting outline.")

    engraving_z = template_thickness + CENTRELINE_LIFT + 0.03
    rail_wires = []
    for rail_name, local_points in rea_c10_complete_rail_polylines(dimensions):
        mapped = _turnout_map_polyline(host_data, toe, orientation, handing, local_points)
        _turnout_validate_mapped_polyline(mapped, "Mapped {}".format(rail_name))
        rail_wires.append(_turnout_wire(mapped, engraving_z))
    rail_shape = _turnout_compound(rail_wires, "complete C10 rail construction geometry")

    timber_bundle = _build_rea_c10_timber_shapes(
        host_data,
        toe,
        orientation,
        handing,
        dimensions,
        template_width,
        engraving_z,
        create_outlines=bool(create_timber_references),
        create_centres=bool(create_timber_centres),
        create_numbers=bool(create_timber_numbers),
        create_length_labels=bool(create_timber_length_labels),
        create_datums=bool(create_construction_marks),
    )
    timber_shape = timber_bundle["outline_shape"]
    timber_centre_shape = timber_bundle["centre_shape"]
    timber_label_shape = timber_bundle["label_shape"]
    datum_shape = timber_bundle["datum_shape"]

    config = {
        "schema_version": TURNOUT_SCHEMA_VERSION,
        "macro_version": MACRO_VERSION_NUMBER,
        "turnout_id": identifier,
        "size": TURNOUT_SIZE_C10,
        "host_object": str(host_obj.Name),
        "host_label": str(getattr(host_obj, "Label", host_obj.Name)),
        "template_set_id": set_id,
        "route_id": route_id,
        "route_name": route_name,
        "track_number": track_number,
        "track_name": track_name,
        "toe_chainage": toe,
        "handing": handing,
        "orientation": orientation,
        "track_gauge": float(track_gauge),
        "flangeway": float(flangeway),
        "template_width": template_width,
        "template_thickness": template_thickness,
        "host_length": host_data["total"],
        "module_start_x": dimensions["module_start_x"],
        "module_end_x": dimensions["module_end_x"],
        "module_length": dimensions["module_end_x"] - dimensions["module_start_x"],
        "switch_radius": dimensions["switch_radius"],
        "turnout_radius_straight_reference": dimensions["turnout_radius"],
        "host_minimum_radius_sampled": mapping["host_minimum_radius"],
        "turnout_minimum_radius_sampled": mapping["turnout_minimum_radius"],
        "host_station_interval": list(turnout_host_station_interval(toe, dimensions, orientation)),
        "source": TURNOUT_SOURCE_NOTE,
        "curvature_mapping": "station-normal mapping through complete host alignment",
        "rail_geometry_revision": TURNOUT_RAIL_GEOMETRY_REVISION,
        "rail_geometry_content": list(TURNOUT_RAIL_GEOMETRY_CONTENT),
        "rail_head_width": dimensions["rail_head_width"],
        "flare_end_gap": dimensions["flare_end_gap"],
        "knuckle_radius": dimensions["knuckle_radius"],
        "timber_references": bool(create_timber_references),
        "timber_outlines": bool(create_timber_references),
        "timber_centres": bool(create_timber_centres),
        "timber_numbers": bool(create_timber_numbers),
        "timber_length_labels": bool(create_timber_length_labels),
        "construction_marks": bool(create_construction_marks),
        "timber_geometry_revision": TURNOUT_TIMBER_GEOMETRY_REVISION,
        "timber_source": TURNOUT_TIMBER_SOURCE_NOTE,
        "timber_count": int(timber_bundle["timber_count"]),
        "timber_total_length": float(timber_bundle["total_length"]),
        "timber_section_counts": dict(timber_bundle["section_counts"]),
        "timber_width": TURNOUT_TIMBER_WIDTH_INCHES * dimensions["inch"],
        "joint_sleeper_width": TURNOUT_SLEEPER_WIDTH_INCHES * dimensions["inch"],
        "timber_length_increment": TURNOUT_TIMBER_LENGTH_INCREMENT_INCHES * dimensions["inch"],
        "timber_outside_template_count": len(timber_bundle["outside_template"]),
        "timber_internal_void_count": len(timber_bundle["internal_voids"]),
        "timber_boundary_status": (
            "All timber outlines remain within the combined turnout-template envelope"
            if not timber_bundle["outside_template"] and not timber_bundle["internal_voids"]
            else "{} outline(s) extend beyond the combined envelope; {} outline(s) cross a template-strip void".format(
                len(timber_bundle["outside_template"]), len(timber_bundle["internal_voids"])
            )
        ),
    }
    return {
        "config": config,
        "number": number,
        "set_id": set_id,
        "route_id": route_id,
        "route_name": route_name,
        "track_number": track_number,
        "template_thickness": template_thickness,
        "template_width": template_width,
        "host_data": host_data,
        "dimensions": dimensions,
        "main_points": main_points,
        "main_headings": main_headings,
        "turnout_points": turnout_points,
        "turnout_headings": turnout_headings,
        "main_solid_shape": main_solid,
        "turnout_solid_shape": turnout_solid,
        "combined_face": combined_face,
        "solid_shape": combined_solid,
        "outline_shape": combined_outline,
        "rail_shape": rail_shape,
        "timber_shape": timber_shape,
        "timber_centre_shape": timber_centre_shape,
        "timber_label_shape": timber_label_shape,
        "datum_shape": datum_shape,
        "timber_layout": timber_bundle["layout"],
    }


def _turnout_apply_display_style(
    solid_obj,
    outline_obj,
    rail_obj,
    timber_obj=None,
    timber_centre_obj=None,
    timber_label_obj=None,
    datum_obj=None,
):
    if Gui is None:
        return
    try:
        solid_obj.ViewObject.ShapeColor = (0.76, 0.80, 0.84)
        outline_obj.ViewObject.Visibility = False
        rail_obj.ViewObject.LineColor = (0.10, 0.10, 0.10)
        rail_obj.ViewObject.LineWidth = 1.5
        if timber_obj is not None:
            timber_obj.ViewObject.LineColor = (0.42, 0.30, 0.18)
            timber_obj.ViewObject.LineWidth = 1.2
        if timber_centre_obj is not None:
            timber_centre_obj.ViewObject.LineColor = (0.55, 0.55, 0.55)
            timber_centre_obj.ViewObject.LineWidth = 1.0
        if timber_label_obj is not None:
            timber_label_obj.ViewObject.LineColor = (0.75, 0.35, 0.05)
            timber_label_obj.ViewObject.LineWidth = 1.0
        if datum_obj is not None:
            datum_obj.ViewObject.LineColor = (0.20, 0.35, 0.80)
            datum_obj.ViewObject.LineWidth = 1.0
    except Exception:
        pass


def _turnout_add_geometry_object(
    doc,
    group,
    turnout_id,
    set_id,
    route_id,
    route_name,
    track_number,
    number,
    config,
    role,
    subtype,
    label,
    internal_stem,
    shape,
):
    if shape is None or _shape_is_null(shape):
        return None
    obj = doc.addObject(
        "Part::Feature",
        unique_internal_name(doc, "{}_{}".format(internal_stem, turnout_id.replace('-', '_'))),
    )
    obj.Label = label
    obj.Shape = shape
    tag_generated_object(obj, role, set_id)
    tag_route_metadata(obj, route_id, route_name)
    tag_export_metadata(
        obj,
        subtype,
        EXPORT_CATEGORY_ENGRAVING,
        track_number=track_number,
        feature_number=number,
        section_length=config["module_length"],
    )
    _turnout_add_identity_properties(obj, turnout_id, config)
    group.addObject(obj)
    return obj


def _turnout_update_optional_geometry_object(
    doc,
    group,
    existing_obj,
    turnout_id,
    set_id,
    route_id,
    route_name,
    track_number,
    number,
    config,
    role,
    subtype,
    label,
    internal_stem,
    shape,
):
    if shape is None or _shape_is_null(shape):
        if existing_obj is not None:
            doc.removeObject(str(existing_obj.Name))
        return None
    obj = existing_obj
    if obj is None:
        obj = doc.addObject(
            "Part::Feature",
            unique_internal_name(doc, "{}_{}".format(internal_stem, turnout_id.replace('-', '_'))),
        )
        group.addObject(obj)
    obj.Label = label
    obj.Shape = shape
    tag_generated_object(obj, role, set_id)
    tag_route_metadata(obj, route_id, route_name)
    tag_export_metadata(
        obj,
        subtype,
        EXPORT_CATEGORY_ENGRAVING,
        track_number=track_number,
        feature_number=number,
        section_length=config["module_length"],
    )
    _turnout_add_identity_properties(obj, turnout_id, config)
    return obj


def _turnout_append_optional_record(
    records,
    obj,
    role,
    subtype,
    config,
    shape,
    number,
    template_thickness,
):
    if obj is None or shape is None or _shape_is_null(shape):
        return
    records.append(
        _turnout_record(
            obj,
            role,
            subtype,
            EXPORT_CATEGORY_ENGRAVING,
            TURNOUT_SELECTION_ENGRAVING,
            config,
            shape,
            number,
            template_thickness,
        )
    )


def create_curve_inheriting_c10_turnout(
    doc,
    host_obj,
    toe_chainage,
    handing,
    orientation,
    track_gauge,
    flangeway,
    create_timber_references=True,
    create_timber_centres=False,
    create_timber_numbers=True,
    create_timber_length_labels=False,
    create_construction_marks=True,
):
    built = _build_curve_inheriting_c10_turnout(
        doc,
        host_obj,
        toe_chainage,
        handing,
        orientation,
        track_gauge,
        flangeway,
        create_timber_references=create_timber_references,
        create_timber_centres=create_timber_centres,
        create_timber_numbers=create_timber_numbers,
        create_timber_length_labels=create_timber_length_labels,
        create_construction_marks=create_construction_marks,
    )
    config = built["config"]
    turnout_id = config["turnout_id"]
    set_id = built["set_id"]
    route_id = built["route_id"]
    route_name = built["route_name"]
    track_number = built["track_number"]
    number = built["number"]
    template_thickness = built["template_thickness"]
    combined_solid = built["solid_shape"]
    combined_outline = built["outline_shape"]
    rail_shape = built["rail_shape"]
    timber_shape = built["timber_shape"]
    timber_centre_shape = built["timber_centre_shape"]
    timber_label_shape = built["timber_label_shape"]
    datum_shape = built["datum_shape"]

    transaction_open = False
    try:
        doc.openTransaction("Create Version {} REA C10 turnout".format(MACRO_VERSION_NUMBER))
        transaction_open = True
        group = doc.addObject(
            "App::DocumentObjectGroup",
            unique_internal_name(doc, "RailwayTurnout_{}".format(turnout_id.replace('-', '_'))),
        )
        group.Label = "{} {} [{}]".format(turnout_id, TURNOUT_SIZE_C10, set_id)
        tag_generated_object(group, TURNOUT_GROUP_ROLE, set_id)
        _turnout_add_identity_properties(group, turnout_id, config)
        parent = _turnout_group_parent(doc, set_id)
        if parent is not None:
            parent.addObject(group)

        settings_obj = doc.addObject(
            "Part::Feature",
            unique_internal_name(doc, "RailwayTurnoutSettings_{}".format(turnout_id.replace('-', '_'))),
        )
        settings_obj.Label = "{} Turnout Settings".format(turnout_id)
        tag_generated_object(settings_obj, TURNOUT_SETTINGS_ROLE, set_id)
        _turnout_add_identity_properties(settings_obj, turnout_id, config)
        group.addObject(settings_obj)

        solid_obj = doc.addObject(
            "Part::Feature",
            unique_internal_name(doc, "RailwayTurnoutTemplate_{}".format(turnout_id.replace('-', '_'))),
        )
        solid_obj.Label = "{} C10 Turnout Template".format(turnout_id)
        solid_obj.Shape = combined_solid
        tag_generated_object(solid_obj, TURNOUT_TEMPLATE_ROLE, set_id)
        tag_route_metadata(solid_obj, route_id, route_name)
        tag_export_metadata(
            solid_obj,
            TURNOUT_SUBTYPE_TEMPLATE,
            EXPORT_CATEGORY_SOLID,
            track_number=track_number,
            feature_number=number,
            section_length=config["module_length"],
        )
        _turnout_add_identity_properties(solid_obj, turnout_id, config)
        group.addObject(solid_obj)

        outline_obj = doc.addObject(
            "Part::Feature",
            unique_internal_name(doc, "RailwayTurnoutPlanOutline_{}".format(turnout_id.replace('-', '_'))),
        )
        outline_obj.Label = "{} C10 Turnout Cutting Footprint".format(turnout_id)
        outline_obj.Shape = combined_outline
        tag_generated_object(outline_obj, TURNOUT_OUTLINE_ROLE, set_id)
        tag_route_metadata(outline_obj, route_id, route_name)
        tag_export_metadata(
            outline_obj,
            TURNOUT_SUBTYPE_TEMPLATE,
            EXPORT_CATEGORY_CUTTING,
            track_number=track_number,
            feature_number=number,
            section_length=config["module_length"],
        )
        _turnout_add_identity_properties(outline_obj, turnout_id, config)
        group.addObject(outline_obj)

        rail_obj = doc.addObject(
            "Part::Feature",
            unique_internal_name(doc, "RailwayTurnoutRailGeometry_{}".format(turnout_id.replace('-', '_'))),
        )
        rail_obj.Label = "{} C10 Rail and Centreline References".format(turnout_id)
        rail_obj.Shape = rail_shape
        tag_generated_object(rail_obj, TURNOUT_RAIL_ROLE, set_id)
        tag_route_metadata(rail_obj, route_id, route_name)
        tag_export_metadata(
            rail_obj,
            TURNOUT_SUBTYPE_RAIL,
            EXPORT_CATEGORY_ENGRAVING,
            track_number=track_number,
            feature_number=number,
            section_length=config["module_length"],
        )
        _turnout_add_identity_properties(rail_obj, turnout_id, config)
        group.addObject(rail_obj)

        timber_obj = _turnout_add_geometry_object(
            doc, group, turnout_id, set_id, route_id, route_name, track_number, number, config,
            TURNOUT_TIMBER_ROLE, TURNOUT_SUBTYPE_TIMBER,
            "{} C10 REA Timber Outlines".format(turnout_id),
            "RailwayTurnoutTimberOutlines", timber_shape,
        )
        timber_centre_obj = _turnout_add_geometry_object(
            doc, group, turnout_id, set_id, route_id, route_name, track_number, number, config,
            TURNOUT_TIMBER_CENTRE_ROLE, TURNOUT_SUBTYPE_TIMBER_CENTRE,
            "{} C10 Timber Centre Lines".format(turnout_id),
            "RailwayTurnoutTimberCentres", timber_centre_shape,
        )
        timber_label_obj = _turnout_add_geometry_object(
            doc, group, turnout_id, set_id, route_id, route_name, track_number, number, config,
            TURNOUT_TIMBER_LABEL_ROLE, TURNOUT_SUBTYPE_TIMBER_LABEL,
            "{} C10 Timber Identities and Lengths".format(turnout_id),
            "RailwayTurnoutTimberLabels", timber_label_shape,
        )
        datum_obj = _turnout_add_geometry_object(
            doc, group, turnout_id, set_id, route_id, route_name, track_number, number, config,
            TURNOUT_DATUM_ROLE, TURNOUT_SUBTYPE_DATUM,
            "{} C10 Construction Datums".format(turnout_id),
            "RailwayTurnoutConstructionMarks", datum_shape,
        )

        _turnout_apply_display_style(
            solid_obj,
            outline_obj,
            rail_obj,
            timber_obj,
            timber_centre_obj,
            timber_label_obj,
            datum_obj,
        )
        records = [
            _turnout_record(
                solid_obj, TURNOUT_TEMPLATE_ROLE, TURNOUT_SUBTYPE_TEMPLATE,
                EXPORT_CATEGORY_SOLID, TURNOUT_SELECTION_TEMPLATE_3D,
                config, combined_solid, number, template_thickness,
            ),
            _turnout_record(
                outline_obj, TURNOUT_OUTLINE_ROLE, TURNOUT_SUBTYPE_TEMPLATE,
                EXPORT_CATEGORY_CUTTING, TURNOUT_SELECTION_TEMPLATE_2D,
                config, combined_outline, number, template_thickness,
            ),
            _turnout_record(
                rail_obj, TURNOUT_RAIL_ROLE, TURNOUT_SUBTYPE_RAIL,
                EXPORT_CATEGORY_ENGRAVING, TURNOUT_SELECTION_ENGRAVING,
                config, rail_shape, number, template_thickness,
            ),
        ]
        _turnout_append_optional_record(
            records, timber_obj, TURNOUT_TIMBER_ROLE, TURNOUT_SUBTYPE_TIMBER,
            config, timber_shape, number, template_thickness,
        )
        _turnout_append_optional_record(
            records, timber_centre_obj, TURNOUT_TIMBER_CENTRE_ROLE, TURNOUT_SUBTYPE_TIMBER_CENTRE,
            config, timber_centre_shape, number, template_thickness,
        )
        _turnout_append_optional_record(
            records, timber_label_obj, TURNOUT_TIMBER_LABEL_ROLE, TURNOUT_SUBTYPE_TIMBER_LABEL,
            config, timber_label_shape, number, template_thickness,
        )
        _turnout_append_optional_record(
            records, datum_obj, TURNOUT_DATUM_ROLE, TURNOUT_SUBTYPE_DATUM,
            config, datum_shape, number, template_thickness,
        )
        _turnout_store_production_records(doc, set_id, records)
        _turnout_store_catalogue(doc, set_id)
        _document_recompute(doc)
        doc.commitTransaction()
        transaction_open = False
    except Exception:
        if transaction_open:
            try:
                doc.abortTransaction()
            except Exception:
                pass
        raise
    return config


def edit_curve_inheriting_c10_turnout(
    doc,
    turnout_id,
    host_obj,
    toe_chainage,
    handing,
    orientation,
    track_gauge,
    flangeway,
    create_timber_references=True,
    create_timber_centres=False,
    create_timber_numbers=True,
    create_timber_length_labels=False,
    create_construction_marks=True,
):
    """Edit an existing turnout in one transaction after complete in-memory validation."""
    identifier = str(turnout_id or "").strip()
    if not identifier:
        raise ValueError("Select a turnout to edit.")
    if turnout_integration_by_id(doc, identifier) is not None:
        raise ValueError("Remove the host-template integration before editing {}. This preserves all affected production records and section boundaries safely.".format(identifier))
    old_config = turnout_config_by_id(doc, identifier)
    if old_config is None:
        raise ValueError("Turnout {} no longer exists in this document.".format(identifier))
    if str(getattr(host_obj, "Name", "")) != str(old_config.get("host_object") or ""):
        raise ValueError("An existing turnout must remain on its original host centreline during Stage 8A editing.")

    clear_chair_analysis_display(doc, "turnout", identifier)
    roles = _turnout_objects_by_role(doc, identifier)
    required_roles = (
        TURNOUT_GROUP_ROLE,
        TURNOUT_SETTINGS_ROLE,
        TURNOUT_TEMPLATE_ROLE,
        TURNOUT_OUTLINE_ROLE,
        TURNOUT_RAIL_ROLE,
    )
    missing = [role for role in required_roles if role not in roles]
    if missing:
        raise ValueError("Turnout {} is incomplete; missing {}.".format(identifier, ", ".join(missing)))

    built = _build_curve_inheriting_c10_turnout(
        doc,
        host_obj,
        toe_chainage,
        handing,
        orientation,
        track_gauge,
        flangeway,
        create_timber_references=create_timber_references,
        create_timber_centres=create_timber_centres,
        create_timber_numbers=create_timber_numbers,
        create_timber_length_labels=create_timber_length_labels,
        create_construction_marks=create_construction_marks,
        turnout_id=identifier,
        ignored_turnout_id=identifier,
    )
    config = built["config"]
    if str(config.get("template_set_id") or "") != str(old_config.get("template_set_id") or ""):
        raise ValueError("The edited turnout cannot move between template sets.")

    changes = turnout_configuration_change_summary(old_config, config)
    if not changes:
        return old_config

    group = roles[TURNOUT_GROUP_ROLE]
    settings_obj = roles[TURNOUT_SETTINGS_ROLE]
    solid_obj = roles[TURNOUT_TEMPLATE_ROLE]
    outline_obj = roles[TURNOUT_OUTLINE_ROLE]
    rail_obj = roles[TURNOUT_RAIL_ROLE]
    old_source_names = {
        str(obj.Name)
        for role, obj in roles.items()
        if role not in (TURNOUT_GROUP_ROLE, TURNOUT_SETTINGS_ROLE)
    }

    set_id = built["set_id"]
    route_id = built["route_id"]
    route_name = built["route_name"]
    track_number = built["track_number"]
    number = built["number"]
    template_thickness = built["template_thickness"]
    combined_solid = built["solid_shape"]
    combined_outline = built["outline_shape"]
    rail_shape = built["rail_shape"]
    timber_shape = built["timber_shape"]
    timber_centre_shape = built["timber_centre_shape"]
    timber_label_shape = built["timber_label_shape"]
    datum_shape = built["datum_shape"]

    transaction_open = False
    try:
        doc.openTransaction("Edit Version {} turnout {}".format(MACRO_VERSION_NUMBER, identifier))
        transaction_open = True

        group.Label = "{} {} [{}]".format(identifier, TURNOUT_SIZE_C10, set_id)
        tag_generated_object(group, TURNOUT_GROUP_ROLE, set_id)
        _turnout_add_identity_properties(group, identifier, config)

        settings_obj.Label = "{} Turnout Settings".format(identifier)
        tag_generated_object(settings_obj, TURNOUT_SETTINGS_ROLE, set_id)
        _turnout_add_identity_properties(settings_obj, identifier, config)

        solid_obj.Label = "{} C10 Turnout Template".format(identifier)
        solid_obj.Shape = combined_solid
        tag_generated_object(solid_obj, TURNOUT_TEMPLATE_ROLE, set_id)
        tag_route_metadata(solid_obj, route_id, route_name)
        tag_export_metadata(
            solid_obj,
            TURNOUT_SUBTYPE_TEMPLATE,
            EXPORT_CATEGORY_SOLID,
            track_number=track_number,
            feature_number=number,
            section_length=config["module_length"],
        )
        _turnout_add_identity_properties(solid_obj, identifier, config)

        outline_obj.Label = "{} C10 Turnout Cutting Footprint".format(identifier)
        outline_obj.Shape = combined_outline
        tag_generated_object(outline_obj, TURNOUT_OUTLINE_ROLE, set_id)
        tag_route_metadata(outline_obj, route_id, route_name)
        tag_export_metadata(
            outline_obj,
            TURNOUT_SUBTYPE_TEMPLATE,
            EXPORT_CATEGORY_CUTTING,
            track_number=track_number,
            feature_number=number,
            section_length=config["module_length"],
        )
        _turnout_add_identity_properties(outline_obj, identifier, config)

        rail_obj.Label = "{} C10 Rail and Centreline References".format(identifier)
        rail_obj.Shape = rail_shape
        tag_generated_object(rail_obj, TURNOUT_RAIL_ROLE, set_id)
        tag_route_metadata(rail_obj, route_id, route_name)
        tag_export_metadata(
            rail_obj,
            TURNOUT_SUBTYPE_RAIL,
            EXPORT_CATEGORY_ENGRAVING,
            track_number=track_number,
            feature_number=number,
            section_length=config["module_length"],
        )
        _turnout_add_identity_properties(rail_obj, identifier, config)

        timber_obj = _turnout_update_optional_geometry_object(
            doc, group, roles.get(TURNOUT_TIMBER_ROLE), identifier, set_id, route_id, route_name,
            track_number, number, config, TURNOUT_TIMBER_ROLE, TURNOUT_SUBTYPE_TIMBER,
            "{} C10 REA Timber Outlines".format(identifier),
            "RailwayTurnoutTimberOutlines", timber_shape,
        )
        timber_centre_obj = _turnout_update_optional_geometry_object(
            doc, group, roles.get(TURNOUT_TIMBER_CENTRE_ROLE), identifier, set_id, route_id, route_name,
            track_number, number, config, TURNOUT_TIMBER_CENTRE_ROLE, TURNOUT_SUBTYPE_TIMBER_CENTRE,
            "{} C10 Timber Centre Lines".format(identifier),
            "RailwayTurnoutTimberCentres", timber_centre_shape,
        )
        timber_label_obj = _turnout_update_optional_geometry_object(
            doc, group, roles.get(TURNOUT_TIMBER_LABEL_ROLE), identifier, set_id, route_id, route_name,
            track_number, number, config, TURNOUT_TIMBER_LABEL_ROLE, TURNOUT_SUBTYPE_TIMBER_LABEL,
            "{} C10 Timber Identities and Lengths".format(identifier),
            "RailwayTurnoutTimberLabels", timber_label_shape,
        )
        datum_obj = _turnout_update_optional_geometry_object(
            doc, group, roles.get(TURNOUT_DATUM_ROLE), identifier, set_id, route_id, route_name,
            track_number, number, config, TURNOUT_DATUM_ROLE, TURNOUT_SUBTYPE_DATUM,
            "{} C10 Construction Datums".format(identifier),
            "RailwayTurnoutConstructionMarks", datum_shape,
        )

        _turnout_apply_display_style(
            solid_obj,
            outline_obj,
            rail_obj,
            timber_obj,
            timber_centre_obj,
            timber_label_obj,
            datum_obj,
        )
        records = [
            _turnout_record(
                solid_obj, TURNOUT_TEMPLATE_ROLE, TURNOUT_SUBTYPE_TEMPLATE,
                EXPORT_CATEGORY_SOLID, TURNOUT_SELECTION_TEMPLATE_3D,
                config, combined_solid, number, template_thickness,
            ),
            _turnout_record(
                outline_obj, TURNOUT_OUTLINE_ROLE, TURNOUT_SUBTYPE_TEMPLATE,
                EXPORT_CATEGORY_CUTTING, TURNOUT_SELECTION_TEMPLATE_2D,
                config, combined_outline, number, template_thickness,
            ),
            _turnout_record(
                rail_obj, TURNOUT_RAIL_ROLE, TURNOUT_SUBTYPE_RAIL,
                EXPORT_CATEGORY_ENGRAVING, TURNOUT_SELECTION_ENGRAVING,
                config, rail_shape, number, template_thickness,
            ),
        ]
        _turnout_append_optional_record(
            records, timber_obj, TURNOUT_TIMBER_ROLE, TURNOUT_SUBTYPE_TIMBER,
            config, timber_shape, number, template_thickness,
        )
        _turnout_append_optional_record(
            records, timber_centre_obj, TURNOUT_TIMBER_CENTRE_ROLE, TURNOUT_SUBTYPE_TIMBER_CENTRE,
            config, timber_centre_shape, number, template_thickness,
        )
        _turnout_append_optional_record(
            records, timber_label_obj, TURNOUT_TIMBER_LABEL_ROLE, TURNOUT_SUBTYPE_TIMBER_LABEL,
            config, timber_label_shape, number, template_thickness,
        )
        _turnout_append_optional_record(
            records, datum_obj, TURNOUT_DATUM_ROLE, TURNOUT_SUBTYPE_DATUM,
            config, datum_shape, number, template_thickness,
        )
        _turnout_store_production_records(
            doc,
            set_id,
            records,
            removed_source_names=old_source_names,
        )
        _turnout_store_catalogue(doc, set_id)
        _document_recompute(doc)
        doc.commitTransaction()
        transaction_open = False
    except Exception:
        if transaction_open:
            try:
                doc.abortTransaction()
            except Exception:
                pass
        raise
    return config


def _turnout_shape_has_material(shape):
    if shape is None or _shape_is_null(shape):
        return False
    try:
        if float(getattr(shape, "Volume", 0.0)) > GEOMETRY_TOLERANCE:
            return True
    except Exception:
        pass
    try:
        return bool(getattr(shape, "Solids", []))
    except Exception:
        return True


def _turnout_shape_common(shape_a, shape_b, description):
    try:
        common = _refine_shape(shape_a.common(shape_b))
    except Exception as error:
        raise ValueError("FreeCAD could not intersect {}: {}".format(description, error))
    return common


def _turnout_shape_cut(shape_a, shape_b, description, allow_empty=False):
    try:
        result = _refine_shape(shape_a.cut(shape_b))
    except Exception as error:
        raise ValueError("FreeCAD could not cut {}: {}".format(description, error))
    if result is None or _shape_is_null(result):
        if allow_empty:
            return None
        raise ValueError("Cutting {} removed the complete source shape.".format(description))
    return result


def _turnout_shape_fuse(shape_a, shape_b, description):
    if shape_a is None or _shape_is_null(shape_a):
        if shape_b is None or _shape_is_null(shape_b):
            raise ValueError("FreeCAD produced an empty {}.".format(description))
        return shape_b.copy()
    if shape_b is None or _shape_is_null(shape_b):
        return shape_a.copy()
    try:
        result = _refine_shape(shape_a.fuse(shape_b))
    except Exception as error:
        raise ValueError("FreeCAD could not fuse {}: {}".format(description, error))
    if result is None or _shape_is_null(result):
        raise ValueError("FreeCAD produced an empty {}.".format(description))
    return result


def _turnout_interval_samples(host_data, start_station, finish_station, spacing=TURNOUT_SAMPLE_SPACING):
    start = min(max(float(start_station), 0.0), host_data["total"])
    finish = min(max(float(finish_station), 0.0), host_data["total"])
    if finish < start:
        start, finish = finish, start
    if finish - start <= GEOMETRY_TOLERANCE:
        raise ValueError("A host-integration interval has no usable length.")
    count = max(1, int(math.ceil((finish - start) / max(float(spacing), 0.25))))
    stations = [start + ((finish - start) * index / float(count)) for index in range(count + 1)]
    points = []
    headings = []
    for station in stations:
        point, heading = interpolate_alignment_station(host_data, station)
        points.append(point)
        headings.append(heading)
    return points, headings


def _turnout_corridor_shape(host_data, start_station, finish_station, width, thickness):
    points, headings = _turnout_interval_samples(host_data, start_station, finish_station)
    face = create_template_plan_face(points, headings, max(float(width), 0.10))
    face.translate(App.Vector(0.0, 0.0, -TURNOUT_INTEGRATION_Z_CLEARANCE))
    solid = face.extrude(App.Vector(
        0.0,
        0.0,
        max(float(thickness), GEOMETRY_TOLERANCE) + (2.0 * TURNOUT_INTEGRATION_Z_CLEARANCE),
    ))
    solid = _refine_shape(solid)
    if solid.isNull():
        raise ValueError("FreeCAD could not create a host-integration corridor.")
    return solid


def _turnout_station_range_from_shape(host_data, shape):
    vertices = _shape_vertices(shape)
    if not vertices:
        raise ValueError("An affected host-template section has no vertices from which to recover its station range.")
    stations = []
    for vertex in vertices:
        try:
            stations.append(nearest_alignment_station(host_data, vertex.Point))
        except Exception:
            pass
    if not stations:
        raise ValueError("The affected section could not be projected onto its host centreline.")
    start = max(0.0, min(stations) - TURNOUT_INTEGRATION_CLEARANCE)
    finish = min(host_data["total"], max(stations) + TURNOUT_INTEGRATION_CLEARANCE)
    if finish - start <= GEOMETRY_TOLERANCE:
        raise ValueError("The affected section projects to a zero-length host interval.")
    return start, finish


def _turnout_host_template_sources(doc, config):
    set_id = str(config.get("template_set_id") or "")
    route_id = str(config.get("route_id") or "")
    track_number = int(config.get("track_number") or 0)
    unsplit = []
    sections = []
    for obj in list(doc.Objects):
        if object_string_property(obj, "GeneratedBy", "") != GENERATOR_ID:
            continue
        if object_string_property(obj, "TemplateSetID", "") != set_id:
            continue
        role = object_string_property(obj, "GeneratedRole", "")
        object_route = object_string_property(obj, "RouteID", "")
        object_track = _integer_object_property(obj, "TrackNumber", 0)
        if route_id:
            if object_route != route_id:
                continue
            if object_track not in (0, track_number):
                continue
            if role == "StraightTrackTemplate":
                unsplit.append(obj)
            elif role == "StraightTrackTemplateSection":
                sections.append(obj)
        else:
            if object_route:
                continue
            if role == "Template":
                unsplit.append(obj)
            elif role == "TrackTemplateSection":
                sections.append(obj)
    sections.sort(key=lambda item: (_integer_object_property(item, "SectionNumber", 0), str(item.Name)))
    return unsplit, sections


def _turnout_visibility_state(obj):
    if Gui is None or obj is None:
        return None
    try:
        return bool(obj.ViewObject.Visibility)
    except Exception:
        return None


def _turnout_set_visibility(obj, visible):
    if Gui is None or obj is None or visible is None:
        return
    try:
        obj.ViewObject.Visibility = bool(visible)
    except Exception:
        pass


def _turnout_integration_objects(doc, turnout_id):
    identifier = str(turnout_id or "").strip()
    result = []
    for obj in list(doc.Objects):
        if object_string_property(obj, TURNOUT_ID_PROPERTY, "") != identifier:
            continue
        role = object_string_property(obj, "GeneratedRole", "")
        if role in (
            TURNOUT_INTEGRATION_GROUP_ROLE,
            TURNOUT_INTEGRATION_SETTINGS_ROLE,
            TURNOUT_INTEGRATED_DISPLAY_ROLE,
            TURNOUT_INTEGRATED_TEMPLATE_ROLE,
            TURNOUT_INTEGRATED_OUTLINE_ROLE,
        ):
            result.append(obj)
    return result


def turnout_integration_by_id(doc, turnout_id):
    for obj in _turnout_integration_objects(doc, turnout_id):
        if object_string_property(obj, "GeneratedRole", "") != TURNOUT_INTEGRATION_SETTINGS_ROLE:
            continue
        stored = object_string_property(obj, TURNOUT_INTEGRATION_PROPERTY, "")
        try:
            config = json.loads(stored)
        except Exception:
            return None
        return config if isinstance(config, dict) else None
    return None


def _turnout_record_metadata_copy(record):
    copied = dict(record or {})
    copied.pop("shape", None)
    copied.pop("hydration_error", None)
    copied.pop("hydration_repair", None)
    return copied


def _turnout_write_production_records(doc, set_id, records):
    assign_production_record_ids(records, set_id)
    tag_production_record_bindings(doc, set_id, records)
    index_payload = build_production_record_index(records, set_id)
    settings = settings_for_template_set(doc, set_id)
    if settings is None:
        raise ValueError("The selected template set has no persistent settings object.")
    prop = ensure_property(
        settings,
        "App::PropertyString",
        PRODUCTION_RECORD_INDEX_PROPERTY,
        "Production utilities",
        "Persistent one-record production catalogue",
    )
    setattr(settings, PRODUCTION_RECORD_INDEX_PROPERTY, json.dumps(index_payload, sort_keys=True))
    set_read_only(settings, [prop])
    return index_payload


def _turnout_integration_record_from_original(original, obj, shape):
    record = dict(original)
    record["source_name"] = str(obj.Name)
    record["source_label"] = str(getattr(obj, "Label", obj.Name))
    record["source_binding_type"] = "direct"
    record["shape"] = shape.copy()
    record.pop("record_id", None)
    record.pop("diagnostic_status", None)
    record.pop("diagnostic_details", None)
    return record


def _turnout_add_integration_identity(obj, turnout_id, integration_config):
    properties = [
        ensure_property(obj, "App::PropertyString", TURNOUT_ID_PROPERTY, "Turnout identity", "Stable turnout identifier"),
        ensure_property(obj, "App::PropertyString", TURNOUT_INTEGRATION_PROPERTY, "Turnout integration", "Validated host-template integration configuration"),
    ]
    setattr(obj, TURNOUT_ID_PROPERTY, str(turnout_id))
    setattr(obj, TURNOUT_INTEGRATION_PROPERTY, json.dumps(integration_config, sort_keys=True))
    set_read_only(obj, properties)


def _turnout_add_integrated_feature(
    doc, group, turnout_id, set_id, route_id, route_name, track_number,
    role, label, stem, shape, subtype, category, section_number=0,
    travel_order_number=0, section_length=0.0,
):
    obj = doc.addObject(
        "Part::Feature",
        unique_internal_name(doc, "{}_{}".format(stem, turnout_id.replace('-', '_'))),
    )
    obj.Label = label
    obj.Shape = shape
    tag_generated_object(obj, role, set_id)
    tag_route_metadata(obj, route_id, route_name)
    tag_export_metadata(
        obj,
        subtype,
        category,
        track_number=track_number,
        section_number=section_number,
        travel_order_number=travel_order_number,
        section_length=section_length,
        feature_number=_turnout_number_from_identifier(turnout_id),
    )
    group.addObject(obj)
    return obj


def build_turnout_host_integration(doc, turnout_id):
    identifier = str(turnout_id or "").strip()
    if not identifier:
        raise ValueError("Select a turnout to integrate.")
    if turnout_integration_by_id(doc, identifier) is not None:
        raise ValueError("{} is already integrated into its host template.".format(identifier))
    turnout_config = turnout_config_by_id(doc, identifier)
    if turnout_config is None:
        raise ValueError("Turnout {} no longer exists in this document.".format(identifier))
    roles = _turnout_objects_by_role(doc, identifier)
    settings_obj = roles.get(TURNOUT_SETTINGS_ROLE)
    turnout_template_obj = roles.get(TURNOUT_TEMPLATE_ROLE)
    turnout_outline_obj = roles.get(TURNOUT_OUTLINE_ROLE)
    if settings_obj is None or turnout_template_obj is None or turnout_outline_obj is None:
        raise ValueError("{} is missing its settings, solid template or cutting footprint.".format(identifier))
    host_obj = doc.getObject(str(turnout_config.get("host_object") or ""))
    if host_obj is None or not is_turnout_host_centreline(host_obj):
        raise ValueError("The original host centreline for {} is no longer available.".format(identifier))

    built = _build_curve_inheriting_c10_turnout(
        doc,
        host_obj,
        float(turnout_config.get("toe_chainage", 0.0)),
        str(turnout_config.get("handing", TURNOUT_HAND_LEFT)),
        str(turnout_config.get("orientation", TURNOUT_ORIENTATION_FACING)),
        float(turnout_config.get("track_gauge", TURNOUT_DEFAULT_GAUGE)),
        float(turnout_config.get("flangeway", TURNOUT_DEFAULT_FLANGEWAY)),
        create_timber_references=bool(turnout_config.get("timber_outlines", turnout_config.get("timber_references", True))),
        create_timber_centres=bool(turnout_config.get("timber_centres", False)),
        create_timber_numbers=bool(turnout_config.get("timber_numbers", True)),
        create_timber_length_labels=bool(turnout_config.get("timber_length_labels", False)),
        create_construction_marks=bool(turnout_config.get("construction_marks", True)),
        turnout_id=identifier,
        ignored_turnout_id=identifier,
    )
    set_id = built["set_id"]
    route_id = built["route_id"]
    route_name = built["route_name"]
    track_number = built["track_number"]
    thickness = built["template_thickness"]
    width = built["template_width"]
    host_data = built["host_data"]
    combined_solid = built["solid_shape"]
    main_solid = built["main_solid_shape"]
    station_start, station_finish = turnout_host_station_interval(
        float(turnout_config["toe_chainage"]), built["dimensions"], str(turnout_config["orientation"])
    )
    cutter = _turnout_corridor_shape(
        host_data,
        max(0.0, station_start - TURNOUT_INTEGRATION_CLEARANCE),
        min(host_data["total"], station_finish + TURNOUT_INTEGRATION_CLEARANCE),
        width + (2.0 * TURNOUT_INTEGRATION_CLEARANCE),
        thickness,
    )
    full_track_corridor = _turnout_corridor_shape(
        host_data, 0.0, host_data["total"], width + (2.0 * TURNOUT_INTEGRATION_CLEARANCE), thickness
    )
    unsplit_sources, section_sources = _turnout_host_template_sources(doc, turnout_config)
    if not unsplit_sources and not section_sources:
        raise ValueError("No matching host-template solid or section objects were found for {}.".format(identifier))

    source_visibility = {}
    output_specs = []
    affected_sections = []

    # Full-template integrations are retained as a clean visual/reference assembly.
    for source in unsplit_sources:
        source_shape = getattr(source, "Shape", None)
        if _shape_is_null(source_shape):
            continue
        integrated = _turnout_shape_fuse(
            _turnout_shape_cut(source_shape.copy(), cutter, str(getattr(source, "Label", source.Name))),
            combined_solid,
            "integrated full host template",
        )
        outline = plan_profile_from_shape(integrated)
        if outline is None or _shape_is_null(outline):
            raise ValueError("FreeCAD could not derive the integrated full-template cutting profile.")
        output_specs.append({
            "source": source,
            "kind": "unsplit",
            "section_number": 0,
            "section_length": float(turnout_config.get("host_length") or host_data["total"]),
            "display_shape": integrated,
            "production_shape": integrated,
            "outline_shape": outline,
        })
        source_visibility[str(source.Name)] = _turnout_visibility_state(source)

    # Section replacements preserve all other tracks in the visible section while
    # production records contain only the selected host track plus its turnout branch.
    for source in section_sources:
        source_shape = getattr(source, "Shape", None)
        if _shape_is_null(source_shape):
            continue
        selected_track_piece = _turnout_shape_common(source_shape, full_track_corridor, "the host track and section {}".format(source.Name))
        module_intersection = _turnout_shape_common(selected_track_piece, main_solid, "the turnout interval and section {}".format(source.Name))
        if not _turnout_shape_has_material(module_intersection):
            continue
        section_start, section_finish = _turnout_station_range_from_shape(host_data, selected_track_piece)
        branch_clip = _turnout_corridor_shape(
            host_data,
            section_start,
            section_finish,
            TURNOUT_INTEGRATION_BRANCH_CLIP_WIDTH,
            thickness,
        )
        turnout_piece = _turnout_shape_common(combined_solid, branch_clip, "the turnout and affected section {}".format(source.Name))
        if not _turnout_shape_has_material(turnout_piece):
            raise ValueError("The turnout did not produce geometry inside affected section {}.".format(source.Name))
        production_shape = _turnout_shape_fuse(
            _turnout_shape_cut(selected_track_piece, cutter, "the selected host track in section {}".format(source.Name), allow_empty=True),
            turnout_piece,
            "integrated selected-track section {}".format(source.Name),
        )
        display_shape = _turnout_shape_fuse(
            _turnout_shape_cut(source_shape.copy(), cutter, "the displayed host section {}".format(source.Name), allow_empty=True),
            turnout_piece,
            "integrated displayed section {}".format(source.Name),
        )
        outline = plan_profile_from_shape(production_shape)
        if outline is None or _shape_is_null(outline):
            raise ValueError("FreeCAD could not derive the cutting profile for affected section {}.".format(source.Name))
        section_number = _integer_object_property(source, "SectionNumber", 0)
        section_length = quantity_value(source, "SectionLength", max(0.0, section_finish - section_start))
        output_specs.append({
            "source": source,
            "kind": "section",
            "section_number": section_number,
            "section_length": section_length,
            "host_station_start": section_start,
            "host_station_finish": section_finish,
            "display_shape": display_shape,
            "production_shape": production_shape,
            "outline_shape": outline,
        })
        affected_sections.append(section_number)
        source_visibility[str(source.Name)] = _turnout_visibility_state(source)

    if not output_specs:
        raise ValueError("The turnout does not intersect any recognised host-template production shape.")
    if section_sources:
        affected_specs = [item for item in output_specs if item.get("kind") == "section"]
        if len(affected_specs) != 1:
            raise ValueError(
                "Host-template integration is blocked because {} spans {} existing template sections. "
                "The turnout itself remains valid at this chainage, but A8A5 will not flatten, overlap or silently replace established section joints and numbering. "
                "Leave it as a separate turnout module, move it wholly inside one section, or regenerate the host section plan around the turnout.".format(
                    identifier, len(affected_specs)
                )
            )
        affected_spec = affected_specs[0]
        if (
            float(affected_spec.get("host_station_start", 0.0)) > station_start + TURNOUT_INTEGRATION_CLEARANCE
            or float(affected_spec.get("host_station_finish", 0.0)) < station_finish - TURNOUT_INTEGRATION_CLEARANCE
        ):
            raise ValueError(
                "Host-template integration is blocked because the complete turnout replacement interval is not contained inside one existing section. "
                "No host object or production record has been changed."
            )

    settings = settings_for_template_set(doc, set_id)
    if settings is None:
        raise ValueError("The selected template set has no persistent production catalogue.")
    index_payload = read_production_record_index(settings)
    if not index_payload:
        raise ValueError("The selected template set has no production-record index to integrate safely.")
    current_records = hydrate_production_index_records(doc, index_payload)
    stored_by_id = {
        str(item.get("record_id") or ""): dict(item)
        for item in index_payload.get("records", [])
        if str(item.get("record_id") or "")
    }

    affected_section_set = set(number for number in affected_sections if number > 0)
    records_to_remove = []
    for record in current_records:
        subtype = str(record.get("subtype") or "")
        record_route = str(record.get("route_id") or "")
        record_track = int(record.get("track_number") or 0)
        record_section = int(record.get("section_number") or 0)
        feature_number = int(record.get("feature_number") or 0)
        remove = False
        if subtype == TURNOUT_SUBTYPE_TEMPLATE and feature_number == _turnout_number_from_identifier(identifier):
            remove = True
        elif affected_section_set and subtype == "TrackTemplateSection":
            remove = (
                record_track == track_number
                and record_section in affected_section_set
                and record_route == route_id
            )
        elif unsplit_sources and subtype == "TrackTemplateCompound":
            if route_id:
                remove = record_route == route_id and record_track in (0, track_number)
            else:
                remove = not record_route
        if remove:
            records_to_remove.append(record)
    if not records_to_remove:
        raise ValueError("No host-template production records matched the affected turnout interval.")
    removed_ids = {str(record.get("record_id") or "") for record in records_to_remove}
    original_record_metadata = [
        stored_by_id[record_id] for record_id in sorted(removed_ids) if record_id in stored_by_id
    ]

    return {
        "turnout_id": identifier,
        "turnout_config": turnout_config,
        "built": built,
        "set_id": set_id,
        "route_id": route_id,
        "route_name": route_name,
        "track_number": track_number,
        "template_thickness": thickness,
        "output_specs": output_specs,
        "affected_sections": sorted(affected_section_set),
        "source_visibility": source_visibility,
        "turnout_visibility": {
            str(turnout_template_obj.Name): _turnout_visibility_state(turnout_template_obj),
            str(turnout_outline_obj.Name): _turnout_visibility_state(turnout_outline_obj),
        },
        "removed_record_ids": sorted(removed_ids),
        "original_record_metadata": original_record_metadata,
        "current_records": current_records,
        "turnout_template_obj": turnout_template_obj,
        "turnout_outline_obj": turnout_outline_obj,
    }


def create_turnout_host_integration(doc, turnout_id):
    clear_chair_analysis_display(doc, "turnout", str(turnout_id or "").strip())
    prepared = build_turnout_host_integration(doc, turnout_id)
    identifier = prepared["turnout_id"]
    set_id = prepared["set_id"]
    route_id = prepared["route_id"]
    route_name = prepared["route_name"]
    track_number = prepared["track_number"]
    integration_config = {
        "schema_version": TURNOUT_INTEGRATION_SCHEMA_VERSION,
        "macro_version": MACRO_VERSION_NUMBER,
        "turnout_id": identifier,
        "template_set_id": set_id,
        "host_object": str(prepared["turnout_config"].get("host_object") or ""),
        "host_label": str(prepared["turnout_config"].get("host_label") or ""),
        "route_id": route_id,
        "route_name": route_name,
        "track_number": track_number,
        "affected_sections": list(prepared["affected_sections"]),
        "source_visibility": dict(prepared["source_visibility"]),
        "turnout_visibility": dict(prepared["turnout_visibility"]),
        "removed_record_ids": list(prepared["removed_record_ids"]),
        "original_record_metadata": list(prepared["original_record_metadata"]),
        "integration_object_names": [],
        "integrated_record_ids": [],
        "mode": "derived replacement geometry; original generated objects retained",
    }
    transaction_open = False
    try:
        doc.openTransaction("Integrate Version {} turnout {} into host template".format(MACRO_VERSION_NUMBER, identifier))
        transaction_open = True
        group = doc.addObject(
            "App::DocumentObjectGroup",
            unique_internal_name(doc, "RailwayTurnoutIntegration_{}".format(identifier.replace('-', '_'))),
        )
        group.Label = "{} Integrated Host Template [{}]".format(identifier, set_id)
        tag_generated_object(group, TURNOUT_INTEGRATION_GROUP_ROLE, set_id)
        parent_roles = _turnout_objects_by_role(doc, identifier)
        parent = parent_roles.get(TURNOUT_GROUP_ROLE) or _turnout_group_parent(doc, set_id)
        if parent is not None:
            parent.addObject(group)

        settings_obj = doc.addObject(
            "Part::Feature",
            unique_internal_name(doc, "RailwayTurnoutIntegrationSettings_{}".format(identifier.replace('-', '_'))),
        )
        settings_obj.Label = "{} Host Integration Settings".format(identifier)
        tag_generated_object(settings_obj, TURNOUT_INTEGRATION_SETTINGS_ROLE, set_id)
        group.addObject(settings_obj)

        created_names = [str(group.Name), str(settings_obj.Name)]
        new_records = []
        display_record_bindings = []
        original_by_key = {}
        for record in prepared["current_records"]:
            key = (
                str(record.get("subtype") or ""),
                str(record.get("category") or ""),
                int(record.get("section_number") or 0),
            )
            if str(record.get("record_id") or "") in set(prepared["removed_record_ids"]):
                original_by_key.setdefault(key, []).append(record)

        for output_index, spec in enumerate(prepared["output_specs"], 1):
            section_number = int(spec["section_number"] or 0)
            section_length = float(spec["section_length"] or 0.0)
            section_token = "S{:02d}".format(section_number) if section_number else "Complete"
            display_obj = _turnout_add_integrated_feature(
                doc, group, identifier, set_id, route_id, route_name, track_number,
                TURNOUT_INTEGRATED_DISPLAY_ROLE,
                "{} {} Integrated Host Display".format(identifier, section_token),
                "RailwayTurnoutIntegratedDisplay_{:02d}".format(output_index),
                spec["display_shape"],
                "TrackTemplateTurnoutIntegratedSection" if section_number else "TrackTemplateTurnoutIntegrated",
                EXPORT_CATEGORY_SOLID,
                section_number=section_number,
                travel_order_number=section_number,
                section_length=section_length,
            )
            production_obj = _turnout_add_integrated_feature(
                doc, group, identifier, set_id, route_id, route_name, track_number,
                TURNOUT_INTEGRATED_TEMPLATE_ROLE,
                "{} {} Integrated Turnout Template".format(identifier, section_token),
                "RailwayTurnoutIntegratedTemplate_{:02d}".format(output_index),
                spec["production_shape"],
                "TrackTemplateTurnoutIntegratedSection" if section_number else "TrackTemplateTurnoutIntegrated",
                EXPORT_CATEGORY_SOLID,
                section_number=section_number,
                travel_order_number=section_number,
                section_length=section_length,
            )
            outline_obj = _turnout_add_integrated_feature(
                doc, group, identifier, set_id, route_id, route_name, track_number,
                TURNOUT_INTEGRATED_OUTLINE_ROLE,
                "{} {} Integrated Cutting Profile".format(identifier, section_token),
                "RailwayTurnoutIntegratedOutline_{:02d}".format(output_index),
                spec["outline_shape"],
                "TrackTemplateTurnoutIntegratedSection" if section_number else "TrackTemplateTurnoutIntegrated",
                EXPORT_CATEGORY_CUTTING,
                section_number=section_number,
                travel_order_number=section_number,
                section_length=section_length,
            )
            created_names.extend([str(display_obj.Name), str(production_obj.Name), str(outline_obj.Name)])
            if Gui is not None:
                try:
                    display_obj.ViewObject.ShapeColor = (0.76, 0.82, 0.86)
                    inherited_visibility = prepared["source_visibility"].get(str(spec["source"].Name))
                    if inherited_visibility is not None:
                        display_obj.ViewObject.Visibility = bool(inherited_visibility)
                    production_obj.ViewObject.Visibility = False
                    outline_obj.ViewObject.Visibility = False
                except Exception:
                    pass

            subtype = "TrackTemplateSection" if section_number else "TrackTemplateCompound"
            solid_key = (subtype, EXPORT_CATEGORY_SOLID, section_number)
            cutting_key = (subtype, EXPORT_CATEGORY_CUTTING, section_number)
            solid_originals = original_by_key.get(solid_key, [])
            cutting_originals = original_by_key.get(cutting_key, [])
            spec_records = []
            if solid_originals:
                record = _turnout_integration_record_from_original(solid_originals[0], production_obj, spec["production_shape"])
                new_records.append(record)
                spec_records.append(record)
            if cutting_originals:
                record = _turnout_integration_record_from_original(cutting_originals[0], outline_obj, spec["outline_shape"])
                new_records.append(record)
                spec_records.append(record)
            display_record_bindings.append((display_obj, spec_records))

        if not new_records:
            raise ValueError("No replacement production records could be built from the host-template catalogue.")
        remaining_records = [
            record for record in prepared["current_records"]
            if str(record.get("record_id") or "") not in set(prepared["removed_record_ids"])
        ]
        combined_records = remaining_records + new_records
        _turnout_write_production_records(doc, set_id, combined_records)
        for display_obj, bound_records in display_record_bindings:
            record_ids = sorted({
                str(record.get("record_id") or "")
                for record in bound_records
                if str(record.get("record_id") or "")
            })
            if not record_ids:
                continue
            properties = [
                ensure_property(display_obj, "App::PropertyString", PRODUCTION_RECORD_ID_PROPERTY, "Production utilities", "Stable production-record identity when this object represents one record"),
                ensure_property(display_obj, "App::PropertyString", PRODUCTION_RECORD_IDS_PROPERTY, "Production utilities", "All production records represented by this integrated display object"),
            ]
            setattr(display_obj, PRODUCTION_RECORD_ID_PROPERTY, record_ids[0] if len(record_ids) == 1 else "")
            setattr(display_obj, PRODUCTION_RECORD_IDS_PROPERTY, json.dumps(record_ids))
            set_read_only(display_obj, properties)
        integration_config["integration_object_names"] = created_names
        integration_config["integrated_record_ids"] = [str(record.get("record_id") or "") for record in new_records]
        _turnout_add_integration_identity(group, identifier, integration_config)
        _turnout_add_integration_identity(settings_obj, identifier, integration_config)

        for source_name in prepared["source_visibility"]:
            _turnout_set_visibility(doc.getObject(source_name), False)
        _turnout_set_visibility(prepared["turnout_template_obj"], False)
        _turnout_set_visibility(prepared["turnout_outline_obj"], False)
        _document_recompute(doc)
        doc.commitTransaction()
        transaction_open = False
    except Exception:
        if transaction_open:
            try:
                doc.abortTransaction()
            except Exception:
                pass
        raise
    return integration_config


def remove_turnout_host_integration(doc, turnout_id):
    identifier = str(turnout_id or "").strip()
    clear_chair_analysis_display(doc, "turnout", identifier)
    integration = turnout_integration_by_id(doc, identifier)
    if integration is None:
        raise ValueError("{} has no host-template integration to remove.".format(identifier))
    set_id = str(integration.get("template_set_id") or "")
    settings = settings_for_template_set(doc, set_id)
    if settings is None:
        raise ValueError("The integrated template set no longer has a persistent settings object.")
    payload = read_production_record_index(settings)
    current_records = hydrate_production_index_records(doc, payload) if payload else []
    integration_names = set(str(name) for name in integration.get("integration_object_names", []))
    retained = [record for record in current_records if str(record.get("source_name") or "") not in integration_names]
    restored_payload = {"records": list(integration.get("original_record_metadata", []))}
    restored = hydrate_production_index_records(doc, restored_payload)
    missing = [record for record in restored if record.get("shape") is None]
    if missing:
        raise ValueError(
            "The original host production geometry for {} cannot be restored because {} source record(s) are missing.".format(
                identifier, len(missing)
            )
        )
    transaction_open = False
    try:
        doc.openTransaction("Remove Version {} turnout host integration {}".format(MACRO_VERSION_NUMBER, identifier))
        transaction_open = True
        _turnout_write_production_records(doc, set_id, retained + restored)
        for source_name, visible in dict(integration.get("source_visibility") or {}).items():
            _turnout_set_visibility(doc.getObject(source_name), visible)
        for source_name, visible in dict(integration.get("turnout_visibility") or {}).items():
            _turnout_set_visibility(doc.getObject(source_name), visible)
        group_names = []
        part_names = []
        for name in integration_names:
            obj = doc.getObject(name)
            if obj is None:
                continue
            if object_string_property(obj, "GeneratedRole", "") == TURNOUT_INTEGRATION_GROUP_ROLE:
                group_names.append(str(obj.Name))
            else:
                part_names.append(str(obj.Name))
        for name in part_names:
            if doc.getObject(name) is not None:
                doc.removeObject(name)
        for name in group_names:
            if doc.getObject(name) is not None:
                doc.removeObject(name)
        _document_recompute(doc)
        doc.commitTransaction()
        transaction_open = False
    except Exception:
        if transaction_open:
            try:
                doc.abortTransaction()
            except Exception:
                pass
        raise
    return identifier


def _next_turnout_reference_copy_id(doc):
    used = set()
    for obj in list(doc.Objects):
        value = object_string_property(obj, TURNOUT_REFERENCE_ID_PROPERTY, "")
        match = re.search(r"([0-9]+)$", value)
        if match:
            used.add(int(match.group(1)))
    number = 1
    while number in used:
        number += 1
    return "TO-REF-{:03d}".format(number)


def create_turnout_reference_copy(doc, turnout_id):
    identifier = str(turnout_id or "").strip()
    config = turnout_config_by_id(doc, identifier)
    if config is None:
        raise ValueError("Select an existing turnout to extract as a reference copy.")
    roles = _turnout_objects_by_role(doc, identifier)
    source_objects = []
    for role in (
        TURNOUT_TEMPLATE_ROLE,
        TURNOUT_OUTLINE_ROLE,
        TURNOUT_RAIL_ROLE,
        TURNOUT_TIMBER_ROLE,
        TURNOUT_TIMBER_CENTRE_ROLE,
        TURNOUT_TIMBER_LABEL_ROLE,
        TURNOUT_DATUM_ROLE,
    ):
        obj = roles.get(role)
        if obj is not None and not _shape_is_null(getattr(obj, "Shape", None)):
            source_objects.append((role, obj))
    if not source_objects:
        raise ValueError("{} has no geometry available for a reference copy.".format(identifier))
    copy_id = _next_turnout_reference_copy_id(doc)
    set_id = str(config.get("template_set_id") or "")
    transaction_open = False
    try:
        doc.openTransaction("Extract Version {} turnout reference {}".format(MACRO_VERSION_NUMBER, identifier))
        transaction_open = True
        group = doc.addObject(
            "App::DocumentObjectGroup",
            unique_internal_name(doc, "RailwayTurnoutReference_{}".format(copy_id.replace('-', '_'))),
        )
        group.Label = "{} Reference Copy of {}".format(copy_id, identifier)
        tag_generated_object(group, TURNOUT_REFERENCE_GROUP_ROLE, set_id)
        parent = _turnout_group_parent(doc, set_id)
        if parent is not None:
            parent.addObject(group)
        properties = [
            ensure_property(group, "App::PropertyString", TURNOUT_REFERENCE_ID_PROPERTY, "Reference copy", "Stable reference-copy identifier"),
            ensure_property(group, "App::PropertyString", TURNOUT_REFERENCE_SOURCE_PROPERTY, "Reference copy", "Source turnout identifier"),
            ensure_property(group, "App::PropertyString", TURNOUT_CONFIGURATION_PROPERTY, "Reference copy", "Snapshot of the source turnout configuration"),
        ]
        setattr(group, TURNOUT_REFERENCE_ID_PROPERTY, copy_id)
        setattr(group, TURNOUT_REFERENCE_SOURCE_PROPERTY, identifier)
        setattr(group, TURNOUT_CONFIGURATION_PROPERTY, json.dumps(config, sort_keys=True))
        set_read_only(group, properties)
        created = []
        for index, (source_role, source_obj) in enumerate(source_objects, 1):
            obj = doc.addObject(
                "Part::Feature",
                unique_internal_name(doc, "RailwayTurnoutReferenceObject_{}_{:02d}".format(copy_id.replace('-', '_'), index)),
            )
            obj.Label = "{} - {}".format(copy_id, str(getattr(source_obj, "Label", source_obj.Name)))
            obj.Shape = source_obj.Shape.copy()
            tag_generated_object(obj, TURNOUT_REFERENCE_OBJECT_ROLE, set_id)
            props = [
                ensure_property(obj, "App::PropertyString", TURNOUT_REFERENCE_ID_PROPERTY, "Reference copy", "Stable reference-copy identifier"),
                ensure_property(obj, "App::PropertyString", TURNOUT_REFERENCE_SOURCE_PROPERTY, "Reference copy", "Source turnout identifier"),
                ensure_property(obj, "App::PropertyString", "ReferenceSourceRole", "Reference copy", "Source turnout geometry role"),
            ]
            setattr(obj, TURNOUT_REFERENCE_ID_PROPERTY, copy_id)
            setattr(obj, TURNOUT_REFERENCE_SOURCE_PROPERTY, identifier)
            obj.ReferenceSourceRole = source_role
            set_read_only(obj, props)
            group.addObject(obj)
            created.append(str(obj.Name))
            if Gui is not None:
                try:
                    obj.ViewObject.ShapeColor = source_obj.ViewObject.ShapeColor
                    obj.ViewObject.LineColor = source_obj.ViewObject.LineColor
                    obj.ViewObject.LineWidth = source_obj.ViewObject.LineWidth
                except Exception:
                    pass
        _document_recompute(doc)
        doc.commitTransaction()
        transaction_open = False
    except Exception:
        if transaction_open:
            try:
                doc.abortTransaction()
            except Exception:
                pass
        raise
    return {"reference_id": copy_id, "source_turnout_id": identifier, "object_names": created}


def remove_curve_inheriting_turnout(doc, turnout_id):
    identifier = str(turnout_id or "").strip()
    if not identifier:
        raise ValueError("Select a turnout to remove.")
    if turnout_integration_by_id(doc, identifier) is not None:
        raise ValueError("Remove the host-template integration before removing {} so the original host production records can be restored first.".format(identifier))
    objects = [
        obj for obj in list(doc.Objects)
        if object_string_property(obj, TURNOUT_ID_PROPERTY, "") == identifier
    ]
    if not objects:
        raise ValueError("Turnout {} no longer exists in this document.".format(identifier))
    set_ids = {object_string_property(obj, "TemplateSetID", "") for obj in objects}
    set_ids.discard("")
    if len(set_ids) != 1:
        raise ValueError("The selected turnout has inconsistent template-set metadata.")
    set_id = next(iter(set_ids))
    source_names = {
        str(obj.Name) for obj in objects
        if object_string_property(obj, "GeneratedRole", "") not in (TURNOUT_GROUP_ROLE, TURNOUT_SETTINGS_ROLE)
    }
    group_names = [str(obj.Name) for obj in objects if object_string_property(obj, "GeneratedRole", "") == TURNOUT_GROUP_ROLE]
    part_names = [str(obj.Name) for obj in objects if str(obj.Name) not in group_names]
    transaction_open = False
    try:
        doc.openTransaction("Remove Version {} turnout {}".format(MACRO_VERSION_NUMBER, identifier))
        transaction_open = True
        for name in part_names:
            if doc.getObject(name) is not None:
                doc.removeObject(name)
        for name in group_names:
            if doc.getObject(name) is not None:
                doc.removeObject(name)
        _turnout_store_production_records(doc, set_id, [], removed_source_names=source_names)
        _turnout_store_catalogue(doc, set_id)
        _document_recompute(doc)
        doc.commitTransaction()
        transaction_open = False
    except Exception:
        if transaction_open:
            try:
                doc.abortTransaction()
            except Exception:
                pass
        raise
    return identifier


def existing_turnout_configs(doc):
    entries = []
    for obj in list(doc.Objects):
        if object_string_property(obj, "GeneratedRole", "") != TURNOUT_SETTINGS_ROLE:
            continue
        stored = object_string_property(obj, TURNOUT_CONFIGURATION_PROPERTY, "")
        try:
            config = json.loads(stored)
        except Exception:
            config = {}
        if isinstance(config, dict) and config.get("turnout_id"):
            entries.append(config)
    return sorted(entries, key=lambda item: str(item.get("turnout_id") or ""))


# Stage 8A6A managed-crossover geometry. This first controlled stage creates
# and validates two source-driven natural REA C10 turnouts plus a solved G1
# connecting road. Independent turnout timbering is retained as a clearly
# marked reference only; automatic crossover timber resolution and host
# integration remain deliberately blocked until A8A6B.
CROSSOVER_SCHEMA_VERSION = 1
CROSSOVER_CATALOGUE_PROPERTY = "CrossoverConfigurationsJSON"
CROSSOVER_CONFIGURATION_PROPERTY = "CrossoverConfigurationJSON"
CROSSOVER_ID_PROPERTY = "CrossoverID"
CROSSOVER_GROUP_ROLE = "CrossoverGroup"
CROSSOVER_SETTINGS_ROLE = "CrossoverSettings"
CROSSOVER_TEMPLATE_ROLE = "CrossoverTemplate"
CROSSOVER_OUTLINE_ROLE = "CrossoverPlanOutline"
CROSSOVER_RAIL_ROLE = "CrossoverRailGeometry"
CROSSOVER_TIMBER_REFERENCE_ROLE = "CrossoverUnresolvedTimberReference"
CROSSOVER_DATUM_ROLE = "CrossoverConstructionMarks"
CROSSOVER_TURNOUT_A_SETTINGS_ROLE = "CrossoverTurnoutASettings"
CROSSOVER_TURNOUT_B_SETTINGS_ROLE = "CrossoverTurnoutBSettings"
CROSSOVER_SUBTYPE_TEMPLATE = "TrackTemplateCrossover"
CROSSOVER_SUBTYPE_RAIL = "CrossoverRailGeometry"
CROSSOVER_SUBTYPE_TIMBER_REFERENCE = "CrossoverUnresolvedTimberReference"
CROSSOVER_SUBTYPE_DATUM = "CrossoverConstructionMarks"
CROSSOVER_ARRANGEMENT_FACING = "Facing crossover"
CROSSOVER_ARRANGEMENT_TRAILING = "Trailing crossover"
CROSSOVER_HAND_AUTO = "Automatic handing"
CROSSOVER_REVERSION_SIDE_A = "A"
CROSSOVER_REVERSION_SIDE_B = "B"
CROSSOVER_OUTPUT_GEOMETRY = "A8A6A geometry module"
CROSSOVER_DEFAULT_MINIMUM_RADIUS = 600.0
CROSSOVER_MINIMUM_ALLOWED_RADIUS = 50.0
CROSSOVER_MAXIMUM_TRACK_SEPARATION = 500.0
CROSSOVER_CONNECTOR_SAMPLE_SPACING = 1.0
CROSSOVER_CONNECTOR_MAX_SWEEP = math.radians(170.0)
CROSSOVER_CONNECTOR_MAX_TOTAL_SWEEP = math.radians(180.0)
CROSSOVER_CONNECTOR_MAX_LENGTH_RATIO = 2.25
CROSSOVER_CONNECTOR_BACKTRACK_FRACTION = 0.25
CROSSOVER_CONNECTOR_BACKTRACK_MINIMUM = 2.0
CROSSOVER_BIARC_RATIO_LEVELS = 6
CROSSOVER_BIARC_RATIO_REFINEMENT_ITERATIONS = 3
CROSSOVER_BIARC_RATIO_REFINEMENT_SEEDS = 3
CROSSOVER_BEZIER_CONTROL_FACTORS = (0.125, 0.25, 0.50, 0.80, 1.25, 2.00)
CROSSOVER_BEZIER_REFINEMENT_ITERATIONS = 2
CROSSOVER_BEZIER_REFINEMENT_SEEDS = 3
CROSSOVER_BEZIER_SAMPLE_SPACING = 0.50
CROSSOVER_CSC_RADIUS_FACTORS = (1.0, 1.25, 1.50, 2.00)
CROSSOVER_CSC_PATH_TYPES = ("LSL", "RSR", "LSR", "RSL")
CROSSOVER_CSC_REFINEMENT_ITERATIONS = 3
CROSSOVER_CSC_REFINEMENT_SEEDS = 2
CROSSOVER_CUBIC_FALLBACK_TOE_LIMIT = 12
CROSSOVER_SOLVER_TRACE_CANDIDATE_LIMIT = 12
CROSSOVER_REFINEMENT_SEED_COUNT = 4
CROSSOVER_REFINEMENT_ITERATIONS = 8
CROSSOVER_POSITION_TOLERANCE = 1.0e-5
CROSSOVER_TANGENT_TOLERANCE = math.radians(0.05)
CROSSOVER_TOPOLOGY_DIRECTION_DOT = 0.01
CROSSOVER_TOPOLOGY_TANGENT_DOT = math.cos(math.radians(1.0))
CROSSOVER_TOPOLOGY_SWITCH_CLEARANCE_GAUGE_FACTOR = 0.45
CROSSOVER_TOPOLOGY_CORRIDOR_SEPARATION_FACTOR = 3.0
CROSSOVER_TOPOLOGY_CORRIDOR_GAUGE_FACTOR = 4.0
CROSSOVER_SOURCE_NOTE = (
    "Natural REA C10 turnout geometry reused from the A8A5 engine; ordinary-"
    "crossover pairing cross-checked against Templot5 revision 556b "
    "math_unit.pas make_crossover and TXP calculations"
)
CROSSOVER_TIMBER_STATUS_UNRESOLVED = (
    "A8A6A reference only: two independent turnout timber arrangements; "
    "automatic shared/interlaced/shoved crossover timbering is not yet resolved"
)


# A8A6B1 timber-analysis metadata, tolerances and lightweight display roles.
# The geometry and support positions are source-derived. The default clearances
# are explicit OO manufacturing assumptions and remain configurable.
CROSSOVER_TIMBER_ANALYSIS_SCHEMA_VERSION = 1
CROSSOVER_TIMBER_ANALYSIS_STATUS_PROPERTY = "CrossoverTimberAnalysisStatus"
CROSSOVER_TIMBER_ANALYSIS_SIGNATURE_PROPERTY = "CrossoverTimberAnalysisSignature"
CROSSOVER_TIMBER_ANALYSIS_SETTINGS_PROPERTY = "CrossoverTimberAnalysisSettingsJSON"
CROSSOVER_TIMBER_ANALYSIS_RESULT_PROPERTY = "CrossoverTimberAnalysisResultJSON"
CROSSOVER_TIMBER_ANALYSIS_GROUP_ROLE = "CrossoverTimberAnalysisDisplay"
CROSSOVER_TIMBER_CONFLICT_MARKER_ROLE = "CrossoverTimberConflictMarker"
CROSSOVER_TIMBER_SUPPORT_MARKER_ROLE = "CrossoverProtectedSupportMarker"
CROSSOVER_TIMBER_ANALYSIS_STATUS_NOT_ANALYSED = "Not analysed"
CROSSOVER_TIMBER_ANALYSIS_STATUS_CLEAR = "Analysed — no critical conflicts"
CROSSOVER_TIMBER_ANALYSIS_STATUS_CONFLICTS = "Analysed — conflicts present"
CROSSOVER_TIMBER_ANALYSIS_STATUS_CRITICAL = "Analysed — production-critical conflicts"
CROSSOVER_TIMBER_ANALYSIS_STATUS_STALE = "Analysis stale"
CROSSOVER_TIMBER_SEVERITY_INFORMATION = "Informational"
CROSSOVER_TIMBER_SEVERITY_ADVISORY = "Advisory"
CROSSOVER_TIMBER_SEVERITY_PRODUCTION_CONFLICT = "Production conflict"
CROSSOVER_TIMBER_SEVERITY_PRODUCTION_CRITICAL = "Production-critical conflict"
CROSSOVER_TIMBER_INTERSECTION_TOLERANCE = 0.05
CROSSOVER_TIMBER_NEAR_TOUCHING_TOLERANCE = 0.30
CROSSOVER_TIMBER_MINIMUM_CLEAR_SPACING = 0.50
CROSSOVER_TIMBER_SAME_STATION_TOLERANCE = 0.50
CROSSOVER_TIMBER_MAXIMUM_ADVISORY_SKEW_DEGREES = 3.0
CROSSOVER_TIMBER_ANALYSIS_SOURCE_BASIS = (
    "Templot5 revision 556b switch_select.pas switch_info timber_centres and REA switch chair-count records",
    "Templot5 revision 556b math_unit.pas switchtimbers procedure and bn_to_a, wingj_sp, mvj_sp, wingtimb_sp and wing_spco constants",
    "Templot5 revision 556b math_unit.pas make_crossover geometry pairing",
    "Templot5 revision 556b shove_timber.pas shove/omit/length workflow and long crossover timber guidance",
    "Templot5 revision 556b chairs_unit.pas REA switch, crossing, wing and check-rail chair families",
)
CROSSOVER_TIMBER_ANALYSIS_ENGINEERING_ASSUMPTIONS = (
    "0.05 mm polygon-intersection tolerance at model scale",
    "0.30 mm near-touching tolerance at model scale",
    "0.50 mm minimum clear timber spacing at model scale",
    "0.50 mm same longitudinal-position tolerance projected along Host A travel",
    "3 degree advisory skew limit relative to the local rail formation",
    "rail-foot and chair-envelope intrusion deferred until A8A7 provides reliable chair envelopes",
)


# A8A6B2 shared long-timber resolution.  Version 10.2A8A6B2A2 retains
# compatible inherited A/B pair replacement and adds a continuous crossover-
# road timbering envelope.  The envelope is numeric and read-only regarding
# host production geometry: it creates preview records only, never shoves,
# omits, interlaces or edits an inherited timber or a host-track sleeper.
CROSSOVER_SHARED_TIMBER_SCHEMA_VERSION = 3
CROSSOVER_SHARED_TIMBER_SETTINGS_PROPERTY = "CrossoverSharedTimberSettingsJSON"
CROSSOVER_SHARED_TIMBER_RESULT_PROPERTY = "CrossoverSharedTimberResultJSON"
CROSSOVER_SHARED_TIMBER_STATUS_PROPERTY = "CrossoverSharedTimberStatus"
CROSSOVER_SHARED_TIMBER_SIGNATURE_PROPERTY = "CrossoverSharedTimberSignature"
CROSSOVER_SHARED_TIMBER_ROLE = "CrossoverSharedLongTimberGeometry"
CROSSOVER_SHARED_TIMBER_SUBTYPE = "CrossoverSharedLongTimberGeometry"
CROSSOVER_SHARED_TIMBER_STATUS_NOT_APPLIED = "Not applied"
CROSSOVER_SHARED_TIMBER_STATUS_APPLIED = "Shared timber envelope applied"
CROSSOVER_SHARED_TIMBER_STATUS_PARTIAL = "Shared timber envelope applied — further timber resolution required"
CROSSOVER_SHARED_TIMBER_STATUS_CONFLICTS = "Shared timber envelope applied — timber conflicts remain"
CROSSOVER_SHARED_TIMBER_STATUS_REQUIRES_B3 = "Shared timber envelope applied — some positions require interlacing or controlled shoving"
CROSSOVER_SHARED_TIMBER_STATUS_RETURN_UNCONFIRMED = "Shared timber envelope applied — plain-track return not confirmed"
CROSSOVER_SHARED_TIMBER_STATUS_CLEAR = "Shared timber envelope applied — no production conflicts detected"
CROSSOVER_SHARED_TIMBER_STATUS_STALE = "Shared timber envelope stale"
CROSSOVER_SHARED_TIMBER_MAX_STATION_OFFSET = 1.00
CROSSOVER_SHARED_TIMBER_MAX_ANGLE_DIFFERENCE_DEGREES = 2.00
CROSSOVER_SHARED_TIMBER_MAX_WIDTH_EXPANSION = 0.35
CROSSOVER_SHARED_TIMBER_END_ALLOWANCE = 0.00
CROSSOVER_SHARED_TIMBER_MAXIMUM_LENGTH = 0.0
CROSSOVER_SHARED_TIMBER_COLLISION_TOLERANCE = 0.05
CROSSOVER_SHARED_TIMBER_ENVELOPE_SPACING_PROTOTYPE_INCHES = 30.0
CROSSOVER_SHARED_TIMBER_ENVELOPE_CLEARANCE = 0.50
CROSSOVER_SHARED_TIMBER_ENVELOPE_ALLOWANCE = 1.00
CROSSOVER_SHARED_TIMBER_ENVELOPE_RETURN_CONFIRMATION = 3
CROSSOVER_SHARED_TIMBER_ENVELOPE_MAXIMUM_SKEW_DEGREES = 12.0
CROSSOVER_SHARED_TIMBER_TARGET_CODES = (
    "timber_body_intersection",
    "timber_fully_covers_another",
    "duplicate_conflicting_support",
    "near_touching_timber_ends",
    "inadequate_facing_end_clearance",
    "insufficient_side_to_side_spacing",
    "effectively_same_longitudinal_station",
)
CROSSOVER_SHARED_TIMBER_SOURCE_BASIS = (
    "Templot5 revision 556b shove_timber.pas retains independent end extensions and timber length changes as explicit shove data",
    "Templot5 revision 556b math_unit.pas switchtimbers and crossing timber spacing establish the protected source timber positions",
    "Templot5 revision 556b make_crossover leaves overlapping crossover timbering for subsequent timber-shoving work",
    "Templot5 revision 556b closure timber fitting uses a whole number of equal spaces not exceeding the normal maximum spacing",
    "Existing A8A6B1 oriented timber records and protected support zones are the geometric authority for inherited shared-timber eligibility",
    "The Main template width inherited by each turnout is the nominal plain-track sleeper length used to determine the end of each shared-timber envelope",
)
CROSSOVER_SHARED_TIMBER_ENGINEERING_ASSUMPTIONS = (
    "1.00 mm maximum inherited longitudinal centre offset for an automatic inherited shared pair",
    "2.00 degree maximum angular difference for an automatic inherited shared pair",
    "0.35 mm maximum width expansion beyond the wider inherited timber",
    "0.05 mm maximum incidental collision area tolerance against unaffected timbers",
    "shared length is rounded upwards to the established six-prototype-inch timber increment",
    "connector sleeper positions are evenly fitted at no more than 30 prototype inches",
    "0.50 mm clear separation is required before two nominal plain-track sleeper footprints are treated as independent",
    "1.00 mm default long-timber envelope allowance extends borderline timbers conservatively beyond the physical clearance threshold",
    "three consecutive clear sleeper positions confirm a stable return to nominal plain-track timbering",
    "12 degrees is the default maximum shared-envelope skew relative to every supported route normal",
    "no automatic maximum long-timber length unless the user configures one",
    "exact host sleeper replacement and longitudinal-position reconciliation remain deferred to A8A6C host integration",
    "rail-foot and chair-envelope validation remains deferred until A8A7",
)


# A8A6B3 controlled interlacing and longitudinal timber shoving. This stage
# operates only on the current validated A8A6B2A2 effective arrangement. It
# preserves long timbers and connector sleepers, and modifies only unresolved
# inherited A/B timber positions. The calculations remain numeric; Part geometry
# is rebuilt once after the complete candidate sequence has been accepted.
CROSSOVER_B3_SCHEMA_VERSION = 1
CROSSOVER_B3_SETTINGS_PROPERTY = "CrossoverB3SettingsJSON"
CROSSOVER_B3_RESULT_PROPERTY = "CrossoverB3ResultJSON"
CROSSOVER_B3_STATUS_PROPERTY = "CrossoverB3Status"
CROSSOVER_B3_SIGNATURE_PROPERTY = "CrossoverB3Signature"
CROSSOVER_B3_ROLE = "CrossoverInterlacedShovedTimberGeometry"
CROSSOVER_B3_SUBTYPE = "CrossoverInterlacedShovedTimberGeometry"
CROSSOVER_B3_STATUS_NOT_APPLIED = "Not applied"
CROSSOVER_B3_STATUS_CLEAR = "Interlacing and timber movement applied — no production conflicts detected"
CROSSOVER_B3_STATUS_PARTIAL = "Interlacing and timber movement applied — unresolved timber positions remain"
CROSSOVER_B3_STATUS_CONFLICTS = "Interlacing and timber movement applied — production conflicts remain"
CROSSOVER_B3_STATUS_STALE = "Interlacing and timber movement result stale"
CROSSOVER_B3_MAXIMUM_MOVEMENT = 1.50
CROSSOVER_B3_MOVEMENT_INCREMENT = 0.25
CROSSOVER_B3_MINIMUM_CLEAR_SPACING = 0.50
CROSSOVER_B3_MAXIMUM_INTERLACING_SEPARATION = 3.00
CROSSOVER_B3_MAXIMUM_ANGLE_DIFFERENCE_DEGREES = 6.00
CROSSOVER_B3_PROTECTED_MOVEMENT_ALLOWANCE = 0.25
CROSSOVER_B3_COLLISION_TOLERANCE = 0.05
CROSSOVER_B3_TARGET_CODES = (
    "timber_body_intersection",
    "timber_fully_covers_another",
    "duplicate_conflicting_support",
    "near_touching_timber_ends",
    "inadequate_facing_end_clearance",
    "insufficient_side_to_side_spacing",
    "effectively_same_longitudinal_station",
)
CROSSOVER_B3_STRICT_PROTECTED_FEATURES = (
    "switch toe",
    "first slide-chair position",
    "switch heel",
    "common-crossing A timber",
    "common-crossing B timber",
    "vee-nose support",
    "crossing-nose support",
    "switch-front rail joint",
    "stock-rail joint support",
    "vee point-rail joint support",
    "exit rail-joint support",
)
CROSSOVER_B3_SOURCE_BASIS = (
    "Templot5 revision 556b shove_timber.pas provides precedent for individual forward/backward timber movement at crossover and junction conflicts; A8A6B3 deliberately excludes twisting",
    "Templot5 revision 556b shove_timber.pas documents long timbers across adjacent tracks and omission of the duplicate timber on the adjoining template",
    "Templot5 revision 556b shove_timber.pas uses one-prototype-inch movement steps and preserves explicit per-timber shove data",
    "Existing A8A6B1 oriented timber records and protected support identities are the geometric authority",
    "The current validated A8A6B2A2 effective arrangement is immutable input to B3 except for accepted inherited A/B longitudinal movements",
)
CROSSOVER_B3_ENGINEERING_ASSUMPTIONS = (
    "1.50 mm default maximum model-scale longitudinal movement for ordinary inherited timber positions",
    "0.25 mm default search increment; the first safe lowest-cost candidate is accepted",
    "0.50 mm minimum clear spacing after controlled shoving",
    "3.00 mm maximum total separation created by a symmetric interlacing operation",
    "6 degree maximum angular difference for automatic interlacing",
    "0.25 mm stricter movement allowance for protected switch, crossing and rail-joint positions",
    "the original protected support centre must remain inside every moved timber body",
    "shared long timbers and nominal connector sleepers are never moved by B3",
    "B3 does not shorten, omit, rotate, widen or invent timbers",
    "chair-fit validation remains deferred until A8A7 supplies reliable chair envelopes",
)


# A8A6B4 hybrid automatic resolver. This is a coordinating and validation
# layer over the source-identical B2A2 and B3 numeric engines. It creates one
# final preview object and never alters turnout rails, host tracks or production
# sleeper geometry.
CROSSOVER_B4_SCHEMA_VERSION = 1
CROSSOVER_B4_SETTINGS_PROPERTY = "CrossoverB4SettingsJSON"
CROSSOVER_B4_RESULT_PROPERTY = "CrossoverB4ResultJSON"
CROSSOVER_B4_STATUS_PROPERTY = "CrossoverB4Status"
CROSSOVER_B4_SIGNATURE_PROPERTY = "CrossoverB4Signature"
CROSSOVER_B4_ROLE = "CrossoverHybridResolvedTimberGeometry"
CROSSOVER_B4_SUBTYPE = "CrossoverHybridResolvedTimberGeometry"
CROSSOVER_B4_STATUS_NOT_APPLIED = "Not applied"
CROSSOVER_B4_STATUS_CLEAR = "Automatic timbering resolved — no production conflicts detected"
CROSSOVER_B4_STATUS_PARTIAL = "Automatic timbering applied — unresolved positions remain"
CROSSOVER_B4_STATUS_CONFLICTS = "Automatic timbering applied — production conflicts remain"
CROSSOVER_B4_STATUS_STALE = "Automatic timbering result stale"
CROSSOVER_B4_SOURCE_BASIS = (
    "The validated A8A6B2A2 complete shared-timber envelope is rebuilt in memory from inherited turnout timber records",
    "The validated A8A6B3 interlacing and minimum controlled-shove engine is applied only to unresolved eligible inherited A/B positions",
    "Templot5 revision 556b shove_timber.pas provides prototype precedent for long timbers, interlacing, omission and individual timber movement",
    "A8A6B1 oriented timber polygons and protected support zones remain the geometric authority",
)
CROSSOVER_B4_ENGINEERING_ASSUMPTIONS = (
    "B4 uses the currently configured B2A2 envelope and B3 movement tolerances without silently relaxing them",
    "the final arrangement is accepted only when it introduces no new production-critical finding",
    "shared long-timber orientation is assessed against every supported road normal",
    "unsafe or unsupported positions remain explicit and are never forced",
    "the result remains preview geometry pending A8A6C exact host integration and A8A7 chair validation",
)

# A8A6C reversible crossover editing and host-template integration.
CROSSOVER_INTEGRATION_SCHEMA_VERSION = 1
CROSSOVER_INTEGRATION_PROPERTY = "CrossoverHostIntegrationJSON"
CROSSOVER_INTEGRATION_STATUS_PROPERTY = "CrossoverHostIntegrationStatus"
CROSSOVER_INTEGRATION_SIGNATURE_PROPERTY = "CrossoverHostIntegrationSignature"
CROSSOVER_INTEGRATION_GROUP_ROLE = "CrossoverHostIntegrationGroup"
CROSSOVER_INTEGRATION_SETTINGS_ROLE = "CrossoverHostIntegrationSettings"
CROSSOVER_INTEGRATED_DISPLAY_ROLE = "CrossoverIntegratedHostDisplay"
CROSSOVER_INTEGRATED_TEMPLATE_ROLE = "CrossoverIntegratedHostTemplate"
CROSSOVER_INTEGRATED_OUTLINE_ROLE = "CrossoverIntegratedHostOutline"
CROSSOVER_INTEGRATED_TIMBER_ROLE = "CrossoverIntegratedResolvedTimberGeometry"
CROSSOVER_INTEGRATED_SUBTYPE = "TrackTemplateCrossoverIntegrated"
CROSSOVER_INTEGRATED_TIMBER_SUBTYPE = "CrossoverResolvedTimberGeometry"
CROSSOVER_INTEGRATION_STATUS_NOT_INTEGRATED = "Not integrated"
CROSSOVER_INTEGRATION_STATUS_READY = "Ready for host integration"
CROSSOVER_INTEGRATION_STATUS_ACTIVE = "Integrated with host templates — chair validation outstanding"
CROSSOVER_INTEGRATION_STATUS_STALE = "Host integration stale"
CROSSOVER_INTEGRATION_CLEARANCE = 0.15
CROSSOVER_INTEGRATION_Z_CLEARANCE = 0.20
CROSSOVER_INTEGRATION_BRANCH_CLIP_WIDTH = 1000.0
CROSSOVER_INTEGRATION_SOURCE_BASIS = (
    "the established reversible turnout host-integration production-record architecture",
    "the current automatically resolved crossover timber records and stable resolution signature",
    "the original host template section identities, route metadata and production catalogue",
)



def _crossover_xy(point):
    return float(point.x), float(point.y)


def _crossover_point(x, y):
    return vector_xy(float(x), float(y))


def _crossover_add(point_a, point_b):
    return _crossover_point(point_a.x + point_b.x, point_a.y + point_b.y)


def _crossover_subtract(point_a, point_b):
    return _crossover_point(point_a.x - point_b.x, point_a.y - point_b.y)


def _crossover_scale(point, factor):
    return _crossover_point(point.x * float(factor), point.y * float(factor))


def _crossover_dot(point_a, point_b):
    return float(point_a.x) * float(point_b.x) + float(point_a.y) * float(point_b.y)


def _crossover_cross(point_a, point_b):
    return float(point_a.x) * float(point_b.y) - float(point_a.y) * float(point_b.x)


def _crossover_length(point):
    return math.hypot(float(point.x), float(point.y))


def _crossover_unit(point, description="vector"):
    length = _crossover_length(point)
    if length <= 1.0e-12:
        raise ValueError("The {} has zero length.".format(description))
    return _crossover_scale(point, 1.0 / length)


def _crossover_heading_vector(heading):
    return _crossover_point(math.cos(float(heading)), math.sin(float(heading)))


def _crossover_left_normal_vector(vector):
    return _crossover_point(-float(vector.y), float(vector.x))


def _crossover_angle_difference(angle_a, angle_b):
    return abs((float(angle_a) - float(angle_b) + math.pi) % (2.0 * math.pi) - math.pi)


def _crossover_vector_angle(vector):
    return math.atan2(float(vector.y), float(vector.x))


def _crossover_polyline_length(points):
    return sum(_xy_distance(a, b) for a, b in zip(points[:-1], points[1:]))


def _crossover_remove_duplicate_points(points, tolerance=1.0e-7):
    clean = []
    for point in points:
        candidate = _crossover_point(point.x, point.y)
        if not clean or _xy_distance(clean[-1], candidate) > float(tolerance):
            clean.append(candidate)
    return clean


def _crossover_nearest_point_on_alignment(data, point):
    station = nearest_alignment_station(data, point)
    projected, heading = interpolate_alignment_station(data, station)
    return station, projected, heading, _xy_distance(projected, point)


def _crossover_host_travel_vector(host_data, station, orientation):
    _point, heading = interpolate_alignment_station(host_data, station)
    direction = _turnout_orientation_sign(orientation)
    if direction < 0.0:
        heading += math.pi
    return _crossover_heading_vector(heading)


def _crossover_branch_endpoint(host_data, toe_chainage, orientation, handing, dimensions):
    finish_x = float(dimensions["module_end_x"])
    local_point = _rea_c10_local_point(dimensions, finish_x, "turnout_centre")
    point = map_turnout_local_point(
        host_data, toe_chainage, orientation, handing, local_point[0], local_point[1]
    )
    delta_x = max(0.05, min(0.50, 0.002 * (float(dimensions["module_end_x"]) - float(dimensions["module_start_x"]))))
    previous_local = _rea_c10_local_point(dimensions, finish_x - delta_x, "turnout_centre")
    previous = map_turnout_local_point(
        host_data, toe_chainage, orientation, handing, previous_local[0], previous_local[1]
    )
    tangent = _crossover_unit(_crossover_subtract(point, previous), "turnout-road end tangent")
    return point, tangent



def _crossover_connection_tangent_context(endpoint_a, raw_tangent_a, endpoint_b, raw_tangent_b):
    """Prepare connector traversal tangents without discarding branch meaning.

    _crossover_branch_endpoint returns the physical outward tangent from each
    switch toe towards its diverging branch end.  Connector traversal runs from
    Turnout A to Turnout B, so its start tangent is Host A's outward tangent and
    its finish tangent is the reverse of Host B's outward tangent.  This is a
    semantic traversal conversion, not a free choice between two directions of
    an undirected tangent line.
    """
    chord = _crossover_subtract(endpoint_b, endpoint_a)
    chord_length = _crossover_length(chord)
    outward_a = _crossover_unit(raw_tangent_a, "Host A outward diverging-road tangent")
    outward_b = _crossover_unit(raw_tangent_b, "Host B outward diverging-road tangent")
    if chord_length <= CROSSOVER_POSITION_TOLERANCE:
        chord_unit = outward_a
    else:
        chord_unit = _crossover_scale(chord, 1.0 / chord_length)
    traversal_a = outward_a
    traversal_b = _crossover_scale(outward_b, -1.0)
    return {
        "chord": chord,
        "chord_length": chord_length,
        "chord_heading_degrees": math.degrees(_crossover_vector_angle(chord_unit)),
        "raw_tangent_a": outward_a,
        "raw_tangent_b": outward_b,
        "outward_tangent_a": outward_a,
        "outward_tangent_b": outward_b,
        "tangent_a": traversal_a,
        "tangent_b": traversal_b,
        "raw_start_heading_degrees": math.degrees(_crossover_vector_angle(outward_a)),
        "raw_finish_heading_degrees": math.degrees(_crossover_vector_angle(outward_b)),
        "outward_start_heading_degrees": math.degrees(_crossover_vector_angle(outward_a)),
        "outward_finish_heading_degrees": math.degrees(_crossover_vector_angle(outward_b)),
        "connection_start_heading_degrees": math.degrees(_crossover_vector_angle(traversal_a)),
        "connection_finish_heading_degrees": math.degrees(_crossover_vector_angle(traversal_b)),
        "start_tangent_reversed": False,
        "finish_tangent_reversed": True,
        "finish_reversal_reason": "connector traversal approaches Host B opposite to its outward branch direction",
        "raw_start_chord_dot": float(_crossover_dot(outward_a, chord_unit)),
        "raw_finish_chord_dot": float(_crossover_dot(outward_b, chord_unit)),
        "connection_start_chord_dot": float(_crossover_dot(traversal_a, chord_unit)),
        "connection_finish_chord_dot": float(_crossover_dot(traversal_b, chord_unit)),
        "endpoint_role_a": "Turnout A diverging branch end",
        "endpoint_role_b": "Turnout B diverging branch end",
    }




def _crossover_apply_tangent_context(connector, context):
    if not isinstance(connector, dict) or not isinstance(context, dict):
        return connector
    for key in (
        "chord_heading_degrees",
        "raw_start_heading_degrees",
        "raw_finish_heading_degrees",
        "outward_start_heading_degrees",
        "outward_finish_heading_degrees",
        "connection_start_heading_degrees",
        "connection_finish_heading_degrees",
        "start_tangent_reversed",
        "finish_tangent_reversed",
        "finish_reversal_reason",
        "raw_start_chord_dot",
        "raw_finish_chord_dot",
        "connection_start_chord_dot",
        "connection_finish_chord_dot",
        "endpoint_role_a",
        "endpoint_role_b",
    ):
        if key in context:
            connector[key] = context[key]
    return connector




def _crossover_first_direction(points, from_start=True):
    ordered = list(points if from_start else reversed(points))
    if len(ordered) < 2:
        raise ValueError("The connector has no usable endpoint direction.")
    origin = ordered[0]
    for point in ordered[1:]:
        vector = _crossover_subtract(point, origin)
        if _crossover_length(vector) > max(1.0e-7, 0.1 * CROSSOVER_CONNECTOR_SAMPLE_SPACING):
            return _crossover_unit(vector, "sampled connector endpoint direction")
    raise ValueError("The connector endpoint samples are coincident.")


def _crossover_minimum_polyline_distance(points_a, points_b):
    if not points_a or not points_b:
        return None
    minimum = None
    for point in points_a:
        for segment_a, segment_b in zip(points_b[:-1], points_b[1:]):
            dx = float(segment_b.x) - float(segment_a.x)
            dy = float(segment_b.y) - float(segment_a.y)
            length_squared = dx * dx + dy * dy
            if length_squared <= 1.0e-18:
                distance = _xy_distance(point, segment_a)
            else:
                fraction = (
                    (float(point.x) - float(segment_a.x)) * dx
                    + (float(point.y) - float(segment_a.y)) * dy
                ) / length_squared
                fraction = min(1.0, max(0.0, fraction))
                projected = _crossover_point(
                    float(segment_a.x) + fraction * dx,
                    float(segment_a.y) + fraction * dy,
                )
                distance = _xy_distance(point, projected)
            if minimum is None or distance < minimum:
                minimum = distance
    return minimum


def _crossover_switch_region_points(host_data, toe_chainage, orientation, handing, dimensions):
    start_x = float(dimensions.get("module_start_x") or 0.0)
    finish_x = max(
        float(dimensions.get("heel_lead") or 0.0),
        float(dimensions.get("switch_curve_end_x") or 0.0),
    )
    count = max(8, int(math.ceil(abs(finish_x - start_x) / 5.0)))
    points = []
    for index in range(count + 1):
        local_x = start_x + (finish_x - start_x) * index / float(count)
        for route_name in ("main_centre", "turnout_centre"):
            try:
                local = _rea_c10_local_point(dimensions, local_x, route_name)
            except Exception:
                local = (local_x, 0.0)
            points.append(map_turnout_local_point(
                host_data, toe_chainage, orientation, handing, local[0], local[1]
            ))
    return points


def _crossover_topology_context(
    host_a_data, host_b_data, toe_a, toe_b, orientation_a, orientation_b,
    handing, dimensions, endpoint_a, endpoint_b, tangent_context,
):
    toe_point_a = map_turnout_local_point(
        host_a_data, toe_a, orientation_a, handing, 0.0, 0.0
    )
    toe_point_b = map_turnout_local_point(
        host_b_data, toe_b, orientation_b, handing, 0.0, 0.0
    )
    finish_x = float(dimensions["module_end_x"])
    host_point_a = map_turnout_local_point(
        host_a_data, toe_a, orientation_a, handing, finish_x, 0.0
    )
    host_point_b = map_turnout_local_point(
        host_b_data, toe_b, orientation_b, handing, finish_x, 0.0
    )
    travel_a = _crossover_host_travel_vector(
        host_a_data, toe_a, orientation_a
    )
    travel_b = _crossover_host_travel_vector(
        host_b_data, toe_b, orientation_b
    )
    branch_offset_a = _crossover_subtract(endpoint_a, host_point_a)
    branch_offset_b = _crossover_subtract(endpoint_b, host_point_b)
    branch_side_a = _crossover_cross(travel_a, branch_offset_a)
    branch_side_b = _crossover_cross(travel_b, branch_offset_b)
    return {
        "endpoint_role_a": "Turnout A diverging branch end",
        "endpoint_role_b": "Turnout B diverging branch end",
        "endpoint_a": endpoint_a,
        "endpoint_b": endpoint_b,
        "toe_point_a": toe_point_a,
        "toe_point_b": toe_point_b,
        "toe_vector_a": _crossover_subtract(toe_point_a, endpoint_a),
        "toe_vector_b": _crossover_subtract(toe_point_b, endpoint_b),
        "outward_tangent_a": tangent_context["outward_tangent_a"],
        "outward_tangent_b": tangent_context["outward_tangent_b"],
        "traversal_tangent_a": tangent_context["tangent_a"],
        "traversal_tangent_b": tangent_context["tangent_b"],
        "branch_side_a": float(branch_side_a),
        "branch_side_b": float(branch_side_b),
        "expected_branch_side_sign": _turnout_hand_sign(handing),
        "switch_region_a": _crossover_switch_region_points(
            host_a_data, toe_a, orientation_a, handing, dimensions
        ),
        "switch_region_b": _crossover_switch_region_points(
            host_b_data, toe_b, orientation_b, handing, dimensions
        ),
        "host_a_data": host_a_data,
        "host_b_data": host_b_data,
        "track_gauge": float(dimensions.get("gauge") or dimensions.get("track_gauge") or TURNOUT_DEFAULT_GAUGE),
    }


def _crossover_validate_topology(connector, context, detailed=False):
    """Reject a smooth curve when it connects the wrong physical turnout ends."""
    if not isinstance(context, dict):
        raise ValueError("Crossover topology context is missing.")
    points = list(connector.get("points") or [])
    if len(points) < 2:
        raise ValueError("Crossover topology cannot be checked without a sampled connector.")
    endpoint_a = context["endpoint_a"]
    endpoint_b = context["endpoint_b"]
    if _xy_distance(points[0], endpoint_a) > CROSSOVER_POSITION_TOLERANCE:
        raise ValueError("Invalid crossover topology: connector start is not Turnout A's diverging branch end.")
    if _xy_distance(points[-1], endpoint_b) > CROSSOVER_POSITION_TOLERANCE:
        raise ValueError("Invalid crossover topology: connector finish is not Turnout B's diverging branch end.")

    outward_a = _crossover_unit(context["outward_tangent_a"], "Host A outward branch tangent")
    outward_b = _crossover_unit(context["outward_tangent_b"], "Host B outward branch tangent")
    traversal_a = _crossover_unit(context["traversal_tangent_a"], "Host A connector traversal tangent")
    traversal_b = _crossover_unit(context["traversal_tangent_b"], "Host B connector traversal tangent")
    if _crossover_dot(traversal_a, outward_a) < CROSSOVER_TOPOLOGY_TANGENT_DOT:
        raise ValueError("Invalid crossover topology: the connector does not use Host A's outward diverging-road tangent.")
    if _crossover_dot(traversal_b, _crossover_scale(outward_b, -1.0)) < CROSSOVER_TOPOLOGY_TANGENT_DOT:
        raise ValueError("Invalid crossover topology: the connector does not approach Host B opposite to its outward diverging-road tangent.")

    chord = _crossover_subtract(endpoint_b, endpoint_a)
    chord_unit = _crossover_unit(chord, "crossover branch-end chord")
    ray_dot_a = _crossover_dot(outward_a, chord_unit)
    ray_dot_b = _crossover_dot(outward_b, _crossover_scale(chord_unit, -1.0))
    if ray_dot_a <= CROSSOVER_TOPOLOGY_DIRECTION_DOT:
        raise ValueError("Invalid crossover topology: Turnout A's diverging road points away from Turnout B.")
    if ray_dot_b <= CROSSOVER_TOPOLOGY_DIRECTION_DOT:
        raise ValueError("Invalid crossover topology: Turnout B's diverging road points away from Turnout A.")

    sampled_from_a = _crossover_first_direction(points, from_start=True)
    sampled_from_b = _crossover_first_direction(points, from_start=False)
    toe_vector_a = _crossover_unit(context["toe_vector_a"], "Host A branch end to switch toe")
    toe_vector_b = _crossover_unit(context["toe_vector_b"], "Host B branch end to switch toe")
    leave_dot_a = _crossover_dot(toe_vector_a, sampled_from_a)
    leave_dot_b = _crossover_dot(toe_vector_b, sampled_from_b)
    if leave_dot_a >= -CROSSOVER_TOPOLOGY_DIRECTION_DOT:
        raise ValueError("Invalid crossover topology: the connector initially leaves Turnout A towards its switch toe.")
    if leave_dot_b >= -CROSSOVER_TOPOLOGY_DIRECTION_DOT:
        raise ValueError("Invalid crossover topology: the connector initially leaves Turnout B towards its switch toe.")

    expected_sign = float(context.get("expected_branch_side_sign") or 1.0)
    side_a = float(context.get("branch_side_a") or 0.0)
    side_b = float(context.get("branch_side_b") or 0.0)
    if expected_sign * side_a <= GEOMETRY_TOLERANCE:
        raise ValueError("Invalid crossover topology: Turnout A's diverging branch lies on the wrong side for its handing.")
    if expected_sign * side_b <= GEOMETRY_TOLERANCE:
        raise ValueError("Invalid crossover topology: Turnout B's diverging branch lies on the wrong side for its handing.")

    connector["topology_accepted"] = True
    connector["topology_status"] = "Endpoint topology accepted; sampled route validation pending"
    connector["endpoint_role_a"] = context["endpoint_role_a"]
    connector["endpoint_role_b"] = context["endpoint_role_b"]
    connector["toe_point_a_xy"] = _crossover_xy(context["toe_point_a"])
    connector["toe_point_b_xy"] = _crossover_xy(context["toe_point_b"])
    connector["branch_endpoint_a_xy"] = _crossover_xy(endpoint_a)
    connector["branch_endpoint_b_xy"] = _crossover_xy(endpoint_b)
    connector["toe_vector_a_xy"] = _crossover_xy(context["toe_vector_a"])
    connector["toe_vector_b_xy"] = _crossover_xy(context["toe_vector_b"])
    connector["connector_leave_dot_a"] = float(leave_dot_a)
    connector["connector_leave_dot_b"] = float(leave_dot_b)
    connector["branch_ray_dot_a"] = float(ray_dot_a)
    connector["branch_ray_dot_b"] = float(ray_dot_b)
    connector["branch_side_sign_a"] = 1 if side_a > 0.0 else -1
    connector["branch_side_sign_b"] = 1 if side_b > 0.0 else -1
    if not bool(detailed):
        return connector

    switch_distance_a = _crossover_minimum_polyline_distance(points, context.get("switch_region_a") or [])
    switch_distance_b = _crossover_minimum_polyline_distance(points, context.get("switch_region_b") or [])
    switch_clearance = max(
        1.0,
        CROSSOVER_TOPOLOGY_SWITCH_CLEARANCE_GAUGE_FACTOR * float(context.get("track_gauge") or TURNOUT_DEFAULT_GAUGE),
    )
    if switch_distance_a is not None and switch_distance_a < switch_clearance - 1.0e-7:
        raise ValueError("Invalid crossover topology: the connecting road runs back through Turnout A's switch region.")
    if switch_distance_b is not None and switch_distance_b < switch_clearance - 1.0e-7:
        raise ValueError("Invalid crossover topology: the connecting road runs back through Turnout B's switch region.")

    host_a_data = context.get("host_a_data")
    host_b_data = context.get("host_b_data")
    distances_a = []
    distances_b = []
    if isinstance(host_a_data, dict) and isinstance(host_b_data, dict):
        for point in points:
            distances_a.append(_crossover_nearest_point_on_alignment(host_a_data, point)[3])
            distances_b.append(_crossover_nearest_point_on_alignment(host_b_data, point)[3])
    track_separation = max(
        _crossover_nearest_point_on_alignment(host_b_data, context["toe_point_a"])[3]
        if isinstance(host_b_data, dict) else 0.0,
        _crossover_nearest_point_on_alignment(host_a_data, context["toe_point_b"])[3]
        if isinstance(host_a_data, dict) else 0.0,
    )
    corridor_limit = max(
        CROSSOVER_TOPOLOGY_CORRIDOR_SEPARATION_FACTOR * track_separation,
        CROSSOVER_TOPOLOGY_CORRIDOR_GAUGE_FACTOR * float(context.get("track_gauge") or TURNOUT_DEFAULT_GAUGE),
        25.0,
    )
    if distances_a and distances_b:
        if any(min(a, b) > corridor_limit for a, b in zip(distances_a, distances_b)):
            raise ValueError("Invalid crossover topology: the connecting road leaves the corridor between the two host tracks.")
        if distances_a[0] > distances_b[0] + float(context.get("track_gauge") or TURNOUT_DEFAULT_GAUGE):
            raise ValueError("Invalid crossover topology: the connecting road does not start from Host A's side of the formation.")
        if distances_b[-1] > distances_a[-1] + float(context.get("track_gauge") or TURNOUT_DEFAULT_GAUGE):
            raise ValueError("Invalid crossover topology: the connecting road does not finish on Host B's side of the formation.")

    connector["topology_accepted"] = True
    connector["topology_status"] = "Accepted: diverging branch end to diverging branch end; sampled route clear of both switch regions"
    connector["endpoint_role_a"] = context["endpoint_role_a"]
    connector["endpoint_role_b"] = context["endpoint_role_b"]
    connector["toe_point_a_xy"] = _crossover_xy(context["toe_point_a"])
    connector["toe_point_b_xy"] = _crossover_xy(context["toe_point_b"])
    connector["branch_endpoint_a_xy"] = _crossover_xy(endpoint_a)
    connector["branch_endpoint_b_xy"] = _crossover_xy(endpoint_b)
    connector["toe_vector_a_xy"] = _crossover_xy(context["toe_vector_a"])
    connector["toe_vector_b_xy"] = _crossover_xy(context["toe_vector_b"])
    connector["connector_leave_dot_a"] = float(leave_dot_a)
    connector["connector_leave_dot_b"] = float(leave_dot_b)
    connector["branch_ray_dot_a"] = float(ray_dot_a)
    connector["branch_ray_dot_b"] = float(ray_dot_b)
    connector["branch_side_sign_a"] = 1 if side_a > 0.0 else -1
    connector["branch_side_sign_b"] = 1 if side_b > 0.0 else -1
    connector["minimum_switch_distance_a"] = switch_distance_a
    connector["minimum_switch_distance_b"] = switch_distance_b
    connector["connector_host_a_distance_bounds"] = (
        min(distances_a), max(distances_a)
    ) if distances_a else None
    connector["connector_host_b_distance_bounds"] = (
        min(distances_b), max(distances_b)
    ) if distances_b else None
    return connector

def _crossover_arc_from_start_tangent(start, tangent, finish):
    """Return one straight or circular segment from a point and tangent to a point."""
    start = _crossover_point(start.x, start.y)
    finish = _crossover_point(finish.x, finish.y)
    tangent = _crossover_unit(tangent, "arc start tangent")
    chord = _crossover_subtract(finish, start)
    chord_length = _crossover_length(chord)
    if chord_length <= CROSSOVER_POSITION_TOLERANCE:
        return {
            "kind": "point",
            "points": [start],
            "length": 0.0,
            "radius": None,
            "sweep": 0.0,
            "start_tangent": tangent,
            "end_tangent": tangent,
        }
    normal = _crossover_left_normal_vector(tangent)
    denominator = 2.0 * _crossover_dot(chord, normal)
    if abs(denominator) <= 1.0e-10 * max(1.0, chord_length):
        chord_unit = _crossover_unit(chord, "straight connector chord")
        if _crossover_dot(chord_unit, tangent) <= 0.0:
            raise ValueError("A connector straight would run backwards from its turnout end.")
        return {
            "kind": "straight",
            "points": [start, finish],
            "length": chord_length,
            "radius": None,
            "sweep": 0.0,
            "start_tangent": chord_unit,
            "end_tangent": chord_unit,
        }
    signed_radius = (chord_length * chord_length) / denominator
    radius = abs(signed_radius)
    if radius <= GEOMETRY_TOLERANCE:
        raise ValueError("A connector arc has zero usable radius.")
    centre = _crossover_add(start, _crossover_scale(normal, signed_radius))
    start_angle = math.atan2(start.y - centre.y, start.x - centre.x)
    finish_angle = math.atan2(finish.y - centre.y, finish.x - centre.x)
    if signed_radius > 0.0:
        sweep = (finish_angle - start_angle) % (2.0 * math.pi)
    else:
        sweep = -((start_angle - finish_angle) % (2.0 * math.pi))
    if abs(sweep) > CROSSOVER_CONNECTOR_MAX_SWEEP + 1.0e-10:
        raise ValueError(
            "A connector arc requires an excessive {:.3f} degree sweep.".format(
                math.degrees(abs(sweep))
            )
        )
    arc_length = radius * abs(sweep)
    count = max(2, int(math.ceil(arc_length / CROSSOVER_CONNECTOR_SAMPLE_SPACING)))
    points = []
    for index in range(count + 1):
        fraction = index / float(count)
        angle = start_angle + sweep * fraction
        points.append(
            _crossover_point(
                centre.x + radius * math.cos(angle),
                centre.y + radius * math.sin(angle),
            )
        )
    end_radius = _crossover_unit(_crossover_subtract(finish, centre), "arc end radius")
    if signed_radius > 0.0:
        end_tangent = _crossover_left_normal_vector(end_radius)
    else:
        end_tangent = _crossover_scale(_crossover_left_normal_vector(end_radius), -1.0)
    return {
        "kind": "arc",
        "points": points,
        "length": arc_length,
        "radius": radius,
        "signed_radius": signed_radius,
        "sweep": sweep,
        "centre": centre,
        "start_tangent": tangent,
        "end_tangent": _crossover_unit(end_tangent, "arc end tangent"),
    }


def _crossover_reverse_segment(segment):
    points = list(reversed(segment["points"]))
    reversed_segment = dict(segment)
    reversed_segment["points"] = points
    reversed_segment["start_tangent"] = _crossover_scale(segment["end_tangent"], -1.0)
    reversed_segment["end_tangent"] = _crossover_scale(segment["start_tangent"], -1.0)
    if segment.get("sweep") is not None:
        reversed_segment["sweep"] = -float(segment.get("sweep") or 0.0)
    if segment.get("signed_radius") is not None:
        reversed_segment["signed_radius"] = -float(segment["signed_radius"])
    return reversed_segment


def _crossover_solve_biarc(start, start_tangent, finish, finish_tangent):
    """Solve a symmetric-distance biarc with exact end positions and tangents."""
    start = _crossover_point(start.x, start.y)
    finish = _crossover_point(finish.x, finish.y)
    t0 = _crossover_unit(start_tangent, "connector start tangent")
    t1 = _crossover_unit(finish_tangent, "connector finish tangent")
    displacement = _crossover_subtract(finish, start)
    distance_squared = _crossover_dot(displacement, displacement)
    if distance_squared <= CROSSOVER_POSITION_TOLERANCE * CROSSOVER_POSITION_TOLERANCE:
        if _crossover_dot(t0, t1) < math.cos(CROSSOVER_TANGENT_TOLERANCE):
            raise ValueError("Coincident connector ends have incompatible tangents.")
        return {
            "points": [start, finish],
            "segments": [],
            "join": start,
            "length": 0.0,
            "minimum_radius": None,
            "position_error": _xy_distance(start, finish),
            "start_tangent_error": 0.0,
            "finish_tangent_error": 0.0,
            "join_tangent_error": 0.0,
        }
    cosine = max(-1.0, min(1.0, _crossover_dot(t0, t1)))
    linear = _crossover_dot(displacement, _crossover_add(t0, t1))
    one_minus_cosine = 1.0 - cosine
    if one_minus_cosine <= 1.0e-12:
        if linear <= 1.0e-12:
            raise ValueError("Parallel connector tangents do not face the required route.")
        distance_parameter = distance_squared / (2.0 * linear)
    else:
        discriminant = linear * linear + 2.0 * one_minus_cosine * distance_squared
        if discriminant < -1.0e-9:
            raise ValueError("The crossover biarc has no real solution.")
        distance_parameter = (
            -linear + math.sqrt(max(0.0, discriminant))
        ) / (2.0 * one_minus_cosine)
    if not math.isfinite(distance_parameter) or distance_parameter <= 0.0:
        raise ValueError("The crossover biarc resolves behind one or both turnout ends.")
    join = _crossover_scale(
        _crossover_add(
            _crossover_add(start, finish),
            _crossover_scale(_crossover_subtract(t0, t1), distance_parameter),
        ),
        0.5,
    )
    first = _crossover_arc_from_start_tangent(start, t0, join)
    reverse_second = _crossover_arc_from_start_tangent(
        finish, _crossover_scale(t1, -1.0), join
    )
    second = _crossover_reverse_segment(reverse_second)
    points = _crossover_remove_duplicate_points(first["points"] + second["points"][1:])
    if len(points) < 2:
        raise ValueError("The crossover connector collapsed to fewer than two points.")
    start_error = _crossover_angle_difference(
        _crossover_vector_angle(first["start_tangent"]), _crossover_vector_angle(t0)
    )
    finish_error = _crossover_angle_difference(
        _crossover_vector_angle(second["end_tangent"]), _crossover_vector_angle(t1)
    )
    join_error = _crossover_angle_difference(
        _crossover_vector_angle(first["end_tangent"]),
        _crossover_vector_angle(second["start_tangent"]),
    )
    position_error = max(
        _xy_distance(points[0], start),
        _xy_distance(points[-1], finish),
        _xy_distance(first["points"][-1], second["points"][0]),
    )
    radii = [
        float(segment["radius"])
        for segment in (first, second)
        if segment.get("radius") is not None
    ]
    return {
        "points": points,
        "segments": [first, second],
        "join": join,
        "length": float(first["length"]) + float(second["length"]),
        "minimum_radius": min(radii) if radii else None,
        "position_error": position_error,
        "start_tangent_error": start_error,
        "finish_tangent_error": finish_error,
        "join_tangent_error": join_error,
    }



def _crossover_solve_biarc_ratio(start, start_tangent, finish, finish_tangent, distance_ratio):
    """Solve one exact biarc from the general positive-distance family.

    distance_ratio is the finish-side tangent distance divided by the
    start-side tangent distance. A value of 1.0 reproduces the established
    symmetric-distance solver exactly.
    """
    ratio = float(distance_ratio)
    if not math.isfinite(ratio) or ratio <= 0.0:
        raise ValueError("The crossover biarc distance ratio must be finite and greater than zero.")
    if abs(ratio - 1.0) <= 1.0e-12:
        connector = _crossover_solve_biarc(
            start, start_tangent, finish, finish_tangent
        )
        connector["biarc_distance_ratio"] = 1.0
        connector["connector_family"] = "exact biarc"
        return connector

    start = _crossover_point(start.x, start.y)
    finish = _crossover_point(finish.x, finish.y)
    t0 = _crossover_unit(start_tangent, "connector start tangent")
    t1 = _crossover_unit(finish_tangent, "connector finish tangent")
    displacement = _crossover_subtract(finish, start)
    distance_squared = _crossover_dot(displacement, displacement)
    if distance_squared <= CROSSOVER_POSITION_TOLERANCE * CROSSOVER_POSITION_TOLERANCE:
        if _crossover_dot(t0, t1) < math.cos(CROSSOVER_TANGENT_TOLERANCE):
            raise ValueError("Coincident connector ends have incompatible tangents.")
        return {
            "points": [start, finish],
            "segments": [],
            "join": start,
            "length": 0.0,
            "minimum_radius": None,
            "position_error": _xy_distance(start, finish),
            "start_tangent_error": 0.0,
            "finish_tangent_error": 0.0,
            "join_tangent_error": 0.0,
            "biarc_distance_ratio": ratio,
            "start_distance_parameter": 0.0,
            "finish_distance_parameter": 0.0,
        }

    cosine = max(-1.0, min(1.0, _crossover_dot(t0, t1)))
    quadratic = 2.0 * (1.0 - cosine) * ratio
    linear = 2.0 * _crossover_dot(
        displacement, _crossover_add(t0, _crossover_scale(t1, ratio))
    )
    constant = -distance_squared
    if abs(quadratic) <= 1.0e-12:
        if linear <= 1.0e-12:
            raise ValueError("The crossover biarc family resolves behind one or both turnout ends.")
        start_distance = -constant / linear
    else:
        discriminant = linear * linear - 4.0 * quadratic * constant
        if discriminant < -1.0e-9:
            raise ValueError("The crossover biarc family has no real solution.")
        root = math.sqrt(max(0.0, discriminant))
        roots = (
            (-linear + root) / (2.0 * quadratic),
            (-linear - root) / (2.0 * quadratic),
        )
        positive = [
            value for value in roots
            if math.isfinite(value) and value > 0.0
        ]
        if not positive:
            raise ValueError("The crossover biarc family resolves behind one or both turnout ends.")
        start_distance = min(positive)
    finish_distance = ratio * start_distance
    if (
        not math.isfinite(start_distance)
        or not math.isfinite(finish_distance)
        or start_distance <= 0.0
        or finish_distance <= 0.0
    ):
        raise ValueError("The crossover biarc family resolves behind one or both turnout ends.")

    join = _crossover_scale(
        _crossover_add(
            _crossover_add(
                _crossover_scale(start, finish_distance),
                _crossover_scale(finish, start_distance),
            ),
            _crossover_scale(
                _crossover_subtract(t0, t1),
                start_distance * finish_distance,
            ),
        ),
        1.0 / (start_distance + finish_distance),
    )
    first = _crossover_arc_from_start_tangent(start, t0, join)
    reverse_second = _crossover_arc_from_start_tangent(
        finish, _crossover_scale(t1, -1.0), join
    )
    second = _crossover_reverse_segment(reverse_second)
    points = _crossover_remove_duplicate_points(first["points"] + second["points"][1:])
    if len(points) < 2:
        raise ValueError("The crossover connector collapsed to fewer than two points.")
    start_error = _crossover_angle_difference(
        _crossover_vector_angle(first["start_tangent"]), _crossover_vector_angle(t0)
    )
    finish_error = _crossover_angle_difference(
        _crossover_vector_angle(second["end_tangent"]), _crossover_vector_angle(t1)
    )
    join_error = _crossover_angle_difference(
        _crossover_vector_angle(first["end_tangent"]),
        _crossover_vector_angle(second["start_tangent"]),
    )
    position_error = max(
        _xy_distance(points[0], start),
        _xy_distance(points[-1], finish),
        _xy_distance(first["points"][-1], second["points"][0]),
    )
    radii = [
        float(segment["radius"])
        for segment in (first, second)
        if segment.get("radius") is not None
    ]
    return {
        "connector_family": "exact biarc",
        "points": points,
        "segments": [first, second],
        "join": join,
        "length": float(first["length"]) + float(second["length"]),
        "minimum_radius": min(radii) if radii else None,
        "position_error": position_error,
        "start_tangent_error": start_error,
        "finish_tangent_error": finish_error,
        "join_tangent_error": join_error,
        "biarc_distance_ratio": ratio,
        "start_distance_parameter": start_distance,
        "finish_distance_parameter": finish_distance,
    }



_CROSSOVER_LAST_SOLVER_TRACE = {}


class _CrossoverCandidateFailure(ValueError):
    def __init__(self, message, scout_candidate=None):
        ValueError.__init__(self, message)
        self.scout_candidate = scout_candidate



def _crossover_solver_trace_reset(**values):
    global _CROSSOVER_LAST_SOLVER_TRACE
    _CROSSOVER_LAST_SOLVER_TRACE = {
        "solver": "connection-facing exact biarc, bounded arc-straight-arc and tangent-exact cubic fallback",
        "status": "running",
        "inputs": dict(values),
        "toe_station_attempts": 0,
        "family_attempts": {
            "exact biarc": 0,
            "bounded arc-straight-arc": 0,
            "cubic Bezier": 0,
        },
        "accepted_counts": {
            "exact biarc": 0,
            "bounded arc-straight-arc": 0,
            "cubic Bezier": 0,
        },
        "rejection_counts": {},
        "best_rejected": [],
        "best_accepted": [],
        "chosen": None,
    }
    return _CROSSOVER_LAST_SOLVER_TRACE



def _crossover_solver_rejection_code(reason):
    value = str(reason or "")
    lower = value.lower()
    if "invalid crossover topology" in lower or "diverging branch" in lower or "switch toe" in lower or "switch region" in lower:
        return "INVALID_CROSSOVER_TOPOLOGY"
    if "total sweep" in lower or "form a loop" in lower or "excessive" in lower and "sweep" in lower:
        return "LOOP_OR_EXCESSIVE_SWEEP"
    if "backtrack" in lower or "run backwards" in lower or "resolves behind" in lower:
        return "BACKTRACKS_BEHIND_TURNOUT"
    if "not local" in lower or "endpoint chord" in lower:
        return "NON_LOCAL_LENGTH"
    if "radius" in lower:
        return "MINIMUM_RADIUS"
    if "tangent" in lower:
        return "TANGENT_CONTINUITY"
    if "position" in lower or "coincident" in lower:
        return "POSITION_CONTINUITY"
    if "finite" in lower or "zero usable" in lower or "collapsed" in lower:
        return "DEGENERATE_GEOMETRY"
    return "OTHER_GEOMETRY"



def _crossover_connector_trace_record(toe_b, family, connector=None, accepted=False, reason="", parameter=None, projected_toe_b=None):
    trace = _CROSSOVER_LAST_SOLVER_TRACE
    if not isinstance(trace, dict) or trace.get("status") not in ("running", "rejected", "accepted"):
        return
    family = str(family or "unknown")
    attempts = trace.setdefault("family_attempts", {})
    attempts[family] = int(attempts.get(family, 0)) + 1
    if accepted:
        accepted_counts = trace.setdefault("accepted_counts", {})
        accepted_counts[family] = int(accepted_counts.get(family, 0)) + 1
    else:
        code = _crossover_solver_rejection_code(reason)
        counts = trace.setdefault("rejection_counts", {})
        counts[code] = int(counts.get(code, 0)) + 1
    item = {
        "toe_b": float(toe_b),
        "projected_offset": None if projected_toe_b is None else float(toe_b) - float(projected_toe_b),
        "family": family,
        "parameter": parameter,
        "accepted": bool(accepted),
        "reason": str(reason or ""),
    }
    if isinstance(connector, dict):
        item.update({
            "length": float(connector.get("length") or 0.0),
            "minimum_radius": None if connector.get("minimum_radius") is None else float(connector.get("minimum_radius")),
            "total_sweep_degrees": math.degrees(float(connector.get("total_sweep") or connector.get("sampled_total_turning") or 0.0)),
            "length_ratio": float(connector.get("local_length_ratio") or 0.0),
            "minimum_start_progress": float(connector.get("minimum_start_progress") or 0.0),
            "minimum_finish_progress": float(connector.get("minimum_finish_progress") or 0.0),
            "chord_length": float(connector.get("endpoint_chord_length") or 0.0),
            "start_heading_degrees": float(connector.get("start_heading_degrees") or 0.0),
            "finish_heading_degrees": float(connector.get("finish_heading_degrees") or 0.0),
            "chord_heading_degrees": float(connector.get("chord_heading_degrees") or 0.0),
            "endpoint_heading_difference_degrees": float(connector.get("endpoint_heading_difference_degrees") or 0.0),
            "raw_start_heading_degrees": float(connector.get("raw_start_heading_degrees") or 0.0),
            "raw_finish_heading_degrees": float(connector.get("raw_finish_heading_degrees") or 0.0),
            "connection_start_heading_degrees": float(connector.get("connection_start_heading_degrees") or connector.get("start_heading_degrees") or 0.0),
            "connection_finish_heading_degrees": float(connector.get("connection_finish_heading_degrees") or connector.get("finish_heading_degrees") or 0.0),
            "start_tangent_reversed": bool(connector.get("start_tangent_reversed", False)),
            "finish_tangent_reversed": bool(connector.get("finish_tangent_reversed", False)),
            "raw_start_chord_dot": float(connector.get("raw_start_chord_dot") or 0.0),
            "raw_finish_chord_dot": float(connector.get("raw_finish_chord_dot") or 0.0),
            "connection_start_chord_dot": float(connector.get("connection_start_chord_dot") or 0.0),
            "connection_finish_chord_dot": float(connector.get("connection_finish_chord_dot") or 0.0),
            "topology_accepted": bool(connector.get("topology_accepted", False)),
            "topology_status": str(connector.get("topology_status") or ""),
            "connector_leave_dot_a": float(connector.get("connector_leave_dot_a") or 0.0),
            "connector_leave_dot_b": float(connector.get("connector_leave_dot_b") or 0.0),
            "branch_ray_dot_a": float(connector.get("branch_ray_dot_a") or 0.0),
            "branch_ray_dot_b": float(connector.get("branch_ray_dot_b") or 0.0),
            "minimum_switch_distance_a": connector.get("minimum_switch_distance_a"),
            "minimum_switch_distance_b": connector.get("minimum_switch_distance_b"),
        })
    target_name = "best_accepted" if accepted else "best_rejected"
    target = trace.setdefault(target_name, [])
    target.append(item)
    if accepted:
        target.sort(key=lambda candidate: (
            candidate.get("length") or 1.0e15,
            candidate.get("total_sweep_degrees") or 0.0,
            -(candidate.get("minimum_radius") if candidate.get("minimum_radius") is not None else 1.0e15),
            abs(candidate.get("projected_offset") or 0.0),
        ))
    else:
        target.sort(key=lambda candidate: (
            candidate.get("total_sweep_degrees") if candidate.get("total_sweep_degrees") is not None else 1.0e15,
            candidate.get("length_ratio") if candidate.get("length_ratio") else 1.0e15,
            -(candidate.get("minimum_radius") if candidate.get("minimum_radius") is not None else -1.0),
            abs(candidate.get("projected_offset") or 0.0),
        ))
    del target[CROSSOVER_SOLVER_TRACE_CANDIDATE_LIMIT:]




def _crossover_connector_identity_key(connector):
    family = str(connector.get("connector_family") or "exact biarc")
    if family == "cubic Bezier":
        return (
            family,
            round(float(connector.get("control_distance_a") or 0.0), 8),
            round(float(connector.get("control_distance_b") or 0.0), 8),
        )
    if family == "bounded arc-straight-arc":
        return (
            family,
            str(connector.get("csc_path_type") or ""),
            round(float(connector.get("csc_radius") or 0.0), 8),
        )
    return (
        family,
        round(float(connector.get("biarc_distance_ratio") or 1.0), 10),
    )



def _crossover_signed_angle_delta(angle, previous):
    return (float(angle) - float(previous) + math.pi) % (2.0 * math.pi) - math.pi


def _crossover_cubic_bezier_components(start, tangent_a, finish, tangent_b, distance_a, distance_b):
    p0 = _crossover_point(start.x, start.y)
    p3 = _crossover_point(finish.x, finish.y)
    t0 = _crossover_unit(tangent_a, "cubic connector start tangent")
    t1 = _crossover_unit(tangent_b, "cubic connector finish tangent")
    da = float(distance_a)
    db = float(distance_b)
    if not math.isfinite(da) or not math.isfinite(db) or da <= 0.0 or db <= 0.0:
        raise ValueError("Cubic connector control distances must be finite and greater than zero.")
    p1 = _crossover_add(p0, _crossover_scale(t0, da))
    p2 = _crossover_subtract(p3, _crossover_scale(t1, db))
    return p0, p1, p2, p3, t0, t1


def _crossover_cubic_bezier_evaluate(control, parameter):
    p0, p1, p2, p3, _t0, _t1 = control
    u = min(max(float(parameter), 0.0), 1.0)
    one = 1.0 - u
    point = _crossover_add(
        _crossover_add(
            _crossover_scale(p0, one * one * one),
            _crossover_scale(p1, 3.0 * one * one * u),
        ),
        _crossover_add(
            _crossover_scale(p2, 3.0 * one * u * u),
            _crossover_scale(p3, u * u * u),
        ),
    )
    derivative = _crossover_scale(
        _crossover_add(
            _crossover_add(
                _crossover_scale(_crossover_subtract(p1, p0), one * one),
                _crossover_scale(_crossover_subtract(p2, p1), 2.0 * one * u),
            ),
            _crossover_scale(_crossover_subtract(p3, p2), u * u),
        ),
        3.0,
    )
    second = _crossover_scale(
        _crossover_add(
            _crossover_scale(
                _crossover_add(_crossover_subtract(p2, _crossover_scale(p1, 2.0)), p0),
                one,
            ),
            _crossover_scale(
                _crossover_add(_crossover_subtract(p3, _crossover_scale(p2, 2.0)), p1),
                u,
            ),
        ),
        6.0,
    )
    return point, derivative, second


def _crossover_solve_cubic_bezier(start, start_tangent, finish, finish_tangent, distance_a, distance_b, detailed=False):
    """Solve one tangent-exact local cubic connector candidate.

    This is a controlled fallback for curved-host arrangements where every
    two-arc member of the exact biarc family selects the remote major route.
    The sampled centreline remains analytical until document creation.
    """
    control = _crossover_cubic_bezier_components(
        start, start_tangent, finish, finish_tangent, distance_a, distance_b
    )
    p0, p1, p2, p3, t0, t1 = control
    control_length = (
        _xy_distance(p0, p1) + _xy_distance(p1, p2) + _xy_distance(p2, p3)
    )
    if detailed:
        sample_count = max(
            24,
            min(4000, int(math.ceil(control_length / CROSSOVER_BEZIER_SAMPLE_SPACING))),
        )
    else:
        sample_count = max(24, min(160, int(math.ceil(control_length / 2.0))))
    points = []
    headings = []
    minimum_radius = None
    for index in range(sample_count + 1):
        u = index / float(sample_count)
        point, derivative, second = _crossover_cubic_bezier_evaluate(control, u)
        speed = _crossover_length(derivative)
        if not math.isfinite(speed) or speed <= 1.0e-10:
            raise ValueError("The cubic connector develops a stationary or non-finite tangent.")
        points.append(point)
        headings.append(_crossover_vector_angle(derivative))
        curvature = abs(_crossover_cross(derivative, second)) / (speed * speed * speed)
        if curvature > 1.0e-12:
            radius = 1.0 / curvature
            minimum_radius = radius if minimum_radius is None else min(minimum_radius, radius)
    points = _crossover_remove_duplicate_points(points)
    if len(points) < 2:
        raise ValueError("The cubic crossover connector collapsed to fewer than two points.")
    total_turning = sum(
        abs(_crossover_signed_angle_delta(angle, previous))
        for previous, angle in zip(headings[:-1], headings[1:])
    )
    length = _crossover_polyline_length(points)
    position_error = max(_xy_distance(points[0], p0), _xy_distance(points[-1], p3))
    segment = {
        "kind": "cubic",
        "points": points,
        "length": length,
        "radius": minimum_radius,
        "sweep": total_turning,
        "absolute_turning": total_turning,
        "start_tangent": t0,
        "end_tangent": t1,
        "control_points": [p0, p1, p2, p3],
    }
    return {
        "connector_family": "cubic Bezier",
        "points": points,
        "segments": [segment],
        "join": None,
        "length": length,
        "minimum_radius": minimum_radius,
        "position_error": position_error,
        "start_tangent_error": 0.0,
        "finish_tangent_error": 0.0,
        "join_tangent_error": 0.0,
        "sampled_total_turning": total_turning,
        "control_distance_a": float(distance_a),
        "control_distance_b": float(distance_b),
    }


def _crossover_bezier_control_values(start, start_tangent, finish, finish_tangent):
    chord = _crossover_subtract(finish, start)
    chord_length = _crossover_length(chord)
    if chord_length <= CROSSOVER_POSITION_TOLERANCE:
        return []
    t0 = _crossover_unit(start_tangent, "cubic connector start tangent")
    t1 = _crossover_unit(finish_tangent, "cubic connector finish tangent")
    values = {chord_length * float(factor) for factor in CROSSOVER_BEZIER_CONTROL_FACTORS}
    special = []
    projection_a = _crossover_dot(chord, t0)
    projection_b = _crossover_dot(chord, t1)
    if projection_a > 1.0e-6:
        special.append(projection_a)
    if projection_b > 1.0e-6:
        special.append(projection_b)
    denominator = _crossover_cross(t0, t1)
    if abs(denominator) > 1.0e-10:
        distance_a = _crossover_cross(chord, t1) / denominator
        distance_b = _crossover_cross(t0, chord) / denominator
        if distance_a > 1.0e-6:
            special.append(distance_a)
        if distance_b > 1.0e-6:
            special.append(distance_b)
    maximum = max(chord_length * 3.0, 1.0)
    for value in special:
        if math.isfinite(value) and 1.0e-4 < value <= maximum:
            values.add(float(value))
    # Bound the Cartesian search while retaining the chord-scaled family and
    # the most geometrically meaningful projection/intersection distances.
    ordered = sorted(values, key=lambda value: (abs(math.log(max(value / chord_length, 1.0e-12), 2.0)), value))
    return sorted(ordered[:10])

def _crossover_search_cubic_bezier_family(start, start_tangent, finish, finish_tangent, minimum_radius, toe_b, projected_toe_b, tangent_context=None, topology_context=None):
    values = _crossover_bezier_control_values(start, start_tangent, finish, finish_tangent)
    connectors = []
    tested = set()
    requested = max(0.0, float(minimum_radius))

    def test(distance_a, distance_b):
        key = (round(float(distance_a), 8), round(float(distance_b), 8))
        if key in tested:
            return None
        tested.add(key)
        connector = None
        try:
            connector = _crossover_solve_cubic_bezier(
                start, start_tangent, finish, finish_tangent, distance_a, distance_b
            )
            _crossover_apply_tangent_context(connector, tangent_context)
            _crossover_validate_local_connector(
                connector, start, finish, start_tangent, finish_tangent
            )
            if topology_context is not None:
                _crossover_validate_topology(connector, topology_context)
        except Exception as error:
            _crossover_connector_trace_record(
                toe_b, "cubic Bezier", connector, False, str(error),
                parameter="dA={:.6f}, dB={:.6f}".format(distance_a, distance_b),
                projected_toe_b=projected_toe_b,
            )
            return None
        connectors.append(connector)
        radius = connector.get("minimum_radius")
        accepted = radius is None or float(radius) >= requested - 1.0e-7
        _crossover_connector_trace_record(
            toe_b, "cubic Bezier", connector, accepted,
            "" if accepted else "The sampled cubic connector radius is below the configured minimum.",
            parameter="dA={:.6f}, dB={:.6f}".format(distance_a, distance_b),
            projected_toe_b=projected_toe_b,
        )
        return connector

    for distance_a in values:
        for distance_b in values:
            test(distance_a, distance_b)

    for iteration in range(CROSSOVER_BEZIER_REFINEMENT_ITERATIONS):
        if not connectors:
            break
        seeds = sorted(
            connectors,
            key=lambda connector: _crossover_connector_family_merit(connector, requested),
            reverse=True,
        )[:CROSSOVER_BEZIER_REFINEMENT_SEEDS]
        factor = 2.0 ** (0.5 ** (iteration + 1))
        for seed in seeds:
            centre_a = float(seed.get("control_distance_a") or 0.0)
            centre_b = float(seed.get("control_distance_b") or 0.0)
            for multiplier_a, multiplier_b in (
                (factor, 1.0), (1.0 / factor, 1.0),
                (1.0, factor), (1.0, 1.0 / factor),
                (factor, factor), (1.0 / factor, 1.0 / factor),
                (factor, 1.0 / factor), (1.0 / factor, factor),
            ):
                test(centre_a * multiplier_a, centre_b * multiplier_b)

    qualifying = [
        connector for connector in connectors
        if connector.get("minimum_radius") is None
        or float(connector.get("minimum_radius")) >= requested - 1.0e-7
    ]
    if not qualifying:
        return None, connectors
    for coarse in sorted(
        qualifying,
        key=lambda connector: _crossover_connector_family_merit(connector, requested),
        reverse=True,
    ):
        detailed = None
        try:
            detailed = _crossover_solve_cubic_bezier(
                start, start_tangent, finish, finish_tangent,
                float(coarse.get("control_distance_a")),
                float(coarse.get("control_distance_b")),
                detailed=True,
            )
            _crossover_apply_tangent_context(detailed, tangent_context)
            _crossover_validate_local_connector(
                detailed, start, finish, start_tangent, finish_tangent
            )
            if topology_context is not None:
                _crossover_validate_topology(detailed, topology_context)
            radius = detailed.get("minimum_radius")
            if radius is not None and float(radius) < requested - 1.0e-7:
                raise ValueError("The detailed sampled cubic connector radius is below the configured minimum.")
        except Exception as error:
            _crossover_connector_trace_record(
                toe_b, "cubic Bezier", detailed, False, str(error),
                parameter="final dA={:.6f}, dB={:.6f}".format(
                    float(coarse.get("control_distance_a") or 0.0),
                    float(coarse.get("control_distance_b") or 0.0),
                ),
                projected_toe_b=projected_toe_b,
            )
            continue
        return detailed, connectors
    return None, connectors



def _crossover_mod2pi(angle):
    return float(angle) % (2.0 * math.pi)


def _crossover_csc_parameters(path_type, alpha, beta, distance):
    """Return normalised Dubins-style CSC parameters for one path type."""
    path_type = str(path_type or "").upper()
    alpha = _crossover_mod2pi(alpha)
    beta = _crossover_mod2pi(beta)
    distance = max(0.0, float(distance))
    if path_type == "LSL":
        temporary = distance + math.sin(alpha) - math.sin(beta)
        squared = (
            2.0 + distance * distance - 2.0 * math.cos(alpha - beta)
            + 2.0 * distance * (math.sin(alpha) - math.sin(beta))
        )
        if squared < -1.0e-12:
            return None
        angle = math.atan2(math.cos(beta) - math.cos(alpha), temporary)
        return (
            _crossover_mod2pi(-alpha + angle),
            math.sqrt(max(0.0, squared)),
            _crossover_mod2pi(beta - angle),
        )
    if path_type == "RSR":
        temporary = distance - math.sin(alpha) + math.sin(beta)
        squared = (
            2.0 + distance * distance - 2.0 * math.cos(alpha - beta)
            + 2.0 * distance * (-math.sin(alpha) + math.sin(beta))
        )
        if squared < -1.0e-12:
            return None
        angle = math.atan2(math.cos(alpha) - math.cos(beta), temporary)
        return (
            _crossover_mod2pi(alpha - angle),
            math.sqrt(max(0.0, squared)),
            _crossover_mod2pi(-beta + angle),
        )
    if path_type == "LSR":
        squared = (
            -2.0 + distance * distance + 2.0 * math.cos(alpha - beta)
            + 2.0 * distance * (math.sin(alpha) + math.sin(beta))
        )
        if squared < -1.0e-12:
            return None
        straight = math.sqrt(max(0.0, squared))
        angle = (
            math.atan2(-math.cos(alpha) - math.cos(beta), distance + math.sin(alpha) + math.sin(beta))
            - math.atan2(-2.0, straight)
        )
        return (
            _crossover_mod2pi(-alpha + angle),
            straight,
            _crossover_mod2pi(-beta + angle),
        )
    if path_type == "RSL":
        squared = (
            distance * distance - 2.0 + 2.0 * math.cos(alpha - beta)
            - 2.0 * distance * (math.sin(alpha) + math.sin(beta))
        )
        if squared < -1.0e-12:
            return None
        straight = math.sqrt(max(0.0, squared))
        angle = (
            math.atan2(math.cos(alpha) + math.cos(beta), distance - math.sin(alpha) - math.sin(beta))
            - math.atan2(2.0, straight)
        )
        return (
            _crossover_mod2pi(alpha - angle),
            straight,
            _crossover_mod2pi(beta - angle),
        )
    raise ValueError("Unknown bounded arc-straight-arc path type: {}".format(path_type))



def _crossover_csc_arc_segment(start, heading, radius, turn_letter, amount, detailed=False):
    sign = 1.0 if str(turn_letter).upper() == "L" else -1.0
    tangent = _crossover_heading_vector(heading)
    normal = _crossover_left_normal_vector(tangent)
    centre = _crossover_add(start, _crossover_scale(normal, sign * radius))
    start_angle = math.atan2(float(start.y) - float(centre.y), float(start.x) - float(centre.x))
    sweep = sign * float(amount)
    arc_length = float(radius) * abs(sweep)
    if detailed:
        count = max(2, int(math.ceil(arc_length / CROSSOVER_CONNECTOR_SAMPLE_SPACING)))
    else:
        count = max(4, min(64, int(math.ceil(abs(sweep) * 24.0))))
    points = []
    for index in range(count + 1):
        angle = start_angle + sweep * index / float(count)
        points.append(_crossover_point(
            float(centre.x) + float(radius) * math.cos(angle),
            float(centre.y) + float(radius) * math.sin(angle),
        ))
    finish_heading = float(heading) + sweep
    return {
        "kind": "arc",
        "points": points,
        "length": arc_length,
        "radius": float(radius),
        "signed_radius": sign * float(radius),
        "sweep": sweep,
        "absolute_turning": abs(sweep),
        "centre": centre,
        "start_tangent": _crossover_heading_vector(heading),
        "end_tangent": _crossover_heading_vector(finish_heading),
    }, points[-1], finish_heading



def _crossover_csc_straight_segment(start, heading, normalised_length, radius):
    distance = max(0.0, float(normalised_length)) * float(radius)
    tangent = _crossover_heading_vector(heading)
    finish = _crossover_add(start, _crossover_scale(tangent, distance))
    return {
        "kind": "straight",
        "points": [start, finish],
        "length": distance,
        "radius": None,
        "sweep": 0.0,
        "absolute_turning": 0.0,
        "start_tangent": tangent,
        "end_tangent": tangent,
    }, finish, float(heading)



def _crossover_solve_bounded_csc(start, start_tangent, finish, finish_tangent, radius, path_type, detailed=False):
    """Build one exact tangent arc-straight-arc connector at a bounded radius."""
    radius = float(radius)
    if not math.isfinite(radius) or radius <= GEOMETRY_TOLERANCE:
        raise ValueError("The bounded connector radius must be finite and greater than zero.")
    start = _crossover_point(start.x, start.y)
    finish = _crossover_point(finish.x, finish.y)
    t0 = _crossover_unit(start_tangent, "bounded connector start tangent")
    t1 = _crossover_unit(finish_tangent, "bounded connector finish tangent")
    heading0 = _crossover_vector_angle(t0)
    heading1 = _crossover_vector_angle(t1)
    displacement = _crossover_subtract(finish, start)
    chord_length = _crossover_length(displacement)
    if chord_length <= CROSSOVER_POSITION_TOLERANCE:
        raise ValueError("The bounded connector endpoints are coincident.")
    normalised_distance = chord_length / radius
    chord_heading = _crossover_vector_angle(displacement)
    alpha = _crossover_mod2pi(heading0 - chord_heading)
    beta = _crossover_mod2pi(heading1 - chord_heading)
    parameters = _crossover_csc_parameters(path_type, alpha, beta, normalised_distance)
    if parameters is None:
        raise ValueError("The bounded {} connector has no real tangent solution.".format(path_type))
    first_amount, straight_amount, second_amount = parameters
    current = start
    heading = heading0
    segments = []
    path_letters = str(path_type).upper()
    first, current, heading = _crossover_csc_arc_segment(
        current, heading, radius, path_letters[0], first_amount, detailed=detailed
    )
    segments.append(first)
    straight, current, heading = _crossover_csc_straight_segment(
        current, heading, straight_amount, radius
    )
    segments.append(straight)
    second, current, heading = _crossover_csc_arc_segment(
        current, heading, radius, path_letters[2], second_amount, detailed=detailed
    )
    segments.append(second)
    points = _crossover_remove_duplicate_points(
        first["points"] + straight["points"][1:] + second["points"][1:]
    )
    position_error = _xy_distance(points[-1], finish)
    finish_error = _crossover_angle_difference(heading, heading1)
    if position_error > CROSSOVER_POSITION_TOLERANCE:
        raise ValueError(
            "Bounded connector positional continuity error {:.9f} mm exceeds {:.9f} mm.".format(
                position_error, CROSSOVER_POSITION_TOLERANCE
            )
        )
    if finish_error > CROSSOVER_TANGENT_TOLERANCE:
        raise ValueError(
            "Bounded connector finish tangent error {:.6f} degrees exceeds {:.6f} degrees.".format(
                math.degrees(finish_error), math.degrees(CROSSOVER_TANGENT_TOLERANCE)
            )
        )
    return {
        "connector_family": "bounded arc-straight-arc",
        "csc_path_type": path_letters,
        "csc_radius": radius,
        "points": points,
        "segments": segments,
        "join": None,
        "length": sum(float(segment.get("length") or 0.0) for segment in segments),
        "minimum_radius": radius,
        "position_error": position_error,
        "start_tangent_error": 0.0,
        "finish_tangent_error": finish_error,
        "join_tangent_error": 0.0,
        "sampled_total_turning": abs(first["sweep"]) + abs(second["sweep"]),
    }




def _crossover_search_bounded_csc_family(start, start_tangent, finish, finish_tangent, minimum_radius, toe_b, projected_toe_b, tangent_context=None, topology_context=None):
    requested = max(float(minimum_radius), CROSSOVER_MINIMUM_ALLOWED_RADIUS)
    accepted = []
    all_local = []

    def test_radius(radius):
        for path_type in CROSSOVER_CSC_PATH_TYPES:
            connector = None
            try:
                connector = _crossover_solve_bounded_csc(
                    start, start_tangent, finish, finish_tangent, radius, path_type,
                    detailed=False,
                )
                _crossover_apply_tangent_context(connector, tangent_context)
                _crossover_validate_local_connector(
                    connector, start, finish, start_tangent, finish_tangent
                )
                if topology_context is not None:
                    _crossover_validate_topology(connector, topology_context)
            except Exception as error:
                _crossover_connector_trace_record(
                    toe_b, "bounded arc-straight-arc", connector, False, str(error),
                    parameter="{} at R={:.6f}".format(path_type, radius),
                    projected_toe_b=projected_toe_b,
                )
                continue
            all_local.append(connector)
            accepted.append(connector)
            _crossover_connector_trace_record(
                toe_b, "bounded arc-straight-arc", connector, True, "",
                parameter="{} at R={:.6f}".format(path_type, radius),
                projected_toe_b=projected_toe_b,
            )

    # The configured minimum radius is the most likely and shortest useful
    # local route. Larger radii are only attempted when no local route exists
    # at the requested value.
    test_radius(requested)
    if not accepted:
        for factor in CROSSOVER_CSC_RADIUS_FACTORS[1:]:
            test_radius(requested * float(factor))
            if accepted:
                break
    if not accepted:
        return None, all_local

    for coarse in sorted(
        accepted,
        key=lambda connector: _crossover_connector_family_merit(connector, requested),
        reverse=True,
    ):
        detailed = None
        try:
            detailed = _crossover_solve_bounded_csc(
                start, start_tangent, finish, finish_tangent,
                float(coarse.get("csc_radius") or requested),
                str(coarse.get("csc_path_type") or ""),
                detailed=True,
            )
            _crossover_apply_tangent_context(detailed, tangent_context)
            _crossover_validate_local_connector(
                detailed, start, finish, start_tangent, finish_tangent
            )
            if topology_context is not None:
                _crossover_validate_topology(detailed, topology_context)
        except Exception as error:
            _crossover_connector_trace_record(
                toe_b, "bounded arc-straight-arc", detailed, False, str(error),
                parameter="final {} at R={:.6f}".format(
                    str(coarse.get("csc_path_type") or "unknown"),
                    float(coarse.get("csc_radius") or requested),
                ),
                projected_toe_b=projected_toe_b,
            )
            continue
        return detailed, all_local
    return None, all_local



def _crossover_branch_end_toe_seed(host_a_data, host_b_data, toe_a, orientation_a, orientation_b, handing, dimensions):
    """Estimate Host B toe from the actual Host A branch end, not the Host A toe."""
    endpoint_a, _tangent_a = _crossover_branch_endpoint(
        host_a_data, toe_a, orientation_a, handing, dimensions
    )
    station_b, projected, heading, distance = _crossover_nearest_point_on_alignment(
        host_b_data, endpoint_a
    )
    finish_local = _rea_c10_local_point(
        dimensions, float(dimensions["module_end_x"]), "turnout_centre"
    )
    direction_b = _turnout_orientation_sign(orientation_b)
    toe_seed = float(station_b) - direction_b * float(finish_local[0])
    return toe_seed, station_b, projected, heading, distance



def crossover_solver_trace_text():
    trace = _CROSSOVER_LAST_SOLVER_TRACE
    if not isinstance(trace, dict) or not trace:
        return "No crossover solver trace is available."
    inputs = dict(trace.get("inputs") or {})
    lines = [
        "Solver: {}".format(trace.get("solver") or "unknown"),
        "Status: {}".format(trace.get("status") or "unknown"),
        "Host A toe: {:.3f} mm".format(float(inputs.get("toe_a") or 0.0)),
        "Host B valid toe interval: {:.3f} to {:.3f} mm".format(
            float(inputs.get("minimum_b") or 0.0), float(inputs.get("maximum_b") or 0.0)
        ),
        "Host A toe projection on Host B: {:.3f} mm".format(float(inputs.get("projected_b") or 0.0)),
        "Host A branch-end Host B toe seed: {:.3f} mm".format(float(inputs.get("branch_toe_seed") or 0.0)),
        "Host A branch-end projection: Host B station {:.3f} mm; separation {:.3f} mm".format(
            float(inputs.get("branch_projection_station") or 0.0),
            float(inputs.get("branch_projection_distance") or 0.0),
        ),
        "Semantic tangent rule: use Host A outward branch tangent; approach Host B opposite to its outward branch tangent.",
        "Seed outward branch headings: A {:.3f} degrees; B {:.3f} degrees".format(
            float(inputs.get("seed_raw_start_heading_degrees") or 0.0),
            float(inputs.get("seed_raw_finish_heading_degrees") or 0.0),
        ),
        "Seed connector traversal headings: A {:.3f} degrees; B {:.3f} degrees".format(
            float(inputs.get("seed_connection_start_heading_degrees") or 0.0),
            float(inputs.get("seed_connection_finish_heading_degrees") or 0.0),
        ),
        "Requested minimum connector radius: {:.3f} mm".format(float(inputs.get("minimum_radius") or 0.0)),
        "Host B toe positions attempted: {}".format(int(trace.get("toe_station_attempts") or 0)),
    ]
    attempts = dict(trace.get("family_attempts") or {})
    accepted = dict(trace.get("accepted_counts") or {})
    lines.append(
        "Family attempts: exact biarc {}; bounded arc-straight-arc {}; cubic Bezier {}".format(
            int(attempts.get("exact biarc") or 0),
            int(attempts.get("bounded arc-straight-arc") or 0),
            int(attempts.get("cubic Bezier") or 0),
        )
    )
    lines.append(
        "Accepted topology-and-geometry candidates: exact biarc {}; bounded arc-straight-arc {}; cubic Bezier {}".format(
            int(accepted.get("exact biarc") or 0),
            int(accepted.get("bounded arc-straight-arc") or 0),
            int(accepted.get("cubic Bezier") or 0),
        )
    )
    counts = dict(trace.get("rejection_counts") or {})
    if counts:
        lines.append("Rejection categories:")
        for code, count in sorted(counts.items(), key=lambda item: (-item[1], item[0])):
            lines.append("  - {}: {}".format(code, count))

    def xy(value):
        if not isinstance(value, (tuple, list)) or len(value) < 2:
            return "not recorded"
        return "({:.3f}, {:.3f}) mm".format(float(value[0]), float(value[1]))

    def bounds(value):
        if not isinstance(value, (tuple, list)) or len(value) < 2:
            return "not recorded"
        return "{:.3f} to {:.3f} mm".format(float(value[0]), float(value[1]))

    chosen = trace.get("chosen")
    if isinstance(chosen, dict):
        lines.extend([
            "Selected connector:",
            "  - Host B toe: {:.6f} mm".format(float(chosen.get("toe_b") or 0.0)),
            "  - Family: {}".format(chosen.get("family") or "unknown"),
            "  - Parameter: {}".format(chosen.get("parameter") or "not applicable"),
            "  - Endpoint roles: {}; {}".format(
                chosen.get("endpoint_role_a") or "Turnout A diverging branch end",
                chosen.get("endpoint_role_b") or "Turnout B diverging branch end",
            ),
            "  - Host A toe / branch end: {} / {}".format(
                xy(chosen.get("toe_point_a_xy")), xy(chosen.get("branch_endpoint_a_xy"))
            ),
            "  - Host B toe / branch end: {} / {}".format(
                xy(chosen.get("toe_point_b_xy")), xy(chosen.get("branch_endpoint_b_xy"))
            ),
            "  - Outward branch headings: A {:.3f} degrees; B {:.3f} degrees".format(
                float(chosen.get("raw_start_heading_degrees") or 0.0),
                float(chosen.get("raw_finish_heading_degrees") or 0.0),
            ),
            "  - Connector traversal headings: A {:.3f} degrees; B {:.3f} degrees".format(
                float(chosen.get("connection_start_heading_degrees") or 0.0),
                float(chosen.get("connection_finish_heading_degrees") or 0.0),
            ),
            "  - Tangent reversal: A {}; B {} (B reversal is traversal-only)".format(
                "yes" if bool(chosen.get("start_tangent_reversed", False)) else "no",
                "yes" if bool(chosen.get("finish_tangent_reversed", False)) else "no",
            ),
            "  - Connector leaves away from toes: A dot {:.6f}; B dot {:.6f}".format(
                float(chosen.get("connector_leave_dot_a") or 0.0),
                float(chosen.get("connector_leave_dot_b") or 0.0),
            ),
            "  - Branch-side signs: A {}; B {}".format(
                int(chosen.get("branch_side_sign_a") or 0),
                int(chosen.get("branch_side_sign_b") or 0),
            ),
            "  - Topology: {}".format(chosen.get("topology_status") or "not validated"),
            "  - Minimum switch-region clearance: A {}; B {}".format(
                "not recorded" if chosen.get("minimum_switch_distance_a") is None else "{:.3f} mm".format(float(chosen.get("minimum_switch_distance_a"))),
                "not recorded" if chosen.get("minimum_switch_distance_b") is None else "{:.3f} mm".format(float(chosen.get("minimum_switch_distance_b"))),
            ),
            "  - Connector distance bounds to Host A: {}".format(bounds(chosen.get("connector_host_a_distance_bounds"))),
            "  - Connector distance bounds to Host B: {}".format(bounds(chosen.get("connector_host_b_distance_bounds"))),
            "  - Length: {:.6f} mm".format(float(chosen.get("length") or 0.0)),
            "  - Minimum radius: {}".format(
                "straight" if chosen.get("minimum_radius") is None else "{:.6f} mm".format(float(chosen.get("minimum_radius")))
            ),
            "  - Total sampled turning: {:.6f} degrees".format(float(chosen.get("total_sweep_degrees") or 0.0)),
            "  - Length/chord ratio: {:.6f}".format(float(chosen.get("length_ratio") or 0.0)),
        ])
    rejected = list(trace.get("best_rejected") or [])
    if rejected:
        lines.append("Best rejected candidates:")
        for item in rejected[:6]:
            radius = item.get("minimum_radius")
            lines.append(
                "  - toe {:.6f}; {}; {}; sweep {:.3f} deg; radius {}; length {:.3f} mm; ratio {:.3f}; {}".format(
                    float(item.get("toe_b") or 0.0),
                    item.get("family") or "unknown",
                    item.get("parameter") or "not applicable",
                    float(item.get("total_sweep_degrees") or 0.0),
                    "straight" if radius is None else "{:.3f} mm".format(float(radius)),
                    float(item.get("length") or 0.0),
                    float(item.get("length_ratio") or 0.0),
                    item.get("reason") or "rejected",
                )
            )
    return "\n".join(lines)





def _crossover_validate_local_connector(connector, start, finish, start_tangent, finish_tangent):
    """Validate the complete sampled route rather than an endpoint chord alone."""
    points = list(connector.get("points") or [])
    if len(points) < 2:
        raise ValueError("The crossover connector has no usable sampled route.")
    for point in points:
        if not math.isfinite(float(point.x)) or not math.isfinite(float(point.y)):
            raise ValueError("The crossover connector contains a non-finite sampled point.")

    if connector.get("sampled_total_turning") is not None:
        total_sweep = abs(float(connector.get("sampled_total_turning") or 0.0))
    else:
        total_sweep = sum(
            abs(float(segment.get("absolute_turning") if segment.get("absolute_turning") is not None else segment.get("sweep") or 0.0))
            for segment in connector.get("segments", [])
        )

    chord = _crossover_subtract(finish, start)
    chord_length = _crossover_length(chord)
    connector_length = float(connector.get("length") or 0.0)
    t0 = _crossover_unit(start_tangent, "connector start tangent")
    t1 = _crossover_unit(finish_tangent, "connector finish tangent")
    start_heading = _crossover_vector_angle(t0)
    finish_heading = _crossover_vector_angle(t1)
    chord_heading = _crossover_vector_angle(chord) if chord_length > CROSSOVER_POSITION_TOLERANCE else start_heading
    endpoint_heading_difference = _crossover_angle_difference(start_heading, finish_heading)
    if chord_length > CROSSOVER_POSITION_TOLERANCE:
        length_ratio = connector_length / chord_length
        backtrack_allowance = max(
            CROSSOVER_CONNECTOR_BACKTRACK_MINIMUM,
            CROSSOVER_CONNECTOR_BACKTRACK_FRACTION * chord_length,
        )
        minimum_start_progress = min(
            _crossover_dot(_crossover_subtract(point, start), t0)
            for point in points
        )
        minimum_finish_progress = min(
            _crossover_dot(_crossover_subtract(finish, point), t1)
            for point in points
        )
    else:
        length_ratio = 1.0
        minimum_start_progress = 0.0
        minimum_finish_progress = 0.0
        backtrack_allowance = CROSSOVER_CONNECTOR_BACKTRACK_MINIMUM

    connector["total_sweep"] = total_sweep
    connector["local_length_ratio"] = length_ratio
    connector["minimum_start_progress"] = minimum_start_progress
    connector["minimum_finish_progress"] = minimum_finish_progress
    connector["local_backtrack_allowance"] = backtrack_allowance
    connector["endpoint_chord_length"] = chord_length
    connector["start_heading_degrees"] = math.degrees(start_heading)
    connector["finish_heading_degrees"] = math.degrees(finish_heading)
    connector["chord_heading_degrees"] = math.degrees(chord_heading)
    connector["endpoint_heading_difference_degrees"] = math.degrees(endpoint_heading_difference)

    if total_sweep > CROSSOVER_CONNECTOR_MAX_TOTAL_SWEEP + 1.0e-10:
        raise ValueError(
            "The candidate connector requires {:.3f} degrees of total sweep and would form a loop.".format(
                math.degrees(total_sweep)
            )
        )
    if chord_length > CROSSOVER_POSITION_TOLERANCE:
        if length_ratio > CROSSOVER_CONNECTOR_MAX_LENGTH_RATIO + 1.0e-10:
            raise ValueError(
                "The candidate connector length is {:.3f} times its endpoint chord and is not local.".format(
                    length_ratio
                )
            )
        if minimum_start_progress < -backtrack_allowance - 1.0e-9:
            raise ValueError(
                "The candidate connector backtracks {:.3f} mm behind the Host A turnout end.".format(
                    -minimum_start_progress
                )
            )
        if minimum_finish_progress < -backtrack_allowance - 1.0e-9:
            raise ValueError(
                "The candidate connector backtracks {:.3f} mm behind the Host B turnout end.".format(
                    -minimum_finish_progress
                )
            )
    return connector


def _crossover_connector_family_merit(connector, minimum_radius):
    radius = connector.get("minimum_radius")
    radius_value = 1.0e15 if radius is None else float(radius)
    requested = max(0.0, float(minimum_radius))
    radius_satisfied = 1 if radius is None or radius_value >= requested - 1.0e-7 else 0
    connector_length = max(float(connector.get("length") or 0.0), CROSSOVER_POSITION_TOLERANCE)
    total_sweep = float(connector.get("total_sweep") or 0.0)
    ratio = max(float(connector.get("biarc_distance_ratio") or 1.0), 1.0e-12)
    straight_connection = 1 if radius is None else 0
    return (
        radius_satisfied,
        straight_connection,
        radius_value / connector_length,
        radius_value,
        -connector_length,
        -total_sweep,
        -abs(math.log(ratio, 2.0)),
    )



def _crossover_candidate_merit(candidate):
    connector = candidate["connector"]
    topology_valid = 1 if bool(connector.get("topology_accepted", False)) else 0
    radius = connector.get("minimum_radius")
    radius_value = 1.0e15 if radius is None else float(radius)
    sweep_total = sum(abs(float(segment.get("sweep") or 0.0)) for segment in connector["segments"])
    straight_connection = 1 if radius is None else 0
    connector_length = max(float(connector["length"]), CROSSOVER_POSITION_TOLERANCE)
    radius_efficiency = radius_value / connector_length
    return (
        topology_valid,
        straight_connection,
        radius_efficiency,
        radius_value,
        -connector_length,
        -sweep_total,
        -abs(float(candidate["toe_b"]) - float(candidate["projected_toe_b"])),
        -float(candidate["toe_b"]),
    )



def _crossover_straightness_value(
    host_a_data, host_b_data, toe_a, toe_b, orientation_a, orientation_b, handing, dimensions
):
    endpoint_a, raw_tangent_a = _crossover_branch_endpoint(
        host_a_data, toe_a, orientation_a, handing, dimensions
    )
    endpoint_b, raw_tangent_b = _crossover_branch_endpoint(
        host_b_data, toe_b, orientation_b, handing, dimensions
    )
    tangent_context = _crossover_connection_tangent_context(
        endpoint_a, raw_tangent_a, endpoint_b, raw_tangent_b
    )
    tangent_a = tangent_context["tangent_a"]
    tangent_b = tangent_context["tangent_b"]
    if _crossover_angle_difference(
        _crossover_vector_angle(tangent_a), _crossover_vector_angle(tangent_b)
    ) > CROSSOVER_TANGENT_TOLERANCE:
        return None
    displacement = _crossover_subtract(endpoint_b, endpoint_a)
    if _crossover_length(displacement) <= CROSSOVER_POSITION_TOLERANCE:
        return 0.0
    if _crossover_dot(_crossover_unit(displacement), tangent_a) <= 0.0:
        return None
    return _crossover_cross(displacement, tangent_a)




def _crossover_candidate_for_toe_b(
    host_a_data,
    host_b_data,
    toe_a,
    toe_b,
    orientation_a,
    orientation_b,
    handing,
    dimensions,
    minimum_radius,
    projected_toe_b=None,
    try_biarc=True,
    allow_csc=False,
    allow_cubic=False,
):
    endpoint_a, raw_tangent_a = _crossover_branch_endpoint(
        host_a_data, toe_a, orientation_a, handing, dimensions
    )
    endpoint_b, raw_tangent_b = _crossover_branch_endpoint(
        host_b_data, toe_b, orientation_b, handing, dimensions
    )
    tangent_context = _crossover_connection_tangent_context(
        endpoint_a, raw_tangent_a, endpoint_b, raw_tangent_b
    )
    tangent_a = tangent_context["tangent_a"]
    tangent_b = tangent_context["tangent_b"]
    topology_context = _crossover_topology_context(
        host_a_data, host_b_data, toe_a, toe_b, orientation_a, orientation_b,
        handing, dimensions, endpoint_a, endpoint_b, tangent_context,
    )

    requested_radius = max(0.0, float(minimum_radius))
    connectors = []
    failures = []
    best_connector = None

    if bool(try_biarc):
        tested_ratios = set()

        def test_ratio(ratio):
            ratio = float(ratio)
            key = round(math.log(ratio, 2.0), 12)
            if key in tested_ratios:
                return None
            tested_ratios.add(key)
            connector = None
            try:
                connector = _crossover_solve_biarc_ratio(
                    endpoint_a, tangent_a, endpoint_b, tangent_b, ratio
                )
                _crossover_apply_tangent_context(connector, tangent_context)
                if connector["position_error"] > CROSSOVER_POSITION_TOLERANCE:
                    raise ValueError(
                        "Connector positional continuity error {:.9f} mm exceeds {:.9f} mm.".format(
                            connector["position_error"], CROSSOVER_POSITION_TOLERANCE
                        )
                    )
                tangent_error = max(
                    connector["start_tangent_error"],
                    connector["finish_tangent_error"],
                    connector["join_tangent_error"],
                )
                if tangent_error > CROSSOVER_TANGENT_TOLERANCE:
                    raise ValueError(
                        "Connector tangent continuity error {:.6f} degrees exceeds {:.6f} degrees.".format(
                            math.degrees(tangent_error), math.degrees(CROSSOVER_TANGENT_TOLERANCE)
                        )
                    )
                _crossover_validate_local_connector(
                    connector, endpoint_a, endpoint_b, tangent_a, tangent_b
                )
                _crossover_validate_topology(connector, topology_context)
            except Exception as error:
                failures.append(str(error))
                _crossover_connector_trace_record(
                    toe_b, "exact biarc", connector, False, str(error),
                    parameter="distance ratio {:.9f}".format(ratio),
                    projected_toe_b=projected_toe_b,
                )
                return None
            connectors.append(connector)
            radius = connector.get("minimum_radius")
            accepted = radius is None or float(radius) >= requested_radius - 1.0e-7
            _crossover_connector_trace_record(
                toe_b, "exact biarc", connector, accepted,
                "" if accepted else "The exact biarc radius is below the configured minimum.",
                parameter="distance ratio {:.9f}".format(ratio),
                projected_toe_b=projected_toe_b,
            )
            return connector

        symmetric = test_ratio(1.0)
        if symmetric is not None:
            symmetric_radius = symmetric.get("minimum_radius")
            if symmetric_radius is None or float(symmetric_radius) >= requested_radius - 1.0e-7:
                best_connector = symmetric

        if best_connector is None:
            for level in range(1, CROSSOVER_BIARC_RATIO_LEVELS + 1):
                test_ratio(2.0 ** level)
                test_ratio(2.0 ** (-level))

            for iteration in range(CROSSOVER_BIARC_RATIO_REFINEMENT_ITERATIONS):
                if not connectors:
                    break
                seeds = sorted(
                    connectors,
                    key=lambda item: _crossover_connector_family_merit(item, requested_radius),
                    reverse=True,
                )[:CROSSOVER_BIARC_RATIO_REFINEMENT_SEEDS]
                step = 0.5 ** (iteration + 1)
                for seed in seeds:
                    centre = math.log(
                        max(float(seed.get("biarc_distance_ratio") or 1.0), 1.0e-12),
                        2.0,
                    )
                    for offset in (-step, step):
                        exponent = min(
                            max(centre + offset, -float(CROSSOVER_BIARC_RATIO_LEVELS)),
                            float(CROSSOVER_BIARC_RATIO_LEVELS),
                        )
                        test_ratio(2.0 ** exponent)

            qualifying = [
                connector for connector in connectors
                if connector.get("minimum_radius") is None
                or float(connector["minimum_radius"]) >= requested_radius - 1.0e-7
            ]
            if qualifying:
                best_connector = max(
                    qualifying,
                    key=lambda item: _crossover_connector_family_merit(item, requested_radius),
                )

    if best_connector is None and bool(allow_csc):
        best_csc, csc_connectors = _crossover_search_bounded_csc_family(
            endpoint_a, tangent_a, endpoint_b, tangent_b, requested_radius,
            toe_b, projected_toe_b, tangent_context=tangent_context,
            topology_context=topology_context,
        )
        connectors.extend(csc_connectors)
        if best_csc is not None:
            best_connector = best_csc

    if best_connector is None and bool(allow_cubic):
        best_bezier, bezier_connectors = _crossover_search_cubic_bezier_family(
            endpoint_a, tangent_a, endpoint_b, tangent_b, requested_radius,
            toe_b, projected_toe_b, tangent_context=tangent_context,
            topology_context=topology_context,
        )
        connectors.extend(bezier_connectors)
        if best_bezier is not None:
            best_connector = best_bezier

    if best_connector is None:
        scout_candidate = None
        if connectors:
            scout_connector = max(
                connectors,
                key=lambda connector: _crossover_connector_family_merit(connector, 0.0),
            )
            if projected_toe_b is None:
                projected_toe_b, _projected, _heading, _distance = _crossover_nearest_point_on_alignment(
                    host_b_data,
                    map_turnout_local_point(host_a_data, toe_a, orientation_a, handing, 0.0, 0.0),
                )
            scout_candidate = {
                "toe_b": float(toe_b),
                "projected_toe_b": float(projected_toe_b),
                "endpoint_a": endpoint_a,
                "endpoint_b": endpoint_b,
                "tangent_a": tangent_a,
                "tangent_b": tangent_b,
                "raw_tangent_a": raw_tangent_a,
                "raw_tangent_b": raw_tangent_b,
                "start_tangent_reversed": bool(tangent_context.get("start_tangent_reversed", False)),
                "finish_tangent_reversed": bool(tangent_context.get("finish_tangent_reversed", False)),
                "topology_context": topology_context,
                "connector": scout_connector,
            }
            radii = [
                float(connector["minimum_radius"])
                for connector in connectors
                if connector.get("minimum_radius") is not None
            ]
            if radii:
                raise _CrossoverCandidateFailure(
                    "The best local connector radius is {:.3f} mm, below the configured {:.3f} mm.".format(
                        max(radii), requested_radius
                    ),
                    scout_candidate,
                )
            raise _CrossoverCandidateFailure(
                "No local tangent-continuous connector satisfies the configured geometry.",
                scout_candidate,
            )
        if failures:
            counts = {}
            for failure in failures:
                counts[failure] = counts.get(failure, 0) + 1
            reason = max(counts, key=lambda item: (counts[item], item))
            raise _CrossoverCandidateFailure(reason)
        raise _CrossoverCandidateFailure("No finite local tangent-continuous connector was found.")

    if projected_toe_b is None:
        projected_toe_b, _projected, _heading, _distance = _crossover_nearest_point_on_alignment(
            host_b_data,
            map_turnout_local_point(host_a_data, toe_a, orientation_a, handing, 0.0, 0.0),
        )
    return {
        "toe_b": float(toe_b),
        "projected_toe_b": float(projected_toe_b),
        "endpoint_a": endpoint_a,
        "endpoint_b": endpoint_b,
        "tangent_a": tangent_a,
        "tangent_b": tangent_b,
        "raw_tangent_a": raw_tangent_a,
        "raw_tangent_b": raw_tangent_b,
        "start_tangent_reversed": bool(tangent_context.get("start_tangent_reversed", False)),
        "finish_tangent_reversed": bool(tangent_context.get("finish_tangent_reversed", False)),
        "topology_context": topology_context,
        "connector": best_connector,
    }




def _crossover_solve_toe_b(
    host_a_data,
    host_b_data,
    toe_a,
    orientation_a,
    orientation_b,
    handing,
    dimensions,
    minimum_radius,
):
    minimum_b, maximum_b = turnout_valid_toe_range(
        host_b_data["total"], dimensions, orientation_b
    )
    if maximum_b < minimum_b - GEOMETRY_TOLERANCE:
        raise ValueError("Host Track B is too short for a complete natural REA C10 turnout.")
    projected_b, _point, _heading, _distance = _crossover_nearest_point_on_alignment(
        host_b_data,
        map_turnout_local_point(host_a_data, toe_a, orientation_a, handing, 0.0, 0.0),
    )
    projected_b = min(max(projected_b, minimum_b), maximum_b)
    branch_seed, branch_station, _branch_point, _branch_heading, branch_distance = _crossover_branch_end_toe_seed(
        host_a_data, host_b_data, toe_a, orientation_a, orientation_b, handing, dimensions
    )
    branch_seed = min(max(float(branch_seed), minimum_b), maximum_b)
    branch_projection_toe = min(max(float(branch_station), minimum_b), maximum_b)
    seed_endpoint_a, seed_raw_tangent_a = _crossover_branch_endpoint(
        host_a_data, toe_a, orientation_a, handing, dimensions
    )
    seed_endpoint_b, seed_raw_tangent_b = _crossover_branch_endpoint(
        host_b_data, branch_seed, orientation_b, handing, dimensions
    )
    seed_tangent_context = _crossover_connection_tangent_context(
        seed_endpoint_a, seed_raw_tangent_a, seed_endpoint_b, seed_raw_tangent_b
    )
    trace = _crossover_solver_trace_reset(
        toe_a=float(toe_a), minimum_b=float(minimum_b), maximum_b=float(maximum_b),
        projected_b=float(projected_b), branch_toe_seed=float(branch_seed),
        branch_projection_station=float(branch_station),
        branch_projection_toe_search_centre=float(branch_projection_toe),
        branch_projection_distance=float(branch_distance),
        seed_raw_start_heading_degrees=float(seed_tangent_context.get("raw_start_heading_degrees") or 0.0),
        seed_raw_finish_heading_degrees=float(seed_tangent_context.get("raw_finish_heading_degrees") or 0.0),
        seed_connection_start_heading_degrees=float(seed_tangent_context.get("connection_start_heading_degrees") or 0.0),
        seed_connection_finish_heading_degrees=float(seed_tangent_context.get("connection_finish_heading_degrees") or 0.0),
        seed_start_tangent_reversed=bool(seed_tangent_context.get("start_tangent_reversed", False)),
        seed_finish_tangent_reversed=bool(seed_tangent_context.get("finish_tangent_reversed", False)),
        seed_connection_start_chord_dot=float(seed_tangent_context.get("connection_start_chord_dot") or 0.0),
        seed_connection_finish_chord_dot=float(seed_tangent_context.get("connection_finish_chord_dot") or 0.0),
        minimum_radius=float(minimum_radius),
        orientation_a=str(orientation_a), orientation_b=str(orientation_b),
        handing=str(handing), host_a_length=float(host_a_data.get("total") or 0.0),
        host_b_length=float(host_b_data.get("total") or 0.0),
    )
    span = max(0.0, maximum_b - minimum_b)
    candidate_values = {minimum_b, maximum_b, projected_b, branch_seed, branch_projection_toe}
    straight_root_values = set()
    coarse_values = [minimum_b, maximum_b]
    if span > 1.0e-9:
        coarse_values = [minimum_b + span * index / 80.0 for index in range(81)]
        candidate_values.update(coarse_values)
        coarse_step = span / 80.0
        for centre in (branch_seed, branch_projection_toe):
            candidate_values.update(
                min(max(float(centre) + coarse_step * offset / 4.0, minimum_b), maximum_b)
                for offset in range(-8, 9)
            )
        previous_toe = None
        previous_value = None
        for coarse_toe in coarse_values:
            value = _crossover_straightness_value(
                host_a_data, host_b_data, toe_a, coarse_toe, orientation_a,
                orientation_b, handing, dimensions,
            )
            if value is not None and abs(value) <= 1.0e-10:
                candidate_values.add(coarse_toe)
                straight_root_values.add(coarse_toe)
            if (
                previous_toe is not None and previous_value is not None and value is not None
                and previous_value * value < 0.0
            ):
                low = previous_toe
                high = coarse_toe
                low_value = previous_value
                for _root_iteration in range(70):
                    middle = 0.5 * (low + high)
                    middle_value = _crossover_straightness_value(
                        host_a_data, host_b_data, toe_a, middle, orientation_a,
                        orientation_b, handing, dimensions,
                    )
                    if middle_value is None:
                        break
                    if abs(middle_value) <= 1.0e-12:
                        low = high = middle
                        break
                    if low_value * middle_value <= 0.0:
                        high = middle
                    else:
                        low = middle
                        low_value = middle_value
                root = 0.5 * (low + high)
                candidate_values.add(root)
                straight_root_values.add(root)
            previous_toe = coarse_toe if value is not None else None
            previous_value = value

    scout_candidates = []
    valid_candidates = []
    failures = []
    attempted_toes = {
        "biarc": set(),
        "csc": set(),
        "cubic": set(),
    }

    def append_unique(target, candidate):
        key = (round(float(candidate["toe_b"]), 10), _crossover_connector_identity_key(candidate["connector"]))
        for existing in target:
            existing_key = (
                round(float(existing["toe_b"]), 10),
                _crossover_connector_identity_key(existing["connector"]),
            )
            if existing_key == key:
                return
        target.append(candidate)

    def register_candidate(toe_b, family_mode):
        toe_b = min(max(float(toe_b), minimum_b), maximum_b)
        toe_key = round(toe_b, 10)
        attempted = attempted_toes[family_mode]
        if toe_key in attempted:
            return None
        attempted.add(toe_key)
        trace["toe_station_attempts"] = len(set().union(*attempted_toes.values()))
        try:
            candidate = _crossover_candidate_for_toe_b(
                host_a_data, host_b_data, toe_a, toe_b,
                orientation_a, orientation_b, handing, dimensions, minimum_radius,
                projected_toe_b=projected_b,
                try_biarc=(family_mode == "biarc"),
                allow_csc=(family_mode == "csc"),
                allow_cubic=(family_mode == "cubic"),
            )
        except _CrossoverCandidateFailure as strict_error:
            failures.append(str(strict_error))
            scout = getattr(strict_error, "scout_candidate", None)
            if scout is None:
                return None
            append_unique(scout_candidates, scout)
            return scout
        except Exception as strict_error:
            failures.append(str(strict_error))
            return None
        append_unique(scout_candidates, candidate)
        append_unique(valid_candidates, candidate)
        return candidate

    # Phase 1: exact-biarc search prioritised around the actual branch-end
    # projection and corrected Host B toe seed before the wider host interval.
    ordered_biarc_values = sorted(
        candidate_values,
        key=lambda value: (
            abs(float(value) - float(branch_seed)),
            abs(float(value) - float(branch_projection_toe)),
            abs(float(value) - float(projected_b)),
            float(value),
        ),
    )
    for toe_b in ordered_biarc_values:
        register_candidate(toe_b, "biarc")

    def scout_merit(candidate):
        connector = candidate["connector"]
        radius = connector.get("minimum_radius")
        straight_connection = 1 if radius is None else 0
        radius_value = 1.0e15 if radius is None else float(radius)
        return (
            straight_connection,
            radius_value / max(float(connector.get("length") or 0.0), CROSSOVER_POSITION_TOLERANCE),
            radius_value,
            -float(connector.get("length") or 0.0),
            -abs(float(candidate["toe_b"]) - float(branch_seed)),
            -float(candidate["toe_b"]),
        )

    step = span / 80.0 if span > 1.0e-9 else 0.0
    seeds = sorted(scout_candidates, key=scout_merit, reverse=True)[:CROSSOVER_REFINEMENT_SEED_COUNT]
    for _iteration in range(CROSSOVER_REFINEMENT_ITERATIONS):
        if step <= 1.0e-5 or not seeds or valid_candidates:
            break
        local_values = set()
        for seed in seeds:
            centre = float(seed["toe_b"])
            local_values.update(
                min(max(centre + step * offset / 5.0, minimum_b), maximum_b)
                for offset in range(-5, 6)
            )
        for toe_b in sorted(local_values):
            register_candidate(toe_b, "biarc")
        seeds = sorted(scout_candidates, key=scout_merit, reverse=True)[:CROSSOVER_REFINEMENT_SEED_COUNT]
        step /= 5.0

    # Phase 2: a bounded arc-straight-arc family is searched across the full
    # coarse interval. This is deterministic, much cheaper than the previous
    # cubic Cartesian grid and can recover a local S-shaped route at the
    # configured minimum radius without accepting a remote major arc.
    if not valid_candidates:
        ordered_csc_values = sorted(
            candidate_values,
            key=lambda value: (
                abs(float(value) - float(branch_seed)),
                abs(float(value) - float(branch_projection_toe)),
                abs(float(value) - float(projected_b)),
                float(value),
            ),
        )
        for toe_b in ordered_csc_values:
            register_candidate(toe_b, "csc")
            if valid_candidates:
                break

        csc_step = span / 80.0 if span > 1.0e-9 else 0.0
        for _iteration in range(CROSSOVER_CSC_REFINEMENT_ITERATIONS):
            if csc_step <= 1.0e-5 or not valid_candidates:
                break
            csc_candidates = [
                candidate for candidate in valid_candidates
                if str(candidate["connector"].get("connector_family") or "") == "bounded arc-straight-arc"
            ]
            centres = [
                float(candidate["toe_b"])
                for candidate in sorted(csc_candidates, key=_crossover_candidate_merit, reverse=True)[:CROSSOVER_CSC_REFINEMENT_SEEDS]
            ]
            local_values = set()
            for centre in centres:
                local_values.update(
                    min(max(centre + csc_step * offset / 3.0, minimum_b), maximum_b)
                    for offset in range(-3, 4)
                )
            for toe_b in sorted(local_values):
                register_candidate(toe_b, "csc")
            csc_step /= 5.0

    # Phase 3: retain the cubic only as a final, tightly bounded recovery path.
    # It is now seeded from the actual branch end as well as the Host A toe,
    # avoiding the previous thousands of unproductive candidates.
    if not valid_candidates:
        cubic_values = {branch_seed, branch_projection_toe, projected_b, minimum_b, maximum_b}
        cubic_values.update(straight_root_values)
        if span > 1.0e-9:
            coarse_step = span / 80.0
            for centre in (branch_seed, branch_projection_toe, projected_b):
                cubic_values.update(
                    min(max(centre + coarse_step * offset, minimum_b), maximum_b)
                    for offset in range(-4, 5)
                )
        for item in list(trace.get("best_rejected") or [])[:8]:
            cubic_values.add(min(max(float(item.get("toe_b") or branch_seed), minimum_b), maximum_b))
        ordered_cubic = sorted(
            cubic_values,
            key=lambda value: (
                abs(float(value) - float(branch_seed)),
                abs(float(value) - float(branch_projection_toe)),
                abs(float(value) - float(projected_b)),
                float(value),
            ),
        )[:CROSSOVER_CUBIC_FALLBACK_TOE_LIMIT]
        for toe_b in ordered_cubic:
            register_candidate(toe_b, "cubic")

    if not valid_candidates:
        trace["status"] = "rejected"
        local_radii = [
            float(candidate["connector"]["minimum_radius"])
            for candidate in scout_candidates
            if candidate["connector"].get("minimum_radius") is not None
        ]
        if local_radii:
            reason = (
                "the best local connector radius is {:.3f} mm, below the configured {:.3f} mm"
                .format(max(local_radii), float(minimum_radius))
            )
        elif scout_candidates:
            reason = "no local connector satisfies the configured geometry"
        elif failures:
            counts = {}
            for failure in failures:
                counts[failure] = counts.get(failure, 0) + 1
            reason = max(counts, key=lambda item: (counts[item], item))
        else:
            reason = "no finite local connecting route was found"
        raise ValueError(
            "Host Track B cannot resolve a valid local C10 crossover: {}. "
            "No crossover geometry was created.".format(reason)
        )

    chosen = None
    detailed_topology_failures = []
    for candidate in sorted(valid_candidates, key=_crossover_candidate_merit, reverse=True):
        try:
            _crossover_validate_topology(
                candidate["connector"], candidate.get("topology_context"), detailed=True
            )
        except Exception as error:
            detailed_topology_failures.append(str(error))
            _crossover_connector_trace_record(
                candidate["toe_b"],
                str(candidate["connector"].get("connector_family") or "unknown"),
                candidate["connector"], False, str(error),
                parameter="final topology validation",
                projected_toe_b=candidate.get("projected_toe_b"),
            )
            continue
        chosen = candidate
        break
    if chosen is None:
        trace["status"] = "rejected"
        reason = detailed_topology_failures[0] if detailed_topology_failures else "no candidate passed complete crossover topology validation"
        raise ValueError(
            "Host Track B cannot resolve a valid local C10 crossover: {}. "
            "No crossover geometry was created.".format(reason)
        )
    connector = chosen["connector"]
    family = str(connector.get("connector_family") or "exact biarc")
    if family == "cubic Bezier":
        parameter = "dA={:.6f}, dB={:.6f}".format(
            float(connector.get("control_distance_a") or 0.0),
            float(connector.get("control_distance_b") or 0.0),
        )
    elif family == "bounded arc-straight-arc":
        parameter = "{} at R={:.6f}".format(
            str(connector.get("csc_path_type") or "unknown"),
            float(connector.get("csc_radius") or 0.0),
        )
    else:
        parameter = "distance ratio {:.9f}".format(float(connector.get("biarc_distance_ratio") or 1.0))
    trace["status"] = "accepted"
    trace["chosen"] = {
        "toe_b": float(chosen["toe_b"]),
        "family": family,
        "parameter": parameter,
        "length": float(connector.get("length") or 0.0),
        "minimum_radius": None if connector.get("minimum_radius") is None else float(connector.get("minimum_radius")),
        "total_sweep_degrees": math.degrees(float(connector.get("total_sweep") or 0.0)),
        "length_ratio": float(connector.get("local_length_ratio") or 0.0),
        "raw_start_heading_degrees": float(connector.get("raw_start_heading_degrees") or 0.0),
        "raw_finish_heading_degrees": float(connector.get("raw_finish_heading_degrees") or 0.0),
        "connection_start_heading_degrees": float(connector.get("connection_start_heading_degrees") or connector.get("start_heading_degrees") or 0.0),
        "connection_finish_heading_degrees": float(connector.get("connection_finish_heading_degrees") or connector.get("finish_heading_degrees") or 0.0),
        "start_tangent_reversed": bool(connector.get("start_tangent_reversed", False)),
        "finish_tangent_reversed": bool(connector.get("finish_tangent_reversed", False)),
        "connection_start_chord_dot": float(connector.get("connection_start_chord_dot") or 0.0),
        "connection_finish_chord_dot": float(connector.get("connection_finish_chord_dot") or 0.0),
        "topology_accepted": bool(connector.get("topology_accepted", False)),
        "topology_status": str(connector.get("topology_status") or ""),
        "endpoint_role_a": str(connector.get("endpoint_role_a") or ""),
        "endpoint_role_b": str(connector.get("endpoint_role_b") or ""),
        "toe_point_a_xy": connector.get("toe_point_a_xy"),
        "toe_point_b_xy": connector.get("toe_point_b_xy"),
        "branch_endpoint_a_xy": connector.get("branch_endpoint_a_xy"),
        "branch_endpoint_b_xy": connector.get("branch_endpoint_b_xy"),
        "connector_leave_dot_a": float(connector.get("connector_leave_dot_a") or 0.0),
        "connector_leave_dot_b": float(connector.get("connector_leave_dot_b") or 0.0),
        "branch_side_sign_a": int(connector.get("branch_side_sign_a") or 0),
        "branch_side_sign_b": int(connector.get("branch_side_sign_b") or 0),
        "minimum_switch_distance_a": connector.get("minimum_switch_distance_a"),
        "minimum_switch_distance_b": connector.get("minimum_switch_distance_b"),
        "connector_host_a_distance_bounds": connector.get("connector_host_a_distance_bounds"),
        "connector_host_b_distance_bounds": connector.get("connector_host_b_distance_bounds"),
    }
    return chosen


def _crossover_automatic_hand(host_a_data, host_b_data, toe_a, orientation_a):
    point_a, heading_a = interpolate_alignment_station(host_a_data, toe_a)
    travel_heading = heading_a
    if _turnout_orientation_sign(orientation_a) < 0.0:
        travel_heading += math.pi
    _station_b, point_b, _heading_b, separation = _crossover_nearest_point_on_alignment(
        host_b_data, point_a
    )
    if separation <= GEOMETRY_TOLERANCE:
        raise ValueError("The two selected host tracks coincide at the crossover reference position.")
    normal_x, normal_y = left_normal(travel_heading)
    lateral = (point_b.x - point_a.x) * normal_x + (point_b.y - point_a.y) * normal_y
    if abs(lateral) <= 1.0e-7:
        raise ValueError("The side of Host Track B is ambiguous at the crossover reference position.")
    return TURNOUT_HAND_LEFT if lateral > 0.0 else TURNOUT_HAND_RIGHT


def _crossover_orientation_b(host_a_data, host_b_data, toe_a, orientation_a):
    point_a, heading_a = interpolate_alignment_station(host_a_data, toe_a)
    station_b, _point_b, heading_b, _distance = _crossover_nearest_point_on_alignment(host_b_data, point_a)
    travel_a = heading_a if _turnout_orientation_sign(orientation_a) > 0.0 else heading_a + math.pi
    candidates = []
    for orientation in (TURNOUT_ORIENTATION_FACING, TURNOUT_ORIENTATION_TRAILING):
        travel_b = heading_b if _turnout_orientation_sign(orientation) > 0.0 else heading_b + math.pi
        opposition_error = abs((travel_b - (travel_a + math.pi) + math.pi) % (2.0 * math.pi) - math.pi)
        candidates.append((opposition_error, orientation))
    candidates.sort(key=lambda item: (item[0], item[1]))
    if candidates[0][0] > math.radians(45.0):
        raise ValueError(
            "The host travel directions cannot provide opposed natural C10 turnout roads at this position."
        )
    return candidates[0][1], station_b, math.cos(heading_b - heading_a)


def _crossover_interval_overlap(a_start, a_finish, b_start, b_finish):
    return min(float(a_finish), float(b_finish)) - max(float(a_start), float(b_start))


def _crossover_find_existing_conflict(doc, host_obj, interval, ignored_crossover_id=None):
    host_name = str(getattr(host_obj, "Name", ""))
    ignored = str(ignored_crossover_id or "")
    for config in existing_crossover_configs(doc):
        if ignored and str(config.get("crossover_id") or "") == ignored:
            continue
        for side in ("a", "b"):
            if str(config.get("host_{}_object".format(side)) or "") != host_name:
                continue
            old_interval = config.get("host_{}_station_interval".format(side)) or []
            if len(old_interval) != 2:
                continue
            overlap = _crossover_interval_overlap(
                interval[0], interval[1], old_interval[0], old_interval[1]
            )
            if overlap > TURNOUT_OVERLAP_TOLERANCE:
                return config, overlap
    return None, 0.0


def _crossover_offset_polyline(points, offset):
    clean = _crossover_remove_duplicate_points(points)
    headings = _turnout_polyline_headings(clean)
    result = []
    for point, heading in zip(clean, headings):
        normal_x, normal_y = left_normal(heading)
        result.append(
            _crossover_point(
                point.x + float(offset) * normal_x,
                point.y + float(offset) * normal_y,
            )
        )
    return result


def _crossover_connector_rail_shape(points, dimensions, z_height):
    gauge = float(dimensions["gauge"])
    width = float(dimensions["rail_head_width"])
    offsets = (
        ("left running rail gauge face", 0.5 * gauge),
        ("left running rail outer face", 0.5 * gauge + width),
        ("right running rail gauge face", -0.5 * gauge),
        ("right running rail outer face", -0.5 * gauge - width),
    )
    wires = []
    for _name, offset in offsets:
        wires.append(_turnout_wire(_crossover_offset_polyline(points, offset), z_height))
    return _turnout_compound(wires, "crossover connecting-road rail geometry")


def _crossover_cross_mark(point, heading, half_width, z_height):
    normal_x, normal_y = left_normal(heading)
    start = _crossover_point(point.x - half_width * normal_x, point.y - half_width * normal_y)
    finish = _crossover_point(point.x + half_width * normal_x, point.y + half_width * normal_y)
    return _turnout_wire([start, finish], z_height)


def _crossover_make_connector_shapes(connector, template_width, template_thickness, dimensions):
    points = connector["points"]
    headings = _turnout_polyline_headings(points)
    solid = create_template_shape(points, headings, template_width, template_thickness)
    face = create_template_plan_face(points, headings, template_width)
    engraving_z = template_thickness + CENTRELINE_LIFT + 0.03
    rail = _crossover_connector_rail_shape(points, dimensions, engraving_z)
    centre = _turnout_wire(points, engraving_z + 0.01)
    marks = [centre]
    marks.append(_crossover_cross_mark(points[0], headings[0], 0.5 * template_width, engraving_z + 0.01))
    marks.append(_crossover_cross_mark(points[-1], headings[-1], 0.5 * template_width, engraving_z + 0.01))
    datum = _turnout_compound(marks, "crossover connector construction datums")
    return {
        "solid": solid,
        "face": face,
        "rail": rail,
        "datum": datum,
        "headings": headings,
    }


def _next_crossover_number(doc):
    used = set()
    for obj in list(doc.Objects):
        value = object_string_property(obj, CROSSOVER_ID_PROPERTY, "")
        match = re.search(r"([0-9]+)$", value)
        if match:
            used.add(int(match.group(1)))
    number = 1
    while number in used:
        number += 1
    return number


def _crossover_number_from_identifier(crossover_id):
    match = re.search(r"([0-9]+)$", str(crossover_id or ""))
    if not match:
        raise ValueError("The crossover identifier does not contain a stable feature number.")
    return int(match.group(1))


def _crossover_add_identity_properties(obj, crossover_id, config, configuration_json=None, write_statistics=None):
    properties = [
        ensure_property(obj, "App::PropertyString", CROSSOVER_ID_PROPERTY, "Crossover identity", "Stable crossover identifier"),
        ensure_property(obj, "App::PropertyString", "CrossoverHostA", "Crossover identity", "Host Track A centreline object"),
        ensure_property(obj, "App::PropertyString", "CrossoverHostB", "Crossover identity", "Host Track B centreline object"),
        ensure_property(obj, "App::PropertyString", "CrossoverArrangement", "Crossover identity", "Facing or trailing arrangement"),
        ensure_property(obj, "App::PropertyString", "CrossoverHanding", "Crossover identity", "Natural C10 turnout handing"),
        ensure_property(obj, "App::PropertyLength", "CrossoverReferenceChainage", "Crossover identity", "Reference switch-toe chainage on Host Track A"),
        ensure_property(obj, "App::PropertyLength", "CrossoverMinimumRadius", "Crossover diagnostics", "Minimum sampled radius across both turnout roads and connector"),
        ensure_property(obj, "App::PropertyString", "CrossoverTimberingStatus", "Crossover timbering", "Unresolved crossover timber-resolution status"),
        ensure_property(obj, "App::PropertyString", CROSSOVER_TIMBER_ANALYSIS_STATUS_PROPERTY, "Crossover timber analysis", "Read-only timber-analysis status"),
        ensure_property(obj, "App::PropertyString", CROSSOVER_TIMBER_ANALYSIS_SIGNATURE_PROPERTY, "Crossover timber analysis", "Stable analyser geometry signature"),
        ensure_property(obj, "App::PropertyString", CHAIR_ANALYSIS_STATUS_PROPERTY, "Chair analysis", "Current logical chair-position analysis status"),
        ensure_property(obj, "App::PropertyString", CHAIR_ANALYSIS_SIGNATURE_PROPERTY, "Chair analysis", "Stable rail, timber and chair-setting signature"),
        ensure_property(obj, "App::PropertyInteger", "CrossoverChairPositionCount", "Chair analysis", "Number of logical chair positions in the latest analysis"),
        ensure_property(obj, "App::PropertyInteger", "CrossoverChairCriticalCount", "Chair analysis", "Number of production-critical logical chair findings"),
        ensure_property(obj, "App::PropertyInteger", "CrossoverTimberConflictCount", "Crossover timber analysis", "Production-conflict finding count"),
        ensure_property(obj, "App::PropertyInteger", "CrossoverTimberCriticalCount", "Crossover timber analysis", "Production-critical finding count"),
        ensure_property(obj, "App::PropertyString", CROSSOVER_SHARED_TIMBER_STATUS_PROPERTY, "Crossover shared timbers", "Complete shared long-timber envelope status"),
        ensure_property(obj, "App::PropertyString", CROSSOVER_SHARED_TIMBER_SIGNATURE_PROPERTY, "Crossover shared timbers", "Stable shared-timber resolution signature"),
        ensure_property(obj, "App::PropertyInteger", "CrossoverSharedTimberCount", "Crossover shared timbers", "Number of automatically created shared long and envelope timbers"),
        ensure_property(obj, "App::PropertyInteger", "CrossoverEnvelopeSharedTimberCount", "Crossover shared timbers", "Number of shared timbers generated through the crossover-road envelope"),
        ensure_property(obj, "App::PropertyInteger", "CrossoverPlainConnectorTimberCount", "Crossover shared timbers", "Number of nominal-width connector sleepers generated after clear return"),
        ensure_property(obj, "App::PropertyInteger", "CrossoverEnvelopeUnresolvedCount", "Crossover shared timbers", "Number of unresolved shared-envelope positions"),
        ensure_property(obj, "App::PropertyInteger", "CrossoverSharedTimberConsumedCount", "Crossover shared timbers", "Number of inherited timber records replaced by shared long timbers"),
        ensure_property(obj, "App::PropertyString", CROSSOVER_B3_STATUS_PROPERTY, "Crossover timber adjustment", "Controlled interlacing and longitudinal timber-movement status"),
        ensure_property(obj, "App::PropertyString", CROSSOVER_B3_SIGNATURE_PROPERTY, "Crossover timber adjustment", "Stable timber-adjustment resolution signature"),
        ensure_property(obj, "App::PropertyInteger", "CrossoverB3InterlacedPairCount", "Crossover timber adjustment", "Number of accepted interlaced A/B timber pairs"),
        ensure_property(obj, "App::PropertyInteger", "CrossoverB3ShovedTimberCount", "Crossover timber adjustment", "Number of inherited timbers moved longitudinally"),
        ensure_property(obj, "App::PropertyInteger", "CrossoverB3UnresolvedCount", "Crossover timber adjustment", "Number of unresolved timber-adjustment positions"),
        ensure_property(obj, "App::PropertyString", CROSSOVER_B4_STATUS_PROPERTY, "Crossover automatic timbering", "Automatic crossover timber-resolution status"),
        ensure_property(obj, "App::PropertyString", CROSSOVER_B4_SIGNATURE_PROPERTY, "Crossover automatic timbering", "Stable automatic-resolution signature"),
        ensure_property(obj, "App::PropertyInteger", "CrossoverB4SharedTimberCount", "Crossover automatic timbering", "Number of shared long timbers in the final resolved arrangement"),
        ensure_property(obj, "App::PropertyInteger", "CrossoverB4InterlacedPairCount", "Crossover automatic timbering", "Number of accepted interlaced A/B timber pairs"),
        ensure_property(obj, "App::PropertyInteger", "CrossoverB4ShovedTimberCount", "Crossover automatic timbering", "Number of inherited timbers moved longitudinally"),
        ensure_property(obj, "App::PropertyInteger", "CrossoverB4UnresolvedCount", "Crossover automatic timbering", "Number of unresolved automatic-resolution positions"),
        ensure_property(obj, "App::PropertyString", CROSSOVER_INTEGRATION_STATUS_PROPERTY, "Crossover host integration", "Reversible host-template integration status"),
        ensure_property(obj, "App::PropertyString", CROSSOVER_INTEGRATION_SIGNATURE_PROPERTY, "Crossover host integration", "Stable host-integration signature"),
        ensure_property(obj, "App::PropertyBool", "CrossoverHostIntegrationActive", "Crossover host integration", "True when the resolved crossover has replaced affected host-template production records"),
        ensure_property(obj, "App::PropertyInteger", "CrossoverIntegratedObjectCount", "Crossover host integration", "Number of generated integration objects"),
        ensure_property(obj, "App::PropertyBool", "CrossoverProductionReady", "Crossover production", "True only after host integration and chair validation are complete"),
        ensure_property(obj, "App::PropertyString", CROSSOVER_CONFIGURATION_PROPERTY, "Crossover identity", "Validated managed-crossover configuration"),
    ]
    chair_summary = dict(config.get("chair_analysis_summary") or {})
    summary = dict(config.get("timber_analysis_summary") or {})
    shared_summary = dict(config.get("shared_timber_summary") or {})
    b3_summary = dict(config.get("b3_summary") or {})
    b4_summary = dict(config.get("b4_summary") or {})
    minimum_radius = config.get("minimum_resulting_radius")
    values = {
        CROSSOVER_ID_PROPERTY: str(crossover_id),
        "CrossoverHostA": str(config.get("host_a_object") or ""),
        "CrossoverHostB": str(config.get("host_b_object") or ""),
        "CrossoverArrangement": str(config.get("arrangement") or ""),
        "CrossoverHanding": str(config.get("handing") or ""),
        "CrossoverReferenceChainage": float(config.get("toe_chainage_a") or 0.0),
        "CrossoverMinimumRadius": float(minimum_radius) if minimum_radius is not None else 0.0,
        "CrossoverTimberingStatus": str(config.get("timbering_status") or CROSSOVER_TIMBER_STATUS_UNRESOLVED),
        CROSSOVER_TIMBER_ANALYSIS_STATUS_PROPERTY: str(config.get("timber_analysis_status") or CROSSOVER_TIMBER_ANALYSIS_STATUS_NOT_ANALYSED),
        CROSSOVER_TIMBER_ANALYSIS_SIGNATURE_PROPERTY: str(config.get("timber_analysis_signature") or ""),
        CHAIR_ANALYSIS_STATUS_PROPERTY: str(config.get("chair_analysis_status") or CHAIR_STATUS_NOT_ANALYSED),
        CHAIR_ANALYSIS_SIGNATURE_PROPERTY: str(config.get("chair_analysis_signature") or ""),
        "CrossoverChairPositionCount": int(chair_summary.get("chair_position_count") or 0),
        "CrossoverChairCriticalCount": int((chair_summary.get("severity_counts") or {}).get(CHAIR_SEVERITY_CRITICAL) or 0),
        "CrossoverTimberConflictCount": int(summary.get("production_conflicts") or 0),
        "CrossoverTimberCriticalCount": int(summary.get("production_critical_conflicts") or 0),
        CROSSOVER_SHARED_TIMBER_STATUS_PROPERTY: str(config.get("shared_timber_status") or CROSSOVER_SHARED_TIMBER_STATUS_NOT_APPLIED),
        CROSSOVER_SHARED_TIMBER_SIGNATURE_PROPERTY: str(config.get("shared_timber_signature") or ""),
        "CrossoverSharedTimberCount": int(shared_summary.get("shared_timber_count") or 0),
        "CrossoverEnvelopeSharedTimberCount": int(shared_summary.get("envelope_shared_timber_count") or 0),
        "CrossoverPlainConnectorTimberCount": int(shared_summary.get("plain_connector_timber_count") or 0),
        "CrossoverEnvelopeUnresolvedCount": int(shared_summary.get("envelope_unresolved_station_count") or 0),
        "CrossoverSharedTimberConsumedCount": int(shared_summary.get("consumed_inherited_timber_count") or 0),
        CROSSOVER_B3_STATUS_PROPERTY: str(config.get("b3_status") or CROSSOVER_B3_STATUS_NOT_APPLIED),
        CROSSOVER_B3_SIGNATURE_PROPERTY: str(config.get("b3_signature") or ""),
        "CrossoverB3InterlacedPairCount": int(b3_summary.get("interlaced_pair_count") or 0),
        "CrossoverB3ShovedTimberCount": int(b3_summary.get("shoved_timber_count") or 0),
        "CrossoverB3UnresolvedCount": int(b3_summary.get("unresolved_count") or 0),
        CROSSOVER_B4_STATUS_PROPERTY: str(config.get("b4_status") or CROSSOVER_B4_STATUS_NOT_APPLIED),
        CROSSOVER_B4_SIGNATURE_PROPERTY: str(config.get("b4_signature") or ""),
        "CrossoverB4SharedTimberCount": int(b4_summary.get("shared_timber_count") or 0),
        "CrossoverB4InterlacedPairCount": int(b4_summary.get("interlaced_pair_count") or 0),
        "CrossoverB4ShovedTimberCount": int(b4_summary.get("shoved_timber_count") or 0),
        "CrossoverB4UnresolvedCount": int(b4_summary.get("unresolved_count") or 0),
        CROSSOVER_INTEGRATION_STATUS_PROPERTY: str(config.get("integration_status") or CROSSOVER_INTEGRATION_STATUS_NOT_INTEGRATED),
        CROSSOVER_INTEGRATION_SIGNATURE_PROPERTY: str(config.get("integration_signature") or ""),
        "CrossoverHostIntegrationActive": bool(config.get("integration_active", False)),
        "CrossoverIntegratedObjectCount": int((config.get("integration_summary") or {}).get("integration_object_count") or 0),
        "CrossoverProductionReady": bool(config.get("production_ready", False)),
        CROSSOVER_CONFIGURATION_PROPERTY: configuration_json if configuration_json is not None else json.dumps(config, sort_keys=True),
    }
    for name, value in values.items():
        _set_persistent_property_if_changed(obj, name, value, write_statistics)
    set_read_only(obj, properties)


def _crossover_add_internal_turnout_properties(obj, crossover_id, side, turnout_config):
    properties = [
        ensure_property(obj, "App::PropertyString", "CrossoverInternalTurnoutID", "Crossover turnout", "Stable internal turnout identity within the crossover"),
        ensure_property(obj, "App::PropertyString", "CrossoverInternalTurnoutSide", "Crossover turnout", "Host side A or B"),
        ensure_property(obj, "App::PropertyString", "CrossoverInternalTurnoutConfigurationJSON", "Crossover turnout", "Source-driven internal C10 turnout configuration"),
    ]
    obj.CrossoverInternalTurnoutID = str(turnout_config.get("turnout_id") or "")
    obj.CrossoverInternalTurnoutSide = str(side)
    obj.CrossoverInternalTurnoutConfigurationJSON = json.dumps(turnout_config, sort_keys=True)
    _crossover_add_identity_properties(obj, crossover_id, {
        "host_a_object": turnout_config.get("host_object") if str(side) == "A" else "",
        "host_b_object": turnout_config.get("host_object") if str(side) == "B" else "",
        "arrangement": "Internal natural C10 turnout",
        "handing": turnout_config.get("handing"),
        "toe_chainage_a": turnout_config.get("toe_chainage", 0.0),
        "minimum_resulting_radius": turnout_config.get("turnout_minimum_radius_sampled"),
        "timbering_status": CROSSOVER_TIMBER_STATUS_UNRESOLVED,
        "production_ready": False,
    })
    set_read_only(obj, properties)


def existing_crossover_configs(doc):
    entries = []
    for obj in list(doc.Objects):
        if object_string_property(obj, "GeneratedRole", "") != CROSSOVER_SETTINGS_ROLE:
            continue
        stored = object_string_property(obj, CROSSOVER_CONFIGURATION_PROPERTY, "")
        try:
            config = json.loads(stored)
        except Exception:
            config = {}
        if isinstance(config, dict) and config.get("crossover_id"):
            entries.append(config)
    return sorted(entries, key=lambda item: str(item.get("crossover_id") or ""))


def crossover_config_by_id(doc, crossover_id):
    identifier = str(crossover_id or "").strip()
    for config in existing_crossover_configs(doc):
        if str(config.get("crossover_id") or "") == identifier:
            return dict(config)
    return None


def _crossover_current_catalogue(doc, set_id):
    return [
        config for config in existing_crossover_configs(doc)
        if str(config.get("template_set_id") or "") == str(set_id or "")
    ]


def _crossover_store_catalogue(doc, set_id, write_statistics=None):
    settings = settings_for_template_set(doc, set_id)
    if settings is None:
        raise ValueError("The selected template set has no recognised settings object.")
    prop = ensure_property(
        settings,
        "App::PropertyString",
        CROSSOVER_CATALOGUE_PROPERTY,
        "Crossover manager",
        "Validated managed REA C10 crossovers on this generated template set",
    )
    payload = json.dumps(_crossover_current_catalogue(doc, set_id), sort_keys=True)
    _set_persistent_property_if_changed(
        settings, CROSSOVER_CATALOGUE_PROPERTY, payload, write_statistics
    )
    set_read_only(settings, [prop])


def _crossover_objects(doc, crossover_id):
    identifier = str(crossover_id or "").strip()
    return [
        obj for obj in list(doc.Objects)
        if object_string_property(obj, CROSSOVER_ID_PROPERTY, "") == identifier
    ]


def _crossover_record(obj, role, subtype, category, selection_key, config, shape, number, thickness):
    route_name = "{} to {}".format(config.get("host_a_track_name", "Host A"), config.get("host_b_track_name", "Host B"))
    return {
        "role": role,
        "subtype": subtype,
        "category": category,
        "selection_key": selection_key,
        "route_id": str(config.get("crossover_id") or ""),
        "route_name": route_name,
        "track_number": 0,
        "track_name": "Managed crossover",
        "platform_number": 0,
        "platform_name": "",
        "section_number": 0,
        "travel_order_number": 0,
        "feature_number": int(number),
        "section_length": float(config.get("overall_crossover_length") or 0.0),
        "template_thickness": float(thickness),
        "source_name": str(obj.Name),
        "source_label": str(getattr(obj, "Label", obj.Name)),
        "shape": shape.copy(),
    }


def _crossover_add_feature(
    doc, group, crossover_id, config, role, subtype, label, stem, shape,
    category, selection_key, number, thickness,
):
    obj = doc.addObject("Part::Feature", unique_internal_name(doc, "{}_{}".format(stem, crossover_id.replace("-", "_"))))
    obj.Label = label
    obj.Shape = shape
    tag_generated_object(obj, role, config["template_set_id"])
    tag_route_metadata(obj, crossover_id, "Managed REA C10 crossover")
    tag_export_metadata(
        obj, subtype, category, feature_number=number,
        section_length=config["overall_crossover_length"],
    )
    _crossover_add_identity_properties(obj, crossover_id, config)
    group.addObject(obj)
    return obj, _crossover_record(obj, role, subtype, category, selection_key, config, shape, number, thickness)


def _crossover_minimum_radius_value(*values):
    finite = [float(value) for value in values if value is not None and math.isfinite(float(value))]
    return min(finite) if finite else None


def solve_rea_c10_crossover_geometry(
    doc,
    host_a,
    host_b,
    reference_chainage,
    arrangement=CROSSOVER_ARRANGEMENT_FACING,
    handing=CROSSOVER_HAND_AUTO,
    track_gauge=TURNOUT_DEFAULT_GAUGE,
    flangeway=TURNOUT_DEFAULT_FLANGEWAY,
    minimum_radius=CROSSOVER_DEFAULT_MINIMUM_RADIUS,
    ignored_crossover_id=None,
    ignored_turnout_id=None,
):
    """Resolve both natural C10 turnouts and the exact G1 connecting road without document changes."""
    if host_a is None or host_b is None:
        raise ValueError("Select both Host Track A and Host Track B.")
    if str(getattr(host_a, "Name", "")) == str(getattr(host_b, "Name", "")):
        raise ValueError("Host Track A and Host Track B must be different generated centrelines.")
    if not is_turnout_host_centreline(host_a) or not is_turnout_host_centreline(host_b):
        raise ValueError("Both crossover hosts must be recognised generated track centrelines.")
    set_a = object_string_property(host_a, "TemplateSetID", "")
    set_b = object_string_property(host_b, "TemplateSetID", "")
    if not set_a or set_a != set_b:
        raise ValueError("Both crossover hosts must belong to the same identified template set.")
    arrangement = str(arrangement)
    if arrangement not in (CROSSOVER_ARRANGEMENT_FACING, CROSSOVER_ARRANGEMENT_TRAILING):
        raise ValueError("Crossover arrangement must be facing or trailing.")
    minimum_radius = float(minimum_radius)
    if not math.isfinite(minimum_radius) or minimum_radius < CROSSOVER_MINIMUM_ALLOWED_RADIUS:
        raise ValueError(
            "Minimum resulting radius must be at least {:.3f} mm.".format(CROSSOVER_MINIMUM_ALLOWED_RADIUS)
        )
    dimensions = rea_c10_dimensions(track_gauge, flangeway)
    host_a_data = turnout_host_alignment(host_a)
    host_b_data = turnout_host_alignment(host_b)
    orientation_a = (
        TURNOUT_ORIENTATION_FACING
        if arrangement == CROSSOVER_ARRANGEMENT_FACING
        else TURNOUT_ORIENTATION_TRAILING
    )
    minimum_a, maximum_a = turnout_valid_toe_range(host_a_data["total"], dimensions, orientation_a)
    toe_a = float(reference_chainage)
    if not math.isfinite(toe_a):
        raise ValueError("Reference chainage must be a finite number.")
    if maximum_a < minimum_a - GEOMETRY_TOLERANCE:
        raise ValueError("Host Track A is too short for a complete natural REA C10 turnout.")
    if toe_a < minimum_a - 1.0e-7 or toe_a > maximum_a + 1.0e-7:
        raise ValueError(
            "Host Track A reference chainage must be between {:.3f} and {:.3f} mm.".format(minimum_a, maximum_a)
        )
    orientation_b, projected_station_b, relative_direction_cosine = _crossover_orientation_b(
        host_a_data, host_b_data, toe_a, orientation_a
    )
    automatic_hand = _crossover_automatic_hand(host_a_data, host_b_data, toe_a, orientation_a)
    if str(handing) == CROSSOVER_HAND_AUTO:
        resolved_hand = automatic_hand
    elif str(handing) in (TURNOUT_HAND_LEFT, TURNOUT_HAND_RIGHT):
        resolved_hand = str(handing)
        if resolved_hand != automatic_hand:
            raise ValueError(
                "The manual {} override turns away from Host Track B; use {} or Automatic handing.".format(
                    resolved_hand, automatic_hand
                )
            )
    else:
        raise ValueError("Crossover handing must be automatic, Left-hand or Right-hand.")

    point_a, heading_a = interpolate_alignment_station(host_a_data, toe_a)
    projected_b, point_b, heading_b, track_separation = _crossover_nearest_point_on_alignment(host_b_data, point_a)
    if track_separation > CROSSOVER_MAXIMUM_TRACK_SEPARATION:
        raise ValueError(
            "Track separation {:.3f} mm exceeds the managed crossover solver limit of {:.3f} mm.".format(
                track_separation, CROSSOVER_MAXIMUM_TRACK_SEPARATION
            )
        )
    if abs(relative_direction_cosine) < math.cos(math.radians(30.0)):
        raise ValueError(
            "The two host tracks are not sufficiently near-parallel at the reference position."
        )

    solved = _crossover_solve_toe_b(
        host_a_data, host_b_data, toe_a, orientation_a, orientation_b,
        resolved_hand, dimensions, minimum_radius,
    )
    toe_b = float(solved["toe_b"])
    interval_a = turnout_host_station_interval(toe_a, dimensions, orientation_a)
    interval_b = turnout_host_station_interval(toe_b, dimensions, orientation_b)
    standalone_conflict_a, overlap_a = _turnout_find_overlap(
        doc, host_a, toe_a, dimensions, orientation_a,
        ignored_turnout_id=ignored_turnout_id,
    )
    if standalone_conflict_a is not None:
        raise ValueError(
            "Host Track A turnout overlaps existing {} by {:.3f} mm.".format(
                standalone_conflict_a.get("turnout_id", "turnout"), overlap_a
            )
        )
    standalone_conflict_b, overlap_b = _turnout_find_overlap(
        doc, host_b, toe_b, dimensions, orientation_b,
        ignored_turnout_id=ignored_turnout_id,
    )
    if standalone_conflict_b is not None:
        raise ValueError(
            "Host Track B turnout overlaps existing {} by {:.3f} mm.".format(
                standalone_conflict_b.get("turnout_id", "turnout"), overlap_b
            )
        )
    crossover_conflict_a, crossover_overlap_a = _crossover_find_existing_conflict(
        doc, host_a, interval_a, ignored_crossover_id
    )
    if crossover_conflict_a is not None:
        raise ValueError(
            "Host Track A overlaps existing crossover {} by {:.3f} mm.".format(
                crossover_conflict_a.get("crossover_id", ""), crossover_overlap_a
            )
        )
    crossover_conflict_b, crossover_overlap_b = _crossover_find_existing_conflict(
        doc, host_b, interval_b, ignored_crossover_id
    )
    if crossover_conflict_b is not None:
        raise ValueError(
            "Host Track B overlaps existing crossover {} by {:.3f} mm.".format(
                crossover_conflict_b.get("crossover_id", ""), crossover_overlap_b
            )
        )

    connector = solved["connector"]
    return {
        "template_set_id": set_a,
        "host_a": host_a,
        "host_b": host_b,
        "host_a_data": host_a_data,
        "host_b_data": host_b_data,
        "dimensions": dimensions,
        "toe_chainage_a": toe_a,
        "toe_chainage_b": toe_b,
        "orientation_a": orientation_a,
        "orientation_b": orientation_b,
        "handing": resolved_hand,
        "automatic_hand": automatic_hand,
        "arrangement": arrangement,
        "track_separation": track_separation,
        "relative_host_direction_cosine": relative_direction_cosine,
        "relative_host_direction": "same" if relative_direction_cosine >= 0.0 else "opposite",
        "projected_chainage_b": projected_b,
        "projected_orientation_chainage_b": projected_station_b,
        "host_a_station_interval": interval_a,
        "host_b_station_interval": interval_b,
        "connector": connector,
        "available_host_length_a": host_a_data["total"],
        "available_host_length_b": host_b_data["total"],
        "track_gauge": float(track_gauge),
        "flangeway": float(flangeway),
        "minimum_requested_radius": minimum_radius,
    }


def _crossover_validate_pre_solved_result(
    solved, host_a, host_b, reference_chainage, arrangement, handing,
    track_gauge, flangeway, minimum_radius,
):
    """Confirm that a cached preview result exactly matches the creation request."""
    if not isinstance(solved, dict):
        raise ValueError("The cached crossover preview is not a valid solver result.")
    if solved.get("host_a") is not host_a or solved.get("host_b") is not host_b:
        raise ValueError("The cached crossover preview belongs to different host tracks.")
    if abs(float(solved.get("toe_chainage_a")) - float(reference_chainage)) > 1.0e-7:
        raise ValueError("The cached crossover preview uses a different Host A chainage.")
    if str(solved.get("arrangement")) != str(arrangement):
        raise ValueError("The cached crossover preview uses a different arrangement.")
    requested_hand = str(handing)
    if requested_hand == CROSSOVER_HAND_AUTO:
        if str(solved.get("handing")) != str(solved.get("automatic_hand")):
            raise ValueError("The cached crossover preview no longer matches automatic handing.")
    elif str(solved.get("handing")) != requested_hand:
        raise ValueError("The cached crossover preview uses a different handing.")
    numeric_checks = (
        ("track gauge", solved.get("track_gauge"), track_gauge),
        ("flangeway", solved.get("flangeway"), flangeway),
        ("minimum radius", solved.get("minimum_requested_radius"), minimum_radius),
    )
    for label, actual, expected in numeric_checks:
        if actual is None or abs(float(actual) - float(expected)) > 1.0e-7:
            raise ValueError("The cached crossover preview uses a different {}.".format(label))
    return solved


def _build_rea_c10_crossover_geometry(
    doc,
    host_a,
    host_b,
    reference_chainage,
    arrangement=CROSSOVER_ARRANGEMENT_FACING,
    handing=CROSSOVER_HAND_AUTO,
    track_gauge=TURNOUT_DEFAULT_GAUGE,
    flangeway=TURNOUT_DEFAULT_FLANGEWAY,
    minimum_radius=CROSSOVER_DEFAULT_MINIMUM_RADIUS,
    crossover_id=None,
    pre_solved=None,
    ignored_turnout_id=None,
    ignored_crossover_id=None,
    turnout_a_id_override=None,
):
    if pre_solved is None:
        solved = solve_rea_c10_crossover_geometry(
            doc, host_a, host_b, reference_chainage, arrangement, handing,
            track_gauge, flangeway, minimum_radius,
            ignored_crossover_id=ignored_crossover_id,
            ignored_turnout_id=ignored_turnout_id,
        )
    else:
        solved = _crossover_validate_pre_solved_result(
            pre_solved, host_a, host_b, reference_chainage, arrangement, handing,
            track_gauge, flangeway, minimum_radius,
        )
    if crossover_id is None:
        number = _next_crossover_number(doc)
        identifier = "XO-{:03d}".format(number)
    else:
        identifier = str(crossover_id).strip()
        number = _crossover_number_from_identifier(identifier)
    turnout_a_id = str(turnout_a_id_override or "{}-A{:03d}".format(identifier, number)).strip()
    if not turnout_a_id:
        raise ValueError("The internal Host A turnout identity is empty.")
    turnout_b_id = "{}-B{:03d}".format(identifier, number)
    built_a = _build_curve_inheriting_c10_turnout(
        doc, host_a, solved["toe_chainage_a"], solved["handing"], solved["orientation_a"],
        track_gauge, flangeway,
        create_timber_references=True,
        create_timber_centres=False,
        # A8A6A timbering is explicitly unresolved reference geometry.  Avoid
        # generating hundreds of text-wire segments which are discarded from
        # production and materially slow FreeCAD shape construction.
        create_timber_numbers=False,
        create_timber_length_labels=False,
        create_construction_marks=True,
        turnout_id=turnout_a_id,
        ignored_turnout_id=ignored_turnout_id,
    )
    built_b = _build_curve_inheriting_c10_turnout(
        doc, host_b, solved["toe_chainage_b"], solved["handing"], solved["orientation_b"],
        track_gauge, flangeway,
        create_timber_references=True,
        create_timber_centres=False,
        # A8A6A timbering is explicitly unresolved reference geometry.  Avoid
        # generating hundreds of text-wire segments which are discarded from
        # production and materially slow FreeCAD shape construction.
        create_timber_numbers=False,
        create_timber_length_labels=False,
        create_construction_marks=True,
        turnout_id=turnout_b_id,
        ignored_turnout_id=ignored_turnout_id,
    )
    if abs(float(built_a["template_thickness"]) - float(built_b["template_thickness"])) > 1.0e-6:
        raise ValueError(
            "Managed crossover geometry requires equal host-template thicknesses; Host A is {:.3f} mm and Host B is {:.3f} mm.".format(
                built_a["template_thickness"], built_b["template_thickness"]
            )
        )
    # rea_c10_dimensions() intentionally exposes module_start_x/module_end_x,
    # not a derived module_length key.  A8A6A2 attempted to read the missing
    # key only after all expensive Part geometry had been built.  Resolve and
    # validate both lengths now from the actual turnout builds.
    default_module_length = (
        float(solved["dimensions"]["module_end_x"])
        - float(solved["dimensions"]["module_start_x"])
    )
    module_length_a = float(built_a["config"].get("module_length", default_module_length))
    module_length_b = float(built_b["config"].get("module_length", default_module_length))
    if module_length_a <= 0.0 or module_length_b <= 0.0:
        raise ValueError("The crossover turnout module length must be greater than zero.")
    thickness = float(built_a["template_thickness"])
    connector_width = max(float(built_a["template_width"]), float(built_b["template_width"]))
    connector_shapes = _crossover_make_connector_shapes(
        solved["connector"], connector_width, thickness, solved["dimensions"]
    )
    solid = _refine_shape(
        built_a["solid_shape"].fuse(built_b["solid_shape"]).fuse(connector_shapes["solid"])
    )
    if _shape_is_null(solid):
        raise ValueError("FreeCAD could not fuse the complete crossover template solid.")
    face = _refine_shape(
        built_a["combined_face"].fuse(built_b["combined_face"]).fuse(connector_shapes["face"])
    )
    if _shape_is_null(face):
        raise ValueError("FreeCAD could not fuse the complete crossover plan footprint.")
    outline = _outline_shape_from_face(face)
    if _shape_is_null(outline):
        raise ValueError("FreeCAD could not extract the complete crossover cutting outline.")
    rail_shape = Part.makeCompound([
        built_a["rail_shape"], built_b["rail_shape"], connector_shapes["rail"]
    ])
    if _shape_is_null(rail_shape):
        raise ValueError("FreeCAD could not compound the complete crossover rail geometry.")
    timber_shapes = [shape for shape in (built_a["timber_shape"], built_b["timber_shape"]) if not _shape_is_null(shape)]
    timber_reference_shape = Part.makeCompound(timber_shapes) if timber_shapes else None
    datum_shapes = [
        shape for shape in (built_a["datum_shape"], built_b["datum_shape"], connector_shapes["datum"])
        if not _shape_is_null(shape)
    ]
    datum_shape = Part.makeCompound(datum_shapes) if datum_shapes else None

    host_a_name = str(getattr(host_a, "Name", ""))
    host_b_name = str(getattr(host_b, "Name", ""))
    track_a_name = built_a["config"].get("track_name") or str(getattr(host_a, "Label", host_a_name))
    track_b_name = built_b["config"].get("track_name") or str(getattr(host_b, "Label", host_b_name))
    connector_radius = solved["connector"].get("minimum_radius")
    minimum_resulting_radius = _crossover_minimum_radius_value(
        built_a["config"].get("turnout_minimum_radius_sampled"),
        built_b["config"].get("turnout_minimum_radius_sampled"),
        connector_radius,
    )
    if minimum_resulting_radius is not None and minimum_resulting_radius < float(minimum_radius) - 1.0e-7:
        raise ValueError(
            "Complete crossover minimum radius {:.3f} mm is below the configured {:.3f} mm.".format(
                minimum_resulting_radius, minimum_radius
            )
        )
    config = {
        "schema_version": CROSSOVER_SCHEMA_VERSION,
        "macro_version": MACRO_VERSION_NUMBER,
        "crossover_id": identifier,
        "size": TURNOUT_SIZE_C10,
        "output_mode": CROSSOVER_OUTPUT_GEOMETRY,
        "template_set_id": solved["template_set_id"],
        "host_a_object": host_a_name,
        "host_a_label": str(getattr(host_a, "Label", host_a_name)),
        "host_a_track_name": str(track_a_name),
        "host_b_object": host_b_name,
        "host_b_label": str(getattr(host_b, "Label", host_b_name)),
        "host_b_track_name": str(track_b_name),
        "toe_chainage_a": solved["toe_chainage_a"],
        "toe_chainage_b": solved["toe_chainage_b"],
        "reference_chainage": solved["toe_chainage_a"],
        "arrangement": solved["arrangement"],
        "handing": solved["handing"],
        "orientation_a": solved["orientation_a"],
        "orientation_b": solved["orientation_b"],
        "track_gauge": float(track_gauge),
        "flangeway": float(flangeway),
        "track_separation": solved["track_separation"],
        "relative_host_direction": solved["relative_host_direction"],
        "relative_host_direction_cosine": solved["relative_host_direction_cosine"],
        "projected_chainage_b": solved["projected_chainage_b"],
        "host_a_station_interval": list(solved["host_a_station_interval"]),
        "host_b_station_interval": list(solved["host_b_station_interval"]),
        "available_host_length_a": solved["available_host_length_a"],
        "available_host_length_b": solved["available_host_length_b"],
        "connector_length": solved["connector"]["length"],
        "turnout_a_module_length": module_length_a,
        "turnout_b_module_length": module_length_b,
        "overall_crossover_length": (
            module_length_a + module_length_b + float(solved["connector"]["length"])
        ),
        "connector_minimum_radius": connector_radius,
        "minimum_resulting_radius": minimum_resulting_radius,
        "minimum_requested_radius": float(minimum_radius),
        "positional_continuity_error": solved["connector"]["position_error"],
        "tangent_continuity_error_degrees": math.degrees(max(
            solved["connector"]["start_tangent_error"],
            solved["connector"]["finish_tangent_error"],
            solved["connector"]["join_tangent_error"],
        )),
        "turnout_a_id": turnout_a_id,
        "turnout_b_id": turnout_b_id,
        "turnout_a_config": built_a["config"],
        "turnout_b_config": built_b["config"],
        "connector_point_count": len(solved["connector"]["points"]),
        "connector_topology_status": str(solved["connector"].get("topology_status") or ""),
        "connector_endpoint_role_a": str(solved["connector"].get("endpoint_role_a") or ""),
        "connector_endpoint_role_b": str(solved["connector"].get("endpoint_role_b") or ""),
        "connector_outward_heading_a_degrees": float(solved["connector"].get("outward_start_heading_degrees") or 0.0),
        "connector_outward_heading_b_degrees": float(solved["connector"].get("outward_finish_heading_degrees") or 0.0),
        "connector_leave_dot_a": float(solved["connector"].get("connector_leave_dot_a") or 0.0),
        "connector_leave_dot_b": float(solved["connector"].get("connector_leave_dot_b") or 0.0),
        "connector_width": connector_width,
        "template_thickness": thickness,
        "source": CROSSOVER_SOURCE_NOTE,
        "timbering_status": CROSSOVER_TIMBER_STATUS_UNRESOLVED,
        "timber_analysis_schema_version": CROSSOVER_TIMBER_ANALYSIS_SCHEMA_VERSION,
        "timber_analysis_status": CROSSOVER_TIMBER_ANALYSIS_STATUS_NOT_ANALYSED,
        "timber_analysis_signature": "",
        "timber_analysis_settings": default_crossover_timber_analysis_settings(),
        "timber_analysis_summary": {},
        "timber_analysis_result_cached": False,
        "shared_timber_schema_version": CROSSOVER_SHARED_TIMBER_SCHEMA_VERSION,
        "shared_timber_status": CROSSOVER_SHARED_TIMBER_STATUS_NOT_APPLIED,
        "shared_timber_signature": "",
        "shared_timber_settings": default_crossover_shared_timber_settings(),
        "shared_timber_summary": {},
        "shared_timber_result": {},
        "b3_schema_version": CROSSOVER_B3_SCHEMA_VERSION,
        "b3_status": CROSSOVER_B3_STATUS_NOT_APPLIED,
        "b3_signature": "",
        "b3_settings": default_crossover_b3_settings(),
        "b3_summary": {},
        "b3_result": {},
        "b4_schema_version": CROSSOVER_B4_SCHEMA_VERSION,
        "b4_status": CROSSOVER_B4_STATUS_NOT_APPLIED,
        "b4_signature": "",
        "b4_settings": default_crossover_b4_settings(),
        "b4_summary": {},
        "b4_result": {},
        "integration_schema_version": CROSSOVER_INTEGRATION_SCHEMA_VERSION,
        "integration_active": False,
        "integration_status": CROSSOVER_INTEGRATION_STATUS_NOT_INTEGRATED,
        "integration_signature": "",
        "integration_summary": {},
        "integration_result": {},
        "production_ready": False,
        "host_integration_allowed": False,
        "host_integration_reason": "Automatic crossover timber resolution is not yet complete",
        "template_joint_check": "Not yet asserted; host integration remains blocked",
        "section_boundary_check": "Not yet asserted; host integration remains blocked",
        "platform_formation_check": "Not asserted where no reliable host-station metadata exists",
    }
    return {
        "config": config,
        "number": number,
        "set_id": solved["template_set_id"],
        "solid_shape": solid,
        "outline_shape": outline,
        "rail_shape": rail_shape,
        "timber_reference_shape": timber_reference_shape,
        "datum_shape": datum_shape,
        "built_a": built_a,
        "built_b": built_b,
        "connector": solved["connector"],
        "template_thickness": thickness,
    }


def _crossover_apply_display_style(solid_obj, outline_obj, rail_obj, timber_obj, datum_obj):
    try:
        solid_obj.ViewObject.ShapeColor = (0.78, 0.70, 0.42)
        solid_obj.ViewObject.Transparency = 45
        outline_obj.ViewObject.LineColor = (0.95, 0.55, 0.10)
        outline_obj.ViewObject.LineWidth = 2.0
        rail_obj.ViewObject.LineColor = (0.15, 0.15, 0.15)
        rail_obj.ViewObject.LineWidth = 1.5
        if timber_obj is not None:
            timber_obj.ViewObject.LineColor = (0.75, 0.20, 0.20)
            timber_obj.ViewObject.LineWidth = 1.0
        if datum_obj is not None:
            datum_obj.ViewObject.LineColor = (0.15, 0.45, 0.85)
            datum_obj.ViewObject.LineWidth = 1.0
    except Exception:
        pass


def _commit_rea_c10_crossover_objects(doc, built):
    """Create crossover document objects inside an already-open transaction."""
    config = built["config"]
    identifier = config["crossover_id"]
    number = built["number"]
    set_id = built["set_id"]
    thickness = built["template_thickness"]

    group = doc.addObject(
        "App::DocumentObjectGroup",
        unique_internal_name(doc, "RailwayCrossover_{}".format(identifier.replace("-", "_"))),
    )
    group.Label = "{} Managed REA C10 Crossover [{}]".format(identifier, set_id)
    tag_generated_object(group, CROSSOVER_GROUP_ROLE, set_id)
    _crossover_add_identity_properties(group, identifier, config)
    parent = _turnout_group_parent(doc, set_id)
    if parent is not None:
        parent.addObject(group)

    settings_obj = doc.addObject(
        "Part::Feature",
        unique_internal_name(doc, "RailwayCrossoverSettings_{}".format(identifier.replace("-", "_"))),
    )
    settings_obj.Label = "{} Crossover Settings and Diagnostics".format(identifier)
    tag_generated_object(settings_obj, CROSSOVER_SETTINGS_ROLE, set_id)
    _crossover_add_identity_properties(settings_obj, identifier, config)
    group.addObject(settings_obj)

    for side, turnout_built, role in (
        ("A", built["built_a"], CROSSOVER_TURNOUT_A_SETTINGS_ROLE),
        ("B", built["built_b"], CROSSOVER_TURNOUT_B_SETTINGS_ROLE),
    ):
        child = doc.addObject(
            "Part::Feature",
            unique_internal_name(doc, "RailwayCrossoverTurnout{}Settings_{}".format(side, identifier.replace("-", "_"))),
        )
        child.Label = "{} Internal Turnout {} Settings".format(identifier, side)
        tag_generated_object(child, role, set_id)
        _crossover_add_internal_turnout_properties(
            child, identifier, side, turnout_built["config"]
        )
        group.addObject(child)

    solid_obj, solid_record = _crossover_add_feature(
        doc, group, identifier, config,
        CROSSOVER_TEMPLATE_ROLE, CROSSOVER_SUBTYPE_TEMPLATE,
        "{} Complete C10 Crossover Template".format(identifier),
        "RailwayCrossoverTemplate", built["solid_shape"],
        EXPORT_CATEGORY_SOLID, TURNOUT_SELECTION_TEMPLATE_3D, number, thickness,
    )
    outline_obj, outline_record = _crossover_add_feature(
        doc, group, identifier, config,
        CROSSOVER_OUTLINE_ROLE, CROSSOVER_SUBTYPE_TEMPLATE,
        "{} Crossover Cutting Footprint".format(identifier),
        "RailwayCrossoverPlanOutline", built["outline_shape"],
        EXPORT_CATEGORY_CUTTING, TURNOUT_SELECTION_TEMPLATE_2D, number, thickness,
    )
    rail_obj, rail_record = _crossover_add_feature(
        doc, group, identifier, config,
        CROSSOVER_RAIL_ROLE, CROSSOVER_SUBTYPE_RAIL,
        "{} Complete Crossover Rail Geometry".format(identifier),
        "RailwayCrossoverRailGeometry", built["rail_shape"],
        EXPORT_CATEGORY_ENGRAVING, TURNOUT_SELECTION_ENGRAVING, number, thickness,
    )
    timber_obj = None
    if built["timber_reference_shape"] is not None and not _shape_is_null(built["timber_reference_shape"]):
        timber_obj, _timber_reference_record = _crossover_add_feature(
            doc, group, identifier, config,
            CROSSOVER_TIMBER_REFERENCE_ROLE, CROSSOVER_SUBTYPE_TIMBER_REFERENCE,
            "{} UNRESOLVED Independent Turnout Timber References".format(identifier),
            "RailwayCrossoverUnresolvedTimbers", built["timber_reference_shape"],
            EXPORT_CATEGORY_ENGRAVING, TURNOUT_SELECTION_ENGRAVING, number, thickness,
        )
    datum_obj = None
    datum_record = None
    if built["datum_shape"] is not None and not _shape_is_null(built["datum_shape"]):
        datum_obj, datum_record = _crossover_add_feature(
            doc, group, identifier, config,
            CROSSOVER_DATUM_ROLE, CROSSOVER_SUBTYPE_DATUM,
            "{} Crossover Construction Datums".format(identifier),
            "RailwayCrossoverConstructionMarks", built["datum_shape"],
            EXPORT_CATEGORY_ENGRAVING, TURNOUT_SELECTION_ENGRAVING, number, thickness,
        )
    _crossover_apply_display_style(solid_obj, outline_obj, rail_obj, timber_obj, datum_obj)
    records = [solid_record, outline_record, rail_record]
    # The red independent-turnout timber overlay is a reference preview,
    # not a production catalogue record. A8A6B must replace it first.
    if datum_record is not None:
        records.append(datum_record)
    return {
        "config": config,
        "records": records,
        "group": group,
        "settings": settings_obj,
    }


def create_rea_c10_crossover(
    doc,
    host_a,
    host_b,
    reference_chainage,
    arrangement=CROSSOVER_ARRANGEMENT_FACING,
    handing=CROSSOVER_HAND_AUTO,
    track_gauge=TURNOUT_DEFAULT_GAUGE,
    flangeway=TURNOUT_DEFAULT_FLANGEWAY,
    minimum_radius=CROSSOVER_DEFAULT_MINIMUM_RADIUS,
    pre_solved=None,
):
    built = _build_rea_c10_crossover_geometry(
        doc, host_a, host_b, reference_chainage, arrangement, handing,
        track_gauge, flangeway, minimum_radius, pre_solved=pre_solved,
    )
    config = built["config"]
    set_id = built["set_id"]
    transaction_open = False
    try:
        doc.openTransaction("Create Version {} REA C10 crossover".format(MACRO_VERSION_NUMBER))
        transaction_open = True
        committed = _commit_rea_c10_crossover_objects(doc, built)
        _turnout_store_production_records(doc, set_id, committed["records"])
        _crossover_store_catalogue(doc, set_id)
        _document_recompute(doc)
        doc.commitTransaction()
        transaction_open = False
    except Exception:
        if transaction_open:
            try:
                doc.abortTransaction()
            except Exception:
                pass
        raise
    return config



def edit_rea_c10_crossover(
    doc,
    crossover_id,
    host_a,
    host_b,
    reference_chainage,
    arrangement=CROSSOVER_ARRANGEMENT_FACING,
    handing=CROSSOVER_HAND_AUTO,
    track_gauge=TURNOUT_DEFAULT_GAUGE,
    flangeway=TURNOUT_DEFAULT_FLANGEWAY,
    minimum_radius=CROSSOVER_DEFAULT_MINIMUM_RADIUS,
    pre_solved=None,
):
    """Rebuild one managed crossover transactionally while preserving its identity.

    When reversible host integration is active, the original host records and
    visibility are restored inside the same transaction before the replacement
    crossover records are committed. A failed edit therefore leaves the complete
    integrated arrangement untouched.
    """
    identifier = str(crossover_id or "").strip()
    clear_chair_analysis_display(doc, "crossover", identifier)
    original = crossover_config_by_id(doc, identifier)
    if original is None:
        raise ValueError("Crossover {} was not found.".format(identifier or "selection"))
    integration = crossover_host_integration_by_id(doc, identifier) if bool(original.get("integration_active", False)) else None
    if bool(original.get("integration_active", False)) and integration is None:
        raise ValueError("The crossover reports active host integration, but its reversible integration record is missing.")
    restored_base_records = (
        _crossover_integration_restored_records(doc, integration, restore_crossover_records=False)
        if integration is not None else None
    )

    built = _build_rea_c10_crossover_geometry(
        doc,
        host_a,
        host_b,
        reference_chainage,
        arrangement,
        handing,
        track_gauge,
        flangeway,
        minimum_radius,
        crossover_id=identifier,
        pre_solved=pre_solved,
        ignored_crossover_id=identifier,
        turnout_a_id_override=str(original.get("turnout_a_id") or ""),
    )
    config = built["config"]
    if str(config.get("template_set_id") or "") != str(original.get("template_set_id") or ""):
        raise ValueError("An existing crossover cannot move between template sets.")
    for key in (
        "extended_from_turnout_id", "extension_preserved_toe_chainage",
        "extension_preserved_handing", "extension_preserved_orientation",
        "extension_mode", "conversion_source_turnout_config",
        "preferred_reversion_side",
    ):
        if key in original:
            config[key] = original[key]
    config["timber_analysis_settings"] = normalise_crossover_timber_analysis_settings(original.get("timber_analysis_settings"))
    config["shared_timber_settings"] = normalise_crossover_shared_timber_settings(original.get("shared_timber_settings"))
    config["b3_settings"] = normalise_crossover_b3_settings(original.get("b3_settings"))
    config["b4_settings"] = normalise_crossover_b4_settings(original.get("b4_settings"))
    config["edit_revision"] = int(original.get("edit_revision") or 0) + 1
    config["edited_from_macro_version"] = str(original.get("macro_version") or "")
    config["integration_active"] = False
    config["integration_status"] = CROSSOVER_INTEGRATION_STATUS_NOT_INTEGRATED
    config["integration_signature"] = ""
    config["integration_summary"] = {}
    config["integration_result"] = {}

    old_objects = list(_crossover_objects(doc, identifier))
    old_source_names = {str(obj.Name) for obj in old_objects}
    group_roles = {CROSSOVER_INTEGRATION_GROUP_ROLE, CROSSOVER_GROUP_ROLE}
    part_names = [
        str(obj.Name) for obj in old_objects
        if object_string_property(obj, "GeneratedRole", "") not in group_roles
    ]
    group_names = [
        str(obj.Name) for obj in old_objects
        if object_string_property(obj, "GeneratedRole", "") == CROSSOVER_INTEGRATION_GROUP_ROLE
    ] + [
        str(obj.Name) for obj in old_objects
        if object_string_property(obj, "GeneratedRole", "") == CROSSOVER_GROUP_ROLE
    ]
    set_id = str(config.get("template_set_id") or "")
    transaction_open = False
    try:
        doc.openTransaction("Edit Version {} crossover {}".format(MACRO_VERSION_NUMBER, identifier))
        transaction_open = True
        committed = _commit_rea_c10_crossover_objects(doc, built)
        if integration is not None:
            for source_name, visible in dict(integration.get("source_visibility") or {}).items():
                _turnout_set_visibility(doc.getObject(source_name), visible)
        for name in part_names:
            if doc.getObject(name) is not None:
                doc.removeObject(name)
        for name in group_names:
            if doc.getObject(name) is not None:
                doc.removeObject(name)
        if restored_base_records is not None:
            retained = [
                record for record in restored_base_records
                if str(record.get("source_name") or "") not in old_source_names
            ]
            _turnout_write_production_records(doc, set_id, retained + list(committed["records"]))
        else:
            _turnout_store_production_records(doc, set_id, committed["records"], removed_source_names=old_source_names)
        _crossover_store_catalogue(doc, set_id)
        _document_recompute(doc)
        doc.commitTransaction()
        transaction_open = False
    except Exception:
        if transaction_open:
            try:
                doc.abortTransaction()
            except Exception:
                pass
        raise
    return config

def resolve_automatic_turnout_crossover_extension(
    doc,
    turnout_id,
    minimum_radius=CROSSOVER_DEFAULT_MINIMUM_RADIUS,
):
    """Find the nearest valid neighbouring host and solve a crossover without document changes.

    The source turnout supplies Host A, its exact toe chainage, orientation,
    handing, gauge and flangeway. Candidate hosts are limited to recognised
    centrelines in the same template set, ordered by physical separation at
    the turnout toe, and tried nearest-first. The existing crossover solver
    remains the authority for handing, host direction, continuity, radius,
    overlap and available-length validation.
    """
    identifier = str(turnout_id or "").strip()
    if not identifier:
        raise ValueError("Select the standalone turnout to convert.")
    original = turnout_config_by_id(doc, identifier)
    if original is None:
        raise ValueError("Turnout {} no longer exists in this document.".format(identifier))
    if turnout_integration_by_id(doc, identifier) is not None:
        raise ValueError(
            "Remove the host-template integration before converting {}. The exact original host production records must be restored first.".format(identifier)
        )

    host_a_name = str(original.get("host_object") or "")
    host_a = doc.getObject(host_a_name) if host_a_name else None
    if host_a is None or not is_turnout_host_centreline(host_a):
        raise ValueError("The original host centreline for {} is no longer available.".format(identifier))

    orientation = str(original.get("orientation") or TURNOUT_ORIENTATION_FACING)
    if orientation == TURNOUT_ORIENTATION_FACING:
        arrangement = CROSSOVER_ARRANGEMENT_FACING
    elif orientation == TURNOUT_ORIENTATION_TRAILING:
        arrangement = CROSSOVER_ARRANGEMENT_TRAILING
    else:
        raise ValueError("The selected turnout has an unrecognised orientation.")
    handing = str(original.get("handing") or "")
    if handing not in (TURNOUT_HAND_LEFT, TURNOUT_HAND_RIGHT):
        raise ValueError("The selected turnout has an unrecognised handing.")
    gauge = float(original.get("track_gauge", TURNOUT_DEFAULT_GAUGE))
    flangeway = float(original.get("flangeway", TURNOUT_DEFAULT_FLANGEWAY))
    toe = float(original.get("toe_chainage", 0.0))
    if not math.isfinite(toe):
        raise ValueError("The selected turnout has an invalid switch-toe chainage.")

    host_a_data = turnout_host_alignment(host_a)
    point_a, _heading_a = interpolate_alignment_station(host_a_data, toe)
    set_id = object_string_property(host_a, "TemplateSetID", "") or str(original.get("template_set_id") or "")
    candidates = []
    prefilter_failures = []
    for candidate in turnout_host_objects(doc):
        candidate_name = str(getattr(candidate, "Name", ""))
        if not candidate_name or candidate_name == host_a_name:
            continue
        candidate_set = object_string_property(candidate, "TemplateSetID", "")
        if set_id and candidate_set and candidate_set != set_id:
            continue
        try:
            _station, _nearest, _heading, separation = _crossover_nearest_point_on_alignment(
                turnout_host_alignment(candidate), point_a
            )
        except Exception as error:
            prefilter_failures.append((candidate_name, str(error)))
            continue
        separation = float(separation)
        if not math.isfinite(separation):
            prefilter_failures.append((candidate_name, "non-finite track separation"))
            continue
        if separation > CROSSOVER_MAXIMUM_TRACK_SEPARATION:
            prefilter_failures.append((
                candidate_name,
                "track separation {:.3f} mm exceeds {:.3f} mm".format(
                    separation, CROSSOVER_MAXIMUM_TRACK_SEPARATION
                ),
            ))
            continue
        candidates.append((separation, candidate_name, candidate))

    candidates.sort(key=lambda item: (round(float(item[0]), 9), str(item[1])))
    if not candidates:
        detail = ""
        if prefilter_failures:
            detail = "\n\nNearest-host checks:\n" + "\n".join(
                "- {}: {}".format(name, reason) for name, reason in prefilter_failures[:6]
            )
        raise ValueError(
            "No recognised neighbouring host track in the same template set is close enough to convert {} into a crossover.{}".format(
                identifier, detail
            )
        )

    solver_failures = []
    for separation, candidate_name, candidate in candidates:
        try:
            solved = solve_rea_c10_crossover_geometry(
                doc,
                host_a,
                candidate,
                toe,
                arrangement,
                handing,
                gauge,
                flangeway,
                minimum_radius,
                ignored_turnout_id=identifier,
            )
        except Exception as error:
            solver_failures.append((candidate_name, separation, str(error)))
            continue
        return {
            "turnout_id": identifier,
            "turnout_config": original,
            "host_a": host_a,
            "host_b": candidate,
            "host_b_name": candidate_name,
            "host_b_label": str(getattr(candidate, "Label", candidate_name)),
            "track_separation": float(solved.get("track_separation", separation)),
            "arrangement": arrangement,
            "handing": handing,
            "toe_chainage_a": toe,
            "toe_chainage_b": float(solved.get("toe_chainage_b", 0.0)),
            "track_gauge": gauge,
            "flangeway": flangeway,
            "minimum_radius": float(minimum_radius),
            "solved": solved,
            "rejected_nearer_hosts": list(solver_failures),
        }

    detail = "\n".join(
        "- {} ({:.3f} mm away): {}".format(name, separation, reason)
        for name, separation, reason in solver_failures[:8]
    )
    raise ValueError(
        "No neighbouring host can form a valid crossover from {} while preserving its exact toe position, {} orientation and {} handing.\n\n{}".format(
            identifier,
            orientation.lower(),
            handing,
            detail or "No candidate passed the crossover solver.",
        )
    )

def extend_turnout_to_rea_c10_crossover(
    doc,
    turnout_id,
    host_b,
    minimum_radius=CROSSOVER_DEFAULT_MINIMUM_RADIUS,
    pre_solved=None,
):
    """Replace one standalone turnout with a managed crossover in one transaction."""
    identifier = str(turnout_id or "").strip()
    if not identifier:
        raise ValueError("Select the standalone turnout to extend.")
    original = turnout_config_by_id(doc, identifier)
    if original is None:
        raise ValueError("Turnout {} no longer exists in this document.".format(identifier))
    if turnout_integration_by_id(doc, identifier) is not None:
        raise ValueError(
            "Remove the host-template integration before extending {}. The original host production records must be restored first.".format(identifier)
        )
    roles = _turnout_objects_by_role(doc, identifier)
    required_roles = (
        TURNOUT_GROUP_ROLE,
        TURNOUT_SETTINGS_ROLE,
        TURNOUT_TEMPLATE_ROLE,
        TURNOUT_OUTLINE_ROLE,
        TURNOUT_RAIL_ROLE,
    )
    missing = [role for role in required_roles if role not in roles]
    if missing:
        raise ValueError("Turnout {} is incomplete; missing {}.".format(identifier, ", ".join(missing)))

    host_a_name = str(original.get("host_object") or "")
    host_a = doc.getObject(host_a_name) if host_a_name else None
    if host_a is None or not is_turnout_host_centreline(host_a):
        raise ValueError("The original host centreline for {} is no longer available.".format(identifier))
    if host_b is None or not is_turnout_host_centreline(host_b):
        raise ValueError("Select a recognised second host centreline for the crossover.")
    if str(getattr(host_b, "Name", "")) == host_a_name:
        raise ValueError("The second host must be different from the turnout's existing host.")

    orientation = str(original.get("orientation") or TURNOUT_ORIENTATION_FACING)
    if orientation == TURNOUT_ORIENTATION_FACING:
        arrangement = CROSSOVER_ARRANGEMENT_FACING
    elif orientation == TURNOUT_ORIENTATION_TRAILING:
        arrangement = CROSSOVER_ARRANGEMENT_TRAILING
    else:
        raise ValueError("The selected turnout has an unrecognised orientation.")
    handing = str(original.get("handing") or "")
    gauge = float(original.get("track_gauge", TURNOUT_DEFAULT_GAUGE))
    flangeway = float(original.get("flangeway", TURNOUT_DEFAULT_FLANGEWAY))
    toe = float(original.get("toe_chainage", 0.0))

    built = _build_rea_c10_crossover_geometry(
        doc,
        host_a,
        host_b,
        toe,
        arrangement,
        handing,
        gauge,
        flangeway,
        minimum_radius,
        pre_solved=pre_solved,
        ignored_turnout_id=identifier,
        turnout_a_id_override=identifier,
    )
    config = built["config"]
    if str(config.get("template_set_id") or "") != str(original.get("template_set_id") or ""):
        raise ValueError("The crossover cannot move the source turnout between template sets.")
    config["extended_from_turnout_id"] = identifier
    config["extension_preserved_toe_chainage"] = toe
    config["extension_preserved_handing"] = handing
    config["extension_preserved_orientation"] = orientation
    config["extension_mode"] = "Transactional standalone-turnout replacement"
    # A8A6A6 stores the complete pre-conversion standalone configuration so a
    # later crossover-to-turnout reversal can reproduce optional timber,
    # identity-label and construction-datum outputs exactly. Older A8A6A4/A5
    # crossovers remain reversible through their stored internal turnout A
    # configuration, but naturally cannot recover options that were not saved.
    config["conversion_source_turnout_config"] = dict(original)
    config["preferred_reversion_side"] = CROSSOVER_REVERSION_SIDE_A

    old_objects = [obj for obj in list(doc.Objects) if object_string_property(obj, TURNOUT_ID_PROPERTY, "") == identifier]
    old_group_names = [
        str(obj.Name) for obj in old_objects
        if object_string_property(obj, "GeneratedRole", "") == TURNOUT_GROUP_ROLE
    ]
    old_part_names = [str(obj.Name) for obj in old_objects if str(obj.Name) not in old_group_names]
    old_source_names = {
        str(obj.Name) for obj in old_objects
        if object_string_property(obj, "GeneratedRole", "") not in (TURNOUT_GROUP_ROLE, TURNOUT_SETTINGS_ROLE)
    }
    set_id = built["set_id"]
    transaction_open = False
    try:
        doc.openTransaction(
            "Extend Version {} turnout {} to crossover".format(MACRO_VERSION_NUMBER, identifier)
        )
        transaction_open = True
        committed = _commit_rea_c10_crossover_objects(doc, built)
        for name in old_part_names:
            if doc.getObject(name) is not None:
                doc.removeObject(name)
        for name in old_group_names:
            if doc.getObject(name) is not None:
                doc.removeObject(name)
        _turnout_store_production_records(
            doc,
            set_id,
            committed["records"],
            removed_source_names=old_source_names,
        )
        _turnout_store_catalogue(doc, set_id)
        _crossover_store_catalogue(doc, set_id)
        _document_recompute(doc)
        doc.commitTransaction()
        transaction_open = False
    except Exception:
        if transaction_open:
            try:
                doc.abortTransaction()
            except Exception:
                pass
        raise
    return config


def _crossover_reversion_source_config(crossover_config, side):
    """Return the best available standalone-turnout snapshot for one side."""
    config = dict(crossover_config or {})
    resolved_side = str(side or "").strip().upper()
    if resolved_side not in (CROSSOVER_REVERSION_SIDE_A, CROSSOVER_REVERSION_SIDE_B):
        raise ValueError("Crossover reversion side must be A or B.")
    if (
        resolved_side == CROSSOVER_REVERSION_SIDE_A
        and isinstance(config.get("conversion_source_turnout_config"), dict)
    ):
        return dict(config["conversion_source_turnout_config"]), "complete source-turnout snapshot"
    key = "turnout_a_config" if resolved_side == CROSSOVER_REVERSION_SIDE_A else "turnout_b_config"
    stored = config.get(key)
    if not isinstance(stored, dict):
        raise ValueError(
            "Crossover {} has no stored internal turnout {} configuration.".format(
                config.get("crossover_id", "selection"), resolved_side
            )
        )
    return dict(stored), "stored internal crossover turnout configuration"


def _crossover_reversion_turnout_id(doc, crossover_config, side, source_config):
    """Choose a collision-free standalone identity, preserving the source ID where possible."""
    resolved_side = str(side or "").strip().upper()
    preferred = ""
    if resolved_side == CROSSOVER_REVERSION_SIDE_A:
        preferred = str(crossover_config.get("extended_from_turnout_id") or "").strip()
    if not preferred:
        candidate = str(source_config.get("turnout_id") or "").strip()
        if re.match(r"^TO-[0-9]+$", candidate):
            preferred = candidate
    if preferred:
        existing = turnout_config_by_id(doc, preferred)
        if existing is not None:
            raise ValueError(
                "Cannot restore turnout identity {} because a standalone turnout already uses it.".format(preferred)
            )
        return preferred, True
    return "TO-{:03d}".format(_next_turnout_number(doc)), False


def resolve_crossover_to_turnout_conversion(doc, crossover_id, keep_side=None):
    """Validate and build one constituent turnout entirely in memory.

    A crossover that originated from a standalone turnout automatically keeps
    side A and restores the original stable turnout identity. An independently
    created crossover requires an explicit A/B choice from the caller.
    """
    identifier = str(crossover_id or "").strip()
    if not identifier:
        raise ValueError("Select a crossover to convert back into a turnout.")
    crossover_config = crossover_config_by_id(doc, identifier)
    if crossover_config is None:
        raise ValueError("Crossover {} no longer exists in this document.".format(identifier))
    objects = _crossover_objects(doc, identifier)
    if not objects:
        raise ValueError("Crossover {} has no generated objects.".format(identifier))
    roles = {
        object_string_property(obj, "GeneratedRole", ""): obj
        for obj in objects
    }
    required = (
        CROSSOVER_GROUP_ROLE,
        CROSSOVER_SETTINGS_ROLE,
        CROSSOVER_TEMPLATE_ROLE,
        CROSSOVER_OUTLINE_ROLE,
        CROSSOVER_RAIL_ROLE,
    )
    missing = [role for role in required if role not in roles]
    if missing:
        raise ValueError(
            "Crossover {} is incomplete; missing {}.".format(identifier, ", ".join(missing))
        )
    source_turnout_id = str(crossover_config.get("extended_from_turnout_id") or "").strip()
    if source_turnout_id:
        side = CROSSOVER_REVERSION_SIDE_A
    else:
        side = str(keep_side or "").strip().upper()
        if side not in (CROSSOVER_REVERSION_SIDE_A, CROSSOVER_REVERSION_SIDE_B):
            raise ValueError(
                "Choose whether to keep the Host A or Host B turnout from this independently created crossover."
            )

    source_config, fidelity = _crossover_reversion_source_config(crossover_config, side)
    host_key = "host_a_object" if side == CROSSOVER_REVERSION_SIDE_A else "host_b_object"
    toe_key = "toe_chainage_a" if side == CROSSOVER_REVERSION_SIDE_A else "toe_chainage_b"
    orientation_key = "orientation_a" if side == CROSSOVER_REVERSION_SIDE_A else "orientation_b"
    host_name = str(crossover_config.get(host_key) or source_config.get("host_object") or "")
    host_obj = doc.getObject(host_name) if host_name else None
    if host_obj is None or not is_turnout_host_centreline(host_obj):
        raise ValueError(
            "The Host {} centreline needed to restore crossover {} is no longer available.".format(side, identifier)
        )

    turnout_id, identity_preserved = _crossover_reversion_turnout_id(
        doc, crossover_config, side, source_config
    )
    toe = float(crossover_config.get(toe_key, source_config.get("toe_chainage", 0.0)))
    orientation = str(
        crossover_config.get(orientation_key)
        or source_config.get("orientation")
        or TURNOUT_ORIENTATION_FACING
    )
    handing = str(
        source_config.get("handing")
        or crossover_config.get("handing")
        or TURNOUT_HAND_LEFT
    )
    gauge = float(source_config.get("track_gauge", crossover_config.get("track_gauge", TURNOUT_DEFAULT_GAUGE)))
    flangeway = float(source_config.get("flangeway", crossover_config.get("flangeway", TURNOUT_DEFAULT_FLANGEWAY)))

    built = _build_curve_inheriting_c10_turnout(
        doc,
        host_obj,
        toe,
        handing,
        orientation,
        gauge,
        flangeway,
        create_timber_references=bool(source_config.get("timber_outlines", source_config.get("timber_references", True))),
        create_timber_centres=bool(source_config.get("timber_centres", False)),
        create_timber_numbers=bool(source_config.get("timber_numbers", True)),
        create_timber_length_labels=bool(source_config.get("timber_length_labels", False)),
        create_construction_marks=bool(source_config.get("construction_marks", True)),
        turnout_id=turnout_id,
        ignored_turnout_id=turnout_id,
    )
    restored = built["config"]
    restored["restored_from_crossover_id"] = identifier
    restored["restored_from_crossover_side"] = side
    restored["restoration_source"] = fidelity
    restored["restored_original_turnout_id"] = source_turnout_id
    restored["restored_identity_preserved"] = bool(identity_preserved)
    return {
        "crossover_id": identifier,
        "crossover_config": crossover_config,
        "keep_side": side,
        "host": host_obj,
        "host_label": str(getattr(host_obj, "Label", host_name)),
        "turnout_id": turnout_id,
        "identity_preserved": bool(identity_preserved),
        "source_fidelity": fidelity,
        "source_turnout_id": source_turnout_id,
        "built": built,
    }


def _commit_reverted_turnout_objects(doc, built):
    """Create standalone turnout objects without opening a nested transaction."""
    config = built["config"]
    turnout_id = config["turnout_id"]
    set_id = built["set_id"]
    route_id = built["route_id"]
    route_name = built["route_name"]
    track_number = built["track_number"]
    number = built["number"]
    template_thickness = built["template_thickness"]
    combined_solid = built["solid_shape"]
    combined_outline = built["outline_shape"]
    rail_shape = built["rail_shape"]
    timber_shape = built["timber_shape"]
    timber_centre_shape = built["timber_centre_shape"]
    timber_label_shape = built["timber_label_shape"]
    datum_shape = built["datum_shape"]

    group = doc.addObject(
        "App::DocumentObjectGroup",
        unique_internal_name(doc, "RailwayTurnout_{}".format(turnout_id.replace('-', '_'))),
    )
    group.Label = "{} {} [{}]".format(turnout_id, TURNOUT_SIZE_C10, set_id)
    tag_generated_object(group, TURNOUT_GROUP_ROLE, set_id)
    _turnout_add_identity_properties(group, turnout_id, config)
    parent = _turnout_group_parent(doc, set_id)
    if parent is not None:
        parent.addObject(group)

    settings_obj = doc.addObject(
        "Part::Feature",
        unique_internal_name(doc, "RailwayTurnoutSettings_{}".format(turnout_id.replace('-', '_'))),
    )
    settings_obj.Label = "{} Turnout Settings".format(turnout_id)
    tag_generated_object(settings_obj, TURNOUT_SETTINGS_ROLE, set_id)
    _turnout_add_identity_properties(settings_obj, turnout_id, config)
    group.addObject(settings_obj)

    solid_obj = doc.addObject(
        "Part::Feature",
        unique_internal_name(doc, "RailwayTurnoutTemplate_{}".format(turnout_id.replace('-', '_'))),
    )
    solid_obj.Label = "{} C10 Turnout Template".format(turnout_id)
    solid_obj.Shape = combined_solid
    tag_generated_object(solid_obj, TURNOUT_TEMPLATE_ROLE, set_id)
    tag_route_metadata(solid_obj, route_id, route_name)
    tag_export_metadata(
        solid_obj, TURNOUT_SUBTYPE_TEMPLATE, EXPORT_CATEGORY_SOLID,
        track_number=track_number, feature_number=number,
        section_length=config["module_length"],
    )
    _turnout_add_identity_properties(solid_obj, turnout_id, config)
    group.addObject(solid_obj)

    outline_obj = doc.addObject(
        "Part::Feature",
        unique_internal_name(doc, "RailwayTurnoutPlanOutline_{}".format(turnout_id.replace('-', '_'))),
    )
    outline_obj.Label = "{} C10 Turnout Cutting Footprint".format(turnout_id)
    outline_obj.Shape = combined_outline
    tag_generated_object(outline_obj, TURNOUT_OUTLINE_ROLE, set_id)
    tag_route_metadata(outline_obj, route_id, route_name)
    tag_export_metadata(
        outline_obj, TURNOUT_SUBTYPE_TEMPLATE, EXPORT_CATEGORY_CUTTING,
        track_number=track_number, feature_number=number,
        section_length=config["module_length"],
    )
    _turnout_add_identity_properties(outline_obj, turnout_id, config)
    group.addObject(outline_obj)

    rail_obj = doc.addObject(
        "Part::Feature",
        unique_internal_name(doc, "RailwayTurnoutRailGeometry_{}".format(turnout_id.replace('-', '_'))),
    )
    rail_obj.Label = "{} C10 Rail and Centreline References".format(turnout_id)
    rail_obj.Shape = rail_shape
    tag_generated_object(rail_obj, TURNOUT_RAIL_ROLE, set_id)
    tag_route_metadata(rail_obj, route_id, route_name)
    tag_export_metadata(
        rail_obj, TURNOUT_SUBTYPE_RAIL, EXPORT_CATEGORY_ENGRAVING,
        track_number=track_number, feature_number=number,
        section_length=config["module_length"],
    )
    _turnout_add_identity_properties(rail_obj, turnout_id, config)
    group.addObject(rail_obj)

    timber_obj = _turnout_add_geometry_object(
        doc, group, turnout_id, set_id, route_id, route_name, track_number, number, config,
        TURNOUT_TIMBER_ROLE, TURNOUT_SUBTYPE_TIMBER,
        "{} C10 REA Timber Outlines".format(turnout_id),
        "RailwayTurnoutTimberOutlines", timber_shape,
    )
    timber_centre_obj = _turnout_add_geometry_object(
        doc, group, turnout_id, set_id, route_id, route_name, track_number, number, config,
        TURNOUT_TIMBER_CENTRE_ROLE, TURNOUT_SUBTYPE_TIMBER_CENTRE,
        "{} C10 Timber Centre Lines".format(turnout_id),
        "RailwayTurnoutTimberCentres", timber_centre_shape,
    )
    timber_label_obj = _turnout_add_geometry_object(
        doc, group, turnout_id, set_id, route_id, route_name, track_number, number, config,
        TURNOUT_TIMBER_LABEL_ROLE, TURNOUT_SUBTYPE_TIMBER_LABEL,
        "{} C10 Timber Identities and Lengths".format(turnout_id),
        "RailwayTurnoutTimberLabels", timber_label_shape,
    )
    datum_obj = _turnout_add_geometry_object(
        doc, group, turnout_id, set_id, route_id, route_name, track_number, number, config,
        TURNOUT_DATUM_ROLE, TURNOUT_SUBTYPE_DATUM,
        "{} C10 Construction Datums".format(turnout_id),
        "RailwayTurnoutConstructionMarks", datum_shape,
    )
    _turnout_apply_display_style(
        solid_obj, outline_obj, rail_obj, timber_obj,
        timber_centre_obj, timber_label_obj, datum_obj,
    )
    records = [
        _turnout_record(
            solid_obj, TURNOUT_TEMPLATE_ROLE, TURNOUT_SUBTYPE_TEMPLATE,
            EXPORT_CATEGORY_SOLID, TURNOUT_SELECTION_TEMPLATE_3D,
            config, combined_solid, number, template_thickness,
        ),
        _turnout_record(
            outline_obj, TURNOUT_OUTLINE_ROLE, TURNOUT_SUBTYPE_TEMPLATE,
            EXPORT_CATEGORY_CUTTING, TURNOUT_SELECTION_TEMPLATE_2D,
            config, combined_outline, number, template_thickness,
        ),
        _turnout_record(
            rail_obj, TURNOUT_RAIL_ROLE, TURNOUT_SUBTYPE_RAIL,
            EXPORT_CATEGORY_ENGRAVING, TURNOUT_SELECTION_ENGRAVING,
            config, rail_shape, number, template_thickness,
        ),
    ]
    _turnout_append_optional_record(
        records, timber_obj, TURNOUT_TIMBER_ROLE, TURNOUT_SUBTYPE_TIMBER,
        config, timber_shape, number, template_thickness,
    )
    _turnout_append_optional_record(
        records, timber_centre_obj, TURNOUT_TIMBER_CENTRE_ROLE, TURNOUT_SUBTYPE_TIMBER_CENTRE,
        config, timber_centre_shape, number, template_thickness,
    )
    _turnout_append_optional_record(
        records, timber_label_obj, TURNOUT_TIMBER_LABEL_ROLE, TURNOUT_SUBTYPE_TIMBER_LABEL,
        config, timber_label_shape, number, template_thickness,
    )
    _turnout_append_optional_record(
        records, datum_obj, TURNOUT_DATUM_ROLE, TURNOUT_SUBTYPE_DATUM,
        config, datum_shape, number, template_thickness,
    )
    return {
        "config": config,
        "records": records,
        "group": group,
        "settings": settings_obj,
    }


def convert_rea_c10_crossover_to_turnout(doc, crossover_id, keep_side=None, pre_resolved=None):
    """Replace a managed crossover with one constituent turnout atomically.

    Active crossover host integration is unwound inside the same transaction:
    original Host A and Host B production records and visibility are restored,
    integrated records are removed, and the retained turnout is committed.
    """
    resolved = pre_resolved
    if resolved is None:
        resolved = resolve_crossover_to_turnout_conversion(doc, crossover_id, keep_side)
    identifier = str(crossover_id or "").strip()
    if str(resolved.get("crossover_id") or "") != identifier:
        raise ValueError("The cached crossover-to-turnout conversion belongs to another crossover.")
    side = str(resolved.get("keep_side") or "").upper()
    requested_side = str(keep_side or "").upper()
    if requested_side and requested_side != side:
        raise ValueError("The cached crossover-to-turnout conversion keeps a different side.")

    config = crossover_config_by_id(doc, identifier)
    if config is None:
        raise ValueError("Crossover {} no longer exists in this document.".format(identifier))
    old_objects = list(_crossover_objects(doc, identifier))
    if not old_objects:
        raise ValueError("Crossover {} has no generated objects.".format(identifier))
    set_id = str(config.get("template_set_id") or "")
    if set_id != str(resolved["built"].get("set_id") or ""):
        raise ValueError("The restored turnout cannot move between template sets.")

    integration = crossover_host_integration_by_id(doc, identifier) if bool(config.get("integration_active", False)) else None
    if bool(config.get("integration_active", False)) and integration is None:
        raise ValueError("The crossover reports active host integration, but its reversible integration record is missing.")
    restored_base_records = (
        _crossover_integration_restored_records(doc, integration, restore_crossover_records=False)
        if integration is not None else None
    )
    old_source_names = {str(obj.Name) for obj in old_objects}
    group_roles = {CROSSOVER_INTEGRATION_GROUP_ROLE, CROSSOVER_GROUP_ROLE}
    part_names = [
        str(obj.Name) for obj in old_objects
        if object_string_property(obj, "GeneratedRole", "") not in group_roles
    ]
    group_names = [
        str(obj.Name) for obj in old_objects
        if object_string_property(obj, "GeneratedRole", "") == CROSSOVER_INTEGRATION_GROUP_ROLE
    ] + [
        str(obj.Name) for obj in old_objects
        if object_string_property(obj, "GeneratedRole", "") == CROSSOVER_GROUP_ROLE
    ]

    transaction_open = False
    try:
        doc.openTransaction("Convert Version {} crossover {} to turnout".format(MACRO_VERSION_NUMBER, identifier))
        transaction_open = True
        committed = _commit_reverted_turnout_objects(doc, resolved["built"])
        if integration is not None:
            for source_name, visible in dict(integration.get("source_visibility") or {}).items():
                _turnout_set_visibility(doc.getObject(source_name), visible)
        for name in part_names:
            if doc.getObject(name) is not None:
                doc.removeObject(name)
        for name in group_names:
            if doc.getObject(name) is not None:
                doc.removeObject(name)
        if restored_base_records is not None:
            retained = [
                record for record in restored_base_records
                if str(record.get("source_name") or "") not in old_source_names
            ]
            _turnout_write_production_records(doc, set_id, retained + list(committed["records"]))
        else:
            _turnout_store_production_records(doc, set_id, committed["records"], removed_source_names=old_source_names)
        _turnout_store_catalogue(doc, set_id)
        _crossover_store_catalogue(doc, set_id)
        _document_recompute(doc)
        doc.commitTransaction()
        transaction_open = False
    except Exception:
        if transaction_open:
            try:
                doc.abortTransaction()
            except Exception:
                pass
        raise
    return committed["config"]

def remove_rea_c10_crossover(doc, crossover_id):
    """Remove a crossover and restore any integrated host records atomically."""
    identifier = str(crossover_id or "").strip()
    config = crossover_config_by_id(doc, identifier)
    if config is None:
        raise ValueError("Crossover {} was not found.".format(identifier or "selection"))
    objects = list(_crossover_objects(doc, identifier))
    if not objects:
        raise ValueError("Crossover {} has no generated objects.".format(identifier))
    set_id = str(config.get("template_set_id") or "")
    integration = crossover_host_integration_by_id(doc, identifier) if bool(config.get("integration_active", False)) else None
    if bool(config.get("integration_active", False)) and integration is None:
        raise ValueError("The crossover reports active host integration, but its reversible integration record is missing.")
    restored_base_records = (
        _crossover_integration_restored_records(doc, integration, restore_crossover_records=False)
        if integration is not None else None
    )
    source_names = {str(obj.Name) for obj in objects}
    group_roles = {CROSSOVER_INTEGRATION_GROUP_ROLE, CROSSOVER_GROUP_ROLE}
    part_names = [
        str(obj.Name) for obj in objects
        if object_string_property(obj, "GeneratedRole", "") not in group_roles
    ]
    group_names = [
        str(obj.Name) for obj in objects
        if object_string_property(obj, "GeneratedRole", "") == CROSSOVER_INTEGRATION_GROUP_ROLE
    ] + [
        str(obj.Name) for obj in objects
        if object_string_property(obj, "GeneratedRole", "") == CROSSOVER_GROUP_ROLE
    ]
    transaction_open = False
    try:
        doc.openTransaction("Remove Version {} crossover {}".format(MACRO_VERSION_NUMBER, identifier))
        transaction_open = True
        if integration is not None:
            for source_name, visible in dict(integration.get("source_visibility") or {}).items():
                _turnout_set_visibility(doc.getObject(source_name), visible)
        for name in part_names:
            if doc.getObject(name) is not None:
                doc.removeObject(name)
        for name in group_names:
            if doc.getObject(name) is not None:
                doc.removeObject(name)
        if restored_base_records is not None:
            retained = [
                record for record in restored_base_records
                if str(record.get("source_name") or "") not in source_names
            ]
            _turnout_write_production_records(doc, set_id, retained)
        else:
            _turnout_store_production_records(doc, set_id, [], removed_source_names=source_names)
        _crossover_store_catalogue(doc, set_id)
        _document_recompute(doc)
        doc.commitTransaction()
        transaction_open = False
    except Exception:
        if transaction_open:
            try:
                doc.abortTransaction()
            except Exception:
                pass
        raise
    return identifier


def crossover_geometry_diagnostics_text(result):
    connector = result["connector"]
    connector_radius = connector.get("minimum_radius")
    tangent_error = math.degrees(max(
        connector["start_tangent_error"],
        connector["finish_tangent_error"],
        connector["join_tangent_error"],
    ))
    family = str(connector.get("connector_family") or "exact biarc")
    if family == "cubic Bezier":
        family_parameter = "control distances A {:.3f} mm; B {:.3f} mm".format(
            float(connector.get("control_distance_a") or 0.0),
            float(connector.get("control_distance_b") or 0.0),
        )
    elif family == "bounded arc-straight-arc":
        family_parameter = "{} at R {:.3f} mm".format(
            str(connector.get("csc_path_type") or "unknown"),
            float(connector.get("csc_radius") or 0.0),
        )
    else:
        family_parameter = "distance ratio {:.6f}".format(
            float(connector.get("biarc_distance_ratio") or 1.0)
        )
    def xy_text(value):
        if not isinstance(value, (tuple, list)) or len(value) < 2:
            return "not recorded"
        return "({:.3f}, {:.3f}) mm".format(float(value[0]), float(value[1]))
    def distance_text(value):
        return "not recorded" if value is None else "{:.3f} mm".format(float(value))
    return (
        "Track separation: {sep:.3f} mm\n"
        "Relative host direction: {relative} (cosine {cosine:.6f})\n"
        "Host A toe chainage: {toe_a:.3f} mm\n"
        "Host B toe chainage: {toe_b:.3f} mm\n"
        "Host A occupied interval: {a0:.3f} to {a1:.3f} mm\n"
        "Host B occupied interval: {b0:.3f} to {b1:.3f} mm\n"
        "Turnout handing: {hand}\n"
        "Host A orientation: {orientation_a}\n"
        "Host B orientation: {orientation_b}\n"
        "Endpoint roles: {role_a}; {role_b}\n"
        "Host A toe point: {toe_point_a}\n"
        "Host A branch-end point: {branch_a}\n"
        "Host B toe point: {toe_point_b}\n"
        "Host B branch-end point: {branch_b}\n"
        "Outward branch tangent headings: A {out_a:.3f} degrees; B {out_b:.3f} degrees\n"
        "Connector traversal tangent reversal: A {reverse_a}; B {reverse_b}\n"
        "Connector leaves away from switch toes: A dot {leave_a:.6f}; B dot {leave_b:.6f}\n"
        "Branch-side signs: A {side_a}; B {side_b}\n"
        "Topology: {topology}\n"
        "Minimum connector distance from switch regions: A {switch_a}; B {switch_b}\n"
        "Connecting-road family: {family} ({family_parameter})\n"
        "Connecting-road length: {length:.3f} mm\n"
        "Connecting-road total sampled turning: {sweep:.3f} degrees\n"
        "Connecting-road length/chord ratio: {ratio:.6f}\n"
        "Connecting-road minimum radius: {radius}\n"
        "Positional continuity error: {position:.9f} mm\n"
        "Maximum tangent continuity error: {tangent:.9f} degrees\n"
        "Available host lengths: A {host_a:.3f} mm; B {host_b:.3f} mm\n"
        "Timbering: {timber}\n"
        "Host integration: blocked until crossover timber resolution is complete"
    ).format(
        sep=result["track_separation"], relative=result["relative_host_direction"],
        cosine=result["relative_host_direction_cosine"], toe_a=result["toe_chainage_a"],
        toe_b=result["toe_chainage_b"], a0=result["host_a_station_interval"][0],
        a1=result["host_a_station_interval"][1], b0=result["host_b_station_interval"][0],
        b1=result["host_b_station_interval"][1], hand=result["handing"],
        orientation_a=result["orientation_a"], orientation_b=result["orientation_b"],
        role_a=str(connector.get("endpoint_role_a") or "Turnout A diverging branch end"),
        role_b=str(connector.get("endpoint_role_b") or "Turnout B diverging branch end"),
        toe_point_a=xy_text(connector.get("toe_point_a_xy")),
        branch_a=xy_text(connector.get("branch_endpoint_a_xy")),
        toe_point_b=xy_text(connector.get("toe_point_b_xy")),
        branch_b=xy_text(connector.get("branch_endpoint_b_xy")),
        out_a=float(connector.get("outward_start_heading_degrees") or connector.get("raw_start_heading_degrees") or 0.0),
        out_b=float(connector.get("outward_finish_heading_degrees") or connector.get("raw_finish_heading_degrees") or 0.0),
        reverse_a="yes" if bool(connector.get("start_tangent_reversed", False)) else "no",
        reverse_b="yes — traversal only" if bool(connector.get("finish_tangent_reversed", False)) else "no",
        leave_a=float(connector.get("connector_leave_dot_a") or 0.0),
        leave_b=float(connector.get("connector_leave_dot_b") or 0.0),
        side_a=int(connector.get("branch_side_sign_a") or 0),
        side_b=int(connector.get("branch_side_sign_b") or 0),
        topology=str(connector.get("topology_status") or "not validated"),
        switch_a=distance_text(connector.get("minimum_switch_distance_a")),
        switch_b=distance_text(connector.get("minimum_switch_distance_b")),
        family=family, family_parameter=family_parameter, length=connector["length"],
        sweep=math.degrees(float(connector.get("total_sweep") or 0.0)),
        ratio=float(connector.get("local_length_ratio") or 0.0),
        radius=("straight" if connector_radius is None else "{:.3f} mm".format(connector_radius)),
        position=connector["position_error"], tangent=tangent_error,
        host_a=result["available_host_length_a"], host_b=result["available_host_length_b"],
        timber=CROSSOVER_TIMBER_STATUS_UNRESOLVED,
    )



# Stage A8A6B1/A8A6B2A2 crossover timber analysis and complete shared-timber envelope. This module uses
# the already generated turnout timber metadata and station-normal mapping.  It
# deliberately performs no Part booleans and never moves, resizes, omits,
# merges, interlaces or replaces production timber geometry.


def default_crossover_timber_analysis_settings():
    return {
        "schema_version": CROSSOVER_TIMBER_ANALYSIS_SCHEMA_VERSION,
        "intersection_tolerance": CROSSOVER_TIMBER_INTERSECTION_TOLERANCE,
        "near_touching_tolerance": CROSSOVER_TIMBER_NEAR_TOUCHING_TOLERANCE,
        "minimum_clear_spacing": CROSSOVER_TIMBER_MINIMUM_CLEAR_SPACING,
        "same_station_tolerance": CROSSOVER_TIMBER_SAME_STATION_TOLERANCE,
        "maximum_advisory_skew_degrees": CROSSOVER_TIMBER_MAXIMUM_ADVISORY_SKEW_DEGREES,
        "show_conflict_markers": True,
        "show_support_markers": False,
        "cache_enabled": True,
    }


def normalise_crossover_timber_analysis_settings(source=None):
    result = default_crossover_timber_analysis_settings()
    if isinstance(source, dict):
        result.update(source)
    numeric_specs = (
        ("intersection_tolerance", 0.001, 5.0),
        ("near_touching_tolerance", 0.01, 10.0),
        ("minimum_clear_spacing", 0.01, 20.0),
        ("same_station_tolerance", 0.01, 20.0),
        ("maximum_advisory_skew_degrees", 0.1, 45.0),
    )
    for key, minimum, maximum in numeric_specs:
        try:
            value = float(result.get(key))
        except Exception:
            value = float(default_crossover_timber_analysis_settings()[key])
        if not math.isfinite(value):
            value = float(default_crossover_timber_analysis_settings()[key])
        result[key] = max(minimum, min(maximum, value))
    for key in ("show_conflict_markers", "show_support_markers", "cache_enabled"):
        result[key] = bool(result.get(key, default_crossover_timber_analysis_settings()[key]))
    result["schema_version"] = CROSSOVER_TIMBER_ANALYSIS_SCHEMA_VERSION
    if result["near_touching_tolerance"] < result["intersection_tolerance"]:
        result["near_touching_tolerance"] = result["intersection_tolerance"]
    if result["minimum_clear_spacing"] < result["intersection_tolerance"]:
        result["minimum_clear_spacing"] = result["intersection_tolerance"]
    return result


def _timber_xy(point):
    if isinstance(point, (tuple, list)) and len(point) >= 2:
        return float(point[0]), float(point[1])
    return float(point.x), float(point.y)


def _timber_point(x, y):
    return (float(x), float(y))


def _timber_add(a, b):
    return (float(a[0]) + float(b[0]), float(a[1]) + float(b[1]))


def _timber_subtract(a, b):
    return (float(a[0]) - float(b[0]), float(a[1]) - float(b[1]))


def _timber_scale(a, value):
    return (float(a[0]) * float(value), float(a[1]) * float(value))


def _timber_dot(a, b):
    return float(a[0]) * float(b[0]) + float(a[1]) * float(b[1])


def _timber_cross(a, b):
    return float(a[0]) * float(b[1]) - float(a[1]) * float(b[0])


def _timber_length(a):
    return math.hypot(float(a[0]), float(a[1]))


def _timber_distance(a, b):
    return _timber_length(_timber_subtract(a, b))


def _timber_midpoint(a, b):
    return ((float(a[0]) + float(b[0])) * 0.5, (float(a[1]) + float(b[1])) * 0.5)


def _timber_unit(a):
    length = _timber_length(a)
    if length <= 1.0e-12:
        return (1.0, 0.0)
    return (float(a[0]) / length, float(a[1]) / length)


def _timber_normalised_angle_difference(angle_a, angle_b):
    difference = abs((float(angle_a) - float(angle_b) + math.pi) % (2.0 * math.pi) - math.pi)
    return min(difference, abs(math.pi - difference))


def _timber_polygon_area(polygon):
    points = list(polygon or [])
    if len(points) < 3:
        return 0.0
    return 0.5 * sum(
        float(points[index][0]) * float(points[(index + 1) % len(points)][1])
        - float(points[(index + 1) % len(points)][0]) * float(points[index][1])
        for index in range(len(points))
    )


def _timber_polygon_centroid(polygon):
    points = list(polygon or [])
    if not points:
        return (0.0, 0.0)
    signed_area = _timber_polygon_area(points)
    if abs(signed_area) <= 1.0e-12:
        return (
            sum(float(point[0]) for point in points) / float(len(points)),
            sum(float(point[1]) for point in points) / float(len(points)),
        )
    factor = 1.0 / (6.0 * signed_area)
    cx = 0.0
    cy = 0.0
    for index, point in enumerate(points):
        following = points[(index + 1) % len(points)]
        cross = float(point[0]) * float(following[1]) - float(following[0]) * float(point[1])
        cx += (float(point[0]) + float(following[0])) * cross
        cy += (float(point[1]) + float(following[1])) * cross
    return (cx * factor, cy * factor)


def _timber_convex_hull(points):
    unique = sorted({(round(float(point[0]), 9), round(float(point[1]), 9)) for point in points or []})
    if len(unique) <= 2:
        return list(unique)

    def cross(origin, a, b):
        return _timber_cross(_timber_subtract(a, origin), _timber_subtract(b, origin))

    lower = []
    for point in unique:
        while len(lower) >= 2 and cross(lower[-2], lower[-1], point) <= 1.0e-12:
            lower.pop()
        lower.append(point)
    upper = []
    for point in reversed(unique):
        while len(upper) >= 2 and cross(upper[-2], upper[-1], point) <= 1.0e-12:
            upper.pop()
        upper.append(point)
    hull = lower[:-1] + upper[:-1]
    if _timber_polygon_area(hull) < 0.0:
        hull.reverse()
    return hull


def _timber_bbox(polygon):
    points = list(polygon or [])
    if not points:
        return (0.0, 0.0, 0.0, 0.0)
    xs = [float(point[0]) for point in points]
    ys = [float(point[1]) for point in points]
    return (min(xs), min(ys), max(xs), max(ys))


def _timber_bbox_intersects(a, b, padding=0.0):
    gap = float(padding)
    return not (
        float(a[2]) + gap < float(b[0])
        or float(b[2]) + gap < float(a[0])
        or float(a[3]) + gap < float(b[1])
        or float(b[3]) + gap < float(a[1])
    )




def _timber_bbox_minimum_distance(first, second):
    """Return an exact lower bound between two axis-aligned bounding boxes."""
    dx = max(float(first[0]) - float(second[2]), float(second[0]) - float(first[2]), 0.0)
    dy = max(float(first[1]) - float(second[3]), float(second[1]) - float(first[3]), 0.0)
    return math.hypot(dx, dy)

def _timber_point_in_convex_polygon(point, polygon, tolerance=1.0e-9):
    points = list(polygon or [])
    if len(points) < 3:
        return False
    sign = 0
    for index, start in enumerate(points):
        finish = points[(index + 1) % len(points)]
        value = _timber_cross(_timber_subtract(finish, start), _timber_subtract(point, start))
        if abs(value) <= float(tolerance):
            continue
        current = 1 if value > 0.0 else -1
        if sign and current != sign:
            return False
        sign = current
    return True


def _timber_line_intersection(a, b, c, d):
    ab = _timber_subtract(b, a)
    cd = _timber_subtract(d, c)
    denominator = _timber_cross(ab, cd)
    if abs(denominator) <= 1.0e-12:
        return _timber_midpoint(b, c)
    scale = _timber_cross(_timber_subtract(c, a), cd) / denominator
    return _timber_add(a, _timber_scale(ab, scale))


def _timber_convex_intersection(subject_polygon, clip_polygon):
    subject = list(subject_polygon or [])
    clip = list(clip_polygon or [])
    if len(subject) < 3 or len(clip) < 3:
        return []
    if _timber_polygon_area(subject) < 0.0:
        subject.reverse()
    if _timber_polygon_area(clip) < 0.0:
        clip.reverse()
    output = subject
    for index, clip_start in enumerate(clip):
        clip_finish = clip[(index + 1) % len(clip)]
        input_points = output
        output = []
        if not input_points:
            break

        def inside(point):
            return _timber_cross(
                _timber_subtract(clip_finish, clip_start),
                _timber_subtract(point, clip_start),
            ) >= -1.0e-9

        previous = input_points[-1]
        previous_inside = inside(previous)
        for current in input_points:
            current_inside = inside(current)
            if current_inside:
                if not previous_inside:
                    output.append(_timber_line_intersection(previous, current, clip_start, clip_finish))
                output.append(current)
            elif previous_inside:
                output.append(_timber_line_intersection(previous, current, clip_start, clip_finish))
            previous = current
            previous_inside = current_inside
    return _timber_convex_hull(output) if len(output) >= 3 else []


def _timber_point_segment_distance(point, start, finish):
    segment = _timber_subtract(finish, start)
    denominator = _timber_dot(segment, segment)
    if denominator <= 1.0e-18:
        return _timber_distance(point, start), start
    value = max(0.0, min(1.0, _timber_dot(_timber_subtract(point, start), segment) / denominator))
    nearest = _timber_add(start, _timber_scale(segment, value))
    return _timber_distance(point, nearest), nearest


def _timber_segments_intersect(a, b, c, d, tolerance=1.0e-9):
    ab = _timber_subtract(b, a)
    ac = _timber_subtract(c, a)
    ad = _timber_subtract(d, a)
    cd = _timber_subtract(d, c)
    ca = _timber_subtract(a, c)
    cb = _timber_subtract(b, c)
    first = _timber_cross(ab, ac)
    second = _timber_cross(ab, ad)
    third = _timber_cross(cd, ca)
    fourth = _timber_cross(cd, cb)
    return first * second <= float(tolerance) and third * fourth <= float(tolerance)


def _timber_segment_distance(a, b, c, d):
    if _timber_segments_intersect(a, b, c, d):
        point = _timber_line_intersection(a, b, c, d)
        return 0.0, point, point
    candidates = []
    for point, start, finish, reversed_pair in (
        (a, c, d, False), (b, c, d, False), (c, a, b, True), (d, a, b, True)
    ):
        distance, nearest = _timber_point_segment_distance(point, start, finish)
        candidates.append((distance, nearest, point) if reversed_pair else (distance, point, nearest))
    return min(candidates, key=lambda item: item[0])


def _timber_segments_minimum_distance(segments_a, segments_b):
    """Return the exact legacy minimum, with conservative pair pruning."""
    pairs = []
    pair_index = 0
    for segment_a in segments_a:
        bbox_a = _timber_bbox(segment_a)
        for segment_b in segments_b:
            bbox_b = _timber_bbox(segment_b)
            pairs.append((
                _timber_bbox_minimum_distance(bbox_a, bbox_b),
                pair_index,
                segment_a,
                segment_b,
            ))
            pair_index += 1
    pairs.sort(key=lambda item: (item[0], item[1]))
    best = (float("inf"), (0.0, 0.0), (0.0, 0.0))
    best_pair_index = None
    for lower_bound, original_index, segment_a, segment_b in pairs:
        if lower_bound > float(best[0]) + max(1.0e-12, abs(float(best[0])) * 1.0e-15):
            break
        candidate = _timber_segment_distance(
            segment_a[0], segment_a[1], segment_b[0], segment_b[1]
        )
        if (
            candidate[0] < best[0]
            or (candidate[0] == best[0] and (best_pair_index is None or original_index < best_pair_index))
        ):
            best = candidate
            best_pair_index = original_index
    return best


def _timber_protected_features(timber):
    identifier = str(timber.get("identifier") or "")
    section = str(timber.get("section") or "")
    suffix = str(timber.get("crossing_suffix") or "")
    features = []
    if identifier.startswith("J"):
        features.extend(["switch-front rail joint", "stock-rail support", "future joint-chair datum"])
    elif identifier == "S1":
        features.extend(["switch toe", "first slide-chair position", "switch-blade support"])
    elif identifier.startswith("S"):
        features.extend(["slide-chair position", "switch-blade support", "stock-rail special support"])
        try:
            if int(identifier[1:]) >= 11:
                features.append("switch heel approach")
        except Exception:
            pass
    elif identifier == "T1":
        features.extend(["switch heel", "closure-rail support", "stock-rail joint support"])
    elif section == "closure":
        features.extend(["closure-rail support", "stock-rail support"])
    elif section == "crossing wing front":
        features.extend(["wing-rail support", "check-rail support", "knuckle-region support"])
    elif suffix == "A":
        features.extend(["common-crossing A timber", "wing-rail support", "check-rail support", "vee-nose support"])
    elif suffix == "B":
        features.extend(["common-crossing B timber", "crossing-nose support", "splice-rail support"])
    elif section == "crossing vee":
        features.extend(["common-crossing support", "vee-rail support", "splice-rail support"])
    elif section == "exit":
        features.extend(["vee point-rail joint support", "exit rail-joint support"])
    else:
        features.append("turnout rail support")
    features.append("future special-chair datum")
    return sorted(set(features))


def _timber_record_from_layout(
    crossover_id,
    side,
    turnout_config,
    host_data,
    origin,
    reference_axis,
    timber,
):
    toe_chainage = float(turnout_config.get("toe_chainage") or 0.0)
    orientation = str(turnout_config.get("orientation") or TURNOUT_ORIENTATION_FACING)
    handing = str(turnout_config.get("handing") or TURNOUT_HAND_LEFT)
    local_outline = _turnout_timber_outline_local_points(timber)
    mapped_outline = _turnout_map_polyline(
        host_data, toe_chainage, orientation, handing, local_outline
    )
    outline = [_timber_xy(point) for point in mapped_outline]
    if outline and _timber_distance(outline[0], outline[-1]) <= 1.0e-8:
        outline.pop()
    collision_polygon = _timber_convex_hull(outline)
    x_value = float(timber["x"])
    half_width = 0.5 * float(timber["width"])
    near_y = float(timber["near_y"])
    far_y = float(timber["far_y"])

    def mapped(local_x, local_y):
        return _timber_xy(map_turnout_local_point(
            host_data, toe_chainage, orientation, handing, local_x, local_y
        ))

    near_start = mapped(x_value - half_width, near_y)
    near_finish = mapped(x_value + half_width, near_y)
    far_start = mapped(x_value - half_width, far_y)
    far_finish = mapped(x_value + half_width, far_y)
    near_midpoint = _timber_midpoint(near_start, near_finish)
    far_midpoint = _timber_midpoint(far_start, far_finish)
    centre = mapped(x_value, float(timber["centre_y"]))
    length_axis = _timber_unit(_timber_subtract(far_midpoint, near_midpoint))
    width_axis = _timber_unit(_timber_subtract(near_finish, near_start))
    angle = math.atan2(length_axis[1], length_axis[0])
    station = toe_chainage + _turnout_orientation_sign(orientation) * x_value
    _host_point, host_heading = interpolate_alignment_station(host_data, station)
    travel_heading = host_heading if _turnout_orientation_sign(orientation) > 0.0 else host_heading + math.pi
    stable_identity = "{}:{}:{}".format(crossover_id, side, timber["identifier"])
    protected_features = _timber_protected_features(timber)
    return {
        "stable_identity": stable_identity,
        "parent_turnout_identity": str(turnout_config.get("turnout_id") or "{}-{}".format(crossover_id, side)),
        "crossover_identity": str(crossover_id),
        "turnout_side": str(side),
        "identifier": str(timber["identifier"]),
        "prototype_reference": str(timber["identifier"]),
        "sequence": int(timber.get("sequence") or 0),
        "section": str(timber.get("section") or ""),
        "centre": [centre[0], centre[1]],
        "angle_radians": angle,
        "angle_degrees": math.degrees(angle),
        "width": float(timber["width"]),
        "length": float(timber["length"]),
        "outline_polygon": [[point[0], point[1]] for point in outline],
        "collision_polygon": [[point[0], point[1]] for point in collision_polygon],
        "bounding_box": list(_timber_bbox(collision_polygon)),
        "near_end_segment": [[near_start[0], near_start[1]], [near_finish[0], near_finish[1]]],
        "far_end_segment": [[far_start[0], far_start[1]], [far_finish[0], far_finish[1]]],
        "side_segments": [
            [[near_start[0], near_start[1]], [far_start[0], far_start[1]]],
            [[near_finish[0], near_finish[1]], [far_finish[0], far_finish[1]]],
        ],
        "length_axis": [length_axis[0], length_axis[1]],
        "width_axis": [width_axis[0], width_axis[1]],
        "longitudinal_reference_axis": [reference_axis[0], reference_axis[1]],
        "longitudinal_station": _timber_dot(_timber_subtract(centre, origin), reference_axis),
        "host_chainage": station,
        "local_rail_heading_radians": travel_heading,
        "local_rail_heading_degrees": math.degrees(travel_heading),
        "source_configuration": {
            "source_note": str(timber.get("source_note") or ""),
            "crossing_suffix": str(timber.get("crossing_suffix") or ""),
            "local_x": x_value,
            "local_near_y": near_y,
            "local_far_y": far_y,
            "length_prototype_inches": float(timber.get("length_prototype_inches") or 0.0),
            "turnout_geometry_revision": int(turnout_config.get("timber_geometry_revision") or TURNOUT_TIMBER_GEOMETRY_REVISION),
            "longitudinal_reference_axis": [reference_axis[0], reference_axis[1]],
        },
        "protected_support_region": True,
        "protected_features": protected_features,
        "supported_feature": ", ".join(protected_features),
        "support_zone_polygon": [[point[0], point[1]] for point in collision_polygon],
    }


def crossover_inherited_timber_records(doc, crossover_config):
    config = dict(crossover_config or {})
    identifier = str(config.get("crossover_id") or "").strip()
    if not identifier:
        raise ValueError("The crossover has no stable identity.")
    host_a = doc.getObject(str(config.get("host_a_object") or ""))
    host_b = doc.getObject(str(config.get("host_b_object") or ""))
    if host_a is None or host_b is None:
        raise ValueError("Both original crossover host centrelines must remain available for timber analysis.")
    host_data_a = turnout_host_alignment(host_a)
    host_data_b = turnout_host_alignment(host_b)
    turnout_a = dict(config.get("turnout_a_config") or {})
    turnout_b = dict(config.get("turnout_b_config") or {})
    if not turnout_a or not turnout_b:
        raise ValueError("The crossover does not contain both inherited turnout configurations.")
    dimensions = rea_c10_dimensions(
        float(config.get("track_gauge", TURNOUT_DEFAULT_GAUGE)),
        float(config.get("flangeway", TURNOUT_DEFAULT_FLANGEWAY)),
    )
    origin_vector, origin_heading = interpolate_alignment_station(
        host_data_a, float(turnout_a.get("toe_chainage") or config.get("toe_chainage_a") or 0.0)
    )
    origin = _timber_xy(origin_vector)
    if _turnout_orientation_sign(str(turnout_a.get("orientation") or config.get("orientation_a") or TURNOUT_ORIENTATION_FACING)) < 0.0:
        origin_heading += math.pi
    reference_axis = (math.cos(origin_heading), math.sin(origin_heading))
    records = []
    for side, turnout_config, host_data in (
        ("A", turnout_a, host_data_a),
        ("B", turnout_b, host_data_b),
    ):
        layout = rea_c10_timber_layout(
            dimensions,
            float(turnout_config.get("template_width") or config.get("connector_width") or DEFAULT_MAIN_TEMPLATE_WIDTH),
        )
        records.extend([
            _timber_record_from_layout(
                identifier, side, turnout_config, host_data, origin, reference_axis, timber
            )
            for timber in layout
        ])
    records.sort(key=lambda item: (float(item["longitudinal_station"]), item["stable_identity"]))
    return records



def _crossover_b2_effective_timber_records(doc, crossover_config):
    """Return the current validated A8A6B2A2 arrangement, ignoring B3."""
    config = dict(crossover_config or {})
    inherited = crossover_inherited_timber_records(doc, config)
    result = config.get("shared_timber_result")
    if not isinstance(result, dict) or not result.get("applied"):
        return inherited
    stored_signature = str(config.get("shared_timber_signature") or result.get("resolution_signature") or "")
    inherited_signature = _shared_timber_inherited_signature(config, inherited)
    if not stored_signature or str(result.get("inherited_signature") or "") != inherited_signature:
        return inherited
    expected_signature = _shared_timber_resolution_signature(
        config,
        result.get("settings"),
        inherited_signature,
        result.get("shared_timbers") or [],
        result.get("consumed_timber_identities") or [],
        result.get("plain_connector_timbers") or [],
        result.get("envelope_summary") or {},
    )
    if stored_signature != expected_signature or str(result.get("resolution_signature") or "") != expected_signature:
        return inherited
    return apply_shared_timber_result_to_records(inherited, result)


def crossover_timber_records(doc, crossover_config):
    """Return the current effective crossover timbering.

    A current B4 hybrid result takes precedence. Stale B4 metadata falls back
    safely to B3, then B2A2, then the inherited turnout arrangements.
    """
    config = dict(crossover_config or {})
    b4_result = config.get("b4_result")
    if isinstance(b4_result, dict) and b4_result.get("applied"):
        try:
            inherited = crossover_inherited_timber_records(doc, config)
            if _crossover_b4_result_is_current(config, inherited, b4_result):
                resolved = list(b4_result.get("resolved_timbers") or [])
                if resolved:
                    return resolved
        except Exception:
            pass
    base_records = _crossover_b2_effective_timber_records(doc, config)
    result = config.get("b3_result")
    if not isinstance(result, dict) or not result.get("applied"):
        return base_records
    try:
        base_signature = _b3_base_signature(config, base_records)
        expected_signature = _b3_resolution_signature(
            config,
            result.get("settings"),
            base_signature,
            result.get("resolved_timbers") or [],
            result.get("operations") or [],
            result.get("unresolved") or [],
        )
    except Exception:
        return base_records
    stored_signature = str(config.get("b3_signature") or "")
    if (
        str(result.get("base_signature") or "") != base_signature
        or str(result.get("resolution_signature") or "") != expected_signature
        or stored_signature != expected_signature
    ):
        return base_records
    resolved = list(result.get("resolved_timbers") or [])
    return resolved if resolved else base_records


def _timber_geometry_signature(crossover_config, settings, records):
    """Return the stable calculation signature, excluding display-only controls."""
    config = dict(crossover_config or {})
    calculation_settings = normalise_crossover_timber_analysis_settings(settings)
    for key in ("show_conflict_markers", "show_support_markers", "cache_enabled"):
        calculation_settings.pop(key, None)
    payload = {
        "analysis_schema_version": CROSSOVER_TIMBER_ANALYSIS_SCHEMA_VERSION,
        "crossover_id": config.get("crossover_id"),
        "macro_version": MACRO_VERSION_NUMBER,
        "settings": calculation_settings,
        "geometry": [
            {
                "id": item["stable_identity"],
                "centre": [round(float(value), 6) for value in item["centre"]],
                "angle": round(float(item["angle_radians"]), 9),
                "width": round(float(item["width"]), 6),
                "length": round(float(item["length"]), 6),
                "outline": [
                    [round(float(point[0]), 6), round(float(point[1]), 6)]
                    for point in item["collision_polygon"]
                ],
                "features": list(item.get("protected_features") or []),
            }
            for item in records
        ],
    }
    encoded = json.dumps(payload, sort_keys=True, separators=(",", ":"))
    return hashlib.sha256(encoded.encode("utf-8")).hexdigest()


def _timber_spatial_candidate_pairs(records, padding):
    if len(records) < 2:
        return []
    lengths = sorted(max(float(item["width"]), min(float(item["length"]), 80.0)) for item in records)
    cell_size = max(10.0, lengths[len(lengths) // 2])
    bins = {}
    for index, record in enumerate(records):
        bbox = record["bounding_box"]
        minimum_x = int(math.floor((float(bbox[0]) - padding) / cell_size))
        maximum_x = int(math.floor((float(bbox[2]) + padding) / cell_size))
        minimum_y = int(math.floor((float(bbox[1]) - padding) / cell_size))
        maximum_y = int(math.floor((float(bbox[3]) + padding) / cell_size))
        for cell_x in range(minimum_x, maximum_x + 1):
            for cell_y in range(minimum_y, maximum_y + 1):
                bins.setdefault((cell_x, cell_y), []).append(index)
    pairs = set()
    for indices in bins.values():
        unique = sorted(set(indices))
        for first_offset, first in enumerate(unique):
            for second in unique[first_offset + 1:]:
                pairs.add((first, second))
    return sorted(pairs)


def _timber_finding(code, severity, message, timber_a=None, timber_b=None, point=None, measurements=None):
    first_id = str((timber_a or {}).get("stable_identity") or "")
    second_id = str((timber_b or {}).get("stable_identity") or "")
    seed = "{}|{}|{}|{}".format(code, severity, first_id, second_id)
    finding_id = hashlib.sha1(seed.encode("utf-8")).hexdigest()[:12]
    if point is None:
        if timber_a and timber_b:
            point = _timber_midpoint(timber_a["centre"], timber_b["centre"])
        elif timber_a:
            point = tuple(timber_a["centre"])
        else:
            point = (0.0, 0.0)
    return {
        "finding_id": finding_id,
        "code": str(code),
        "severity": str(severity),
        "message": str(message),
        "timber_a": first_id,
        "timber_b": second_id,
        "turnout_a_side": str((timber_a or {}).get("turnout_side") or ""),
        "turnout_b_side": str((timber_b or {}).get("turnout_side") or ""),
        "marker_point": [float(point[0]), float(point[1])],
        "timber_a_centre": list((timber_a or {}).get("centre") or []),
        "timber_b_centre": list((timber_b or {}).get("centre") or []),
        "protected_features": sorted(set(
            list((timber_a or {}).get("protected_features") or [])
            + list((timber_b or {}).get("protected_features") or [])
        )),
        "measurements": dict(measurements or {}),
    }


def _timber_end_segments(record):
    return [
        (tuple(record["near_end_segment"][0]), tuple(record["near_end_segment"][1])),
        (tuple(record["far_end_segment"][0]), tuple(record["far_end_segment"][1])),
    ]


def _timber_side_segments(record):
    return [
        (tuple(segment[0]), tuple(segment[1]))
        for segment in record.get("side_segments") or []
    ]


def _timber_ends_face(end_point_a, end_point_b, record_a, record_b):
    separation = _timber_unit(_timber_subtract(end_point_b, end_point_a))
    axis_a = tuple(record_a.get("length_axis") or (1.0, 0.0))
    axis_b = tuple(record_b.get("length_axis") or (1.0, 0.0))
    return abs(_timber_dot(axis_a, separation)) >= 0.60 and abs(_timber_dot(axis_b, separation)) >= 0.60


def _timber_shared_protected_features(record_a, record_b):
    generic = {
        "future special-chair datum", "stock-rail support", "turnout rail support",
        "closure-rail support", "common-crossing support", "vee-rail support",
    }
    features_a = set(record_a.get("protected_features") or []) - generic
    features_b = set(record_b.get("protected_features") or []) - generic
    return sorted(features_a & features_b)


def analyse_crossover_timber_records(crossover_config, records, settings=None):
    profile_start = time.perf_counter()
    profile_stage_start = profile_start
    profile_timings = {}
    config = dict(crossover_config or {})
    settings = normalise_crossover_timber_analysis_settings(settings)
    intersection_tolerance = float(settings["intersection_tolerance"])
    near_tolerance = float(settings["near_touching_tolerance"])
    minimum_spacing = float(settings["minimum_clear_spacing"])
    same_station_tolerance = float(settings["same_station_tolerance"])
    maximum_skew = math.radians(float(settings["maximum_advisory_skew_degrees"]))
    findings = []
    statistics = {
        "total_timbers_examined": len(records),
        "turnout_a_timber_count": sum(1 for item in records if item.get("turnout_side") == "A"),
        "turnout_b_timber_count": sum(1 for item in records if item.get("turnout_side") == "B"),
        "broad_phase_candidate_pairs": 0,
        "exact_pair_tests": 0,
        "intersections": 0,
        "overlapping_areas": 0,
        "fully_covering_overlaps": 0,
        "near_touching_ends": 0,
        "spacing_conflicts": 0,
        "same_station_conflicts": 0,
        "skew_warnings": 0,
        "duplicate_support_conflicts": 0,
        "unsupported_protected_locations": 0,
    }
    profile_timings["settings_and_statistics_setup"] = (time.perf_counter() - profile_stage_start) * 1000.0
    pair_padding = max(near_tolerance, minimum_spacing, same_station_tolerance)
    profile_stage_start = time.perf_counter()
    pairs = _timber_spatial_candidate_pairs(records, pair_padding)
    statistics["broad_phase_candidate_pairs"] = len(pairs)
    profile_timings["broad_phase_pair_generation"] = (time.perf_counter() - profile_stage_start) * 1000.0
    reported_codes = set()
    geometry_cache = []
    profile_stage_start = time.perf_counter()
    records_by_parent = {}
    for record in records:
        polygon = [tuple(point) for point in record["collision_polygon"]]
        end_segments = _timber_end_segments(record)
        side_segments = _timber_side_segments(record)
        geometry_cache.append({
            "polygon": polygon,
            "area": abs(_timber_polygon_area(polygon)),
            "end_segments": end_segments,
            "side_segments": side_segments,
            "end_bbox": _timber_bbox([point for segment in end_segments for point in segment]),
            "side_bbox": _timber_bbox([point for segment in side_segments for point in segment]),
        })
        records_by_parent.setdefault(record.get("parent_turnout_identity"), []).append(record)
    profile_timings["geometry_preparation"] = (time.perf_counter() - profile_stage_start) * 1000.0

    def append_once(finding):
        key = (
            finding["code"], finding["timber_a"], finding["timber_b"],
            round(float(finding["marker_point"][0]), 4), round(float(finding["marker_point"][1]), 4),
        )
        if key not in reported_codes:
            reported_codes.add(key)
            findings.append(finding)

    profile_stage_start = time.perf_counter()
    for first_index, second_index in pairs:
        first = records[first_index]
        second = records[second_index]
        if not _timber_bbox_intersects(first["bounding_box"], second["bounding_box"], pair_padding):
            continue
        statistics["exact_pair_tests"] += 1
        first_geometry = geometry_cache[first_index]
        second_geometry = geometry_cache[second_index]
        polygon_a = first_geometry["polygon"]
        polygon_b = second_geometry["polygon"]
        intersection = _timber_convex_intersection(polygon_a, polygon_b)
        overlap_area = abs(_timber_polygon_area(intersection))
        area_a = first_geometry["area"]
        area_b = second_geometry["area"]
        same_parent = first["turnout_side"] == second["turnout_side"]
        pair_label = "internal {}".format(first["turnout_side"]) if same_parent else "between turnout A and turnout B"
        if overlap_area > max(1.0e-6, intersection_tolerance * intersection_tolerance):
            statistics["intersections"] += 1
            statistics["overlapping_areas"] += 1
            centroid = _timber_polygon_centroid(intersection)
            append_once(_timber_finding(
                "timber_body_intersection",
                CROSSOVER_TIMBER_SEVERITY_PRODUCTION_CONFLICT,
                "Timber bodies {} intersect by {:.3f} mm²: {} and {}.".format(
                    pair_label, overlap_area, first["stable_identity"], second["stable_identity"]
                ),
                first, second, centroid,
                {"overlap_area_mm2": overlap_area, "internal_to_one_turnout": same_parent},
            ))
            coverage = overlap_area / max(1.0e-12, min(area_a, area_b))
            if coverage >= 0.98:
                statistics["fully_covering_overlaps"] += 1
                append_once(_timber_finding(
                    "timber_fully_covers_another",
                    CROSSOVER_TIMBER_SEVERITY_PRODUCTION_CONFLICT,
                    "One timber covers at least 98% of the other timber body: {} and {}.".format(
                        first["stable_identity"], second["stable_identity"]
                    ),
                    first, second, centroid,
                    {"coverage_ratio": coverage, "overlap_area_mm2": overlap_area},
                ))
            shared_features = _timber_shared_protected_features(first, second)
            if shared_features and not same_parent:
                statistics["duplicate_support_conflicts"] += 1
                append_once(_timber_finding(
                    "duplicate_conflicting_support",
                    CROSSOVER_TIMBER_SEVERITY_PRODUCTION_CONFLICT,
                    "Conflicting inherited support provision overlaps for {}: {} and {}.".format(
                        ", ".join(shared_features), first["stable_identity"], second["stable_identity"]
                    ),
                    first, second, centroid,
                    {"shared_protected_features": shared_features, "overlap_area_mm2": overlap_area},
                ))
        else:
            if _timber_bbox_minimum_distance(
                first_geometry["end_bbox"], second_geometry["end_bbox"]
            ) <= near_tolerance + 1.0e-9:
                end_distance, end_point_a, end_point_b = _timber_segments_minimum_distance(
                    first_geometry["end_segments"], second_geometry["end_segments"]
                )
            else:
                end_distance, end_point_a, end_point_b = float("inf"), None, None
            if _timber_bbox_minimum_distance(
                first_geometry["side_bbox"], second_geometry["side_bbox"]
            ) < minimum_spacing - 1.0e-9:
                side_distance, side_point_a, side_point_b = _timber_segments_minimum_distance(
                    first_geometry["side_segments"], second_geometry["side_segments"]
                )
            else:
                side_distance, side_point_a, side_point_b = float("inf"), None, None
            if end_distance <= near_tolerance + 1.0e-9:
                statistics["near_touching_ends"] += 1
                severity = (
                    CROSSOVER_TIMBER_SEVERITY_INFORMATION
                    if end_distance <= intersection_tolerance
                    else CROSSOVER_TIMBER_SEVERITY_ADVISORY
                )
                code = "timber_end_contact" if severity == CROSSOVER_TIMBER_SEVERITY_INFORMATION else "near_touching_timber_ends"
                append_once(_timber_finding(
                    code,
                    severity,
                    "Timber ends are {:.3f} mm apart: {} and {}.".format(
                        end_distance, first["stable_identity"], second["stable_identity"]
                    ),
                    first, second, _timber_midpoint(end_point_a, end_point_b),
                    {"end_clearance_mm": end_distance},
                ))
                if end_distance < minimum_spacing - 1.0e-9 and _timber_ends_face(end_point_a, end_point_b, first, second):
                    statistics["spacing_conflicts"] += 1
                    append_once(_timber_finding(
                        "inadequate_facing_end_clearance",
                        CROSSOVER_TIMBER_SEVERITY_PRODUCTION_CONFLICT,
                        "Facing timber ends have only {:.3f} mm clearance; {:.3f} mm is configured.".format(
                            end_distance, minimum_spacing
                        ),
                        first, second, _timber_midpoint(end_point_a, end_point_b),
                        {"end_clearance_mm": end_distance, "minimum_clear_spacing_mm": minimum_spacing},
                    ))
            if side_distance < minimum_spacing - 1.0e-9:
                statistics["spacing_conflicts"] += 1
                append_once(_timber_finding(
                    "insufficient_side_to_side_spacing",
                    CROSSOVER_TIMBER_SEVERITY_PRODUCTION_CONFLICT,
                    "Timber side clearance is {:.3f} mm; {:.3f} mm is configured: {} and {}.".format(
                        side_distance, minimum_spacing, first["stable_identity"], second["stable_identity"]
                    ),
                    first, second, _timber_midpoint(side_point_a, side_point_b),
                    {"side_clearance_mm": side_distance, "minimum_clear_spacing_mm": minimum_spacing},
                ))
        station_difference = abs(float(first["longitudinal_station"]) - float(second["longitudinal_station"]))
        if (
            first["turnout_side"] != second["turnout_side"]
            and station_difference <= same_station_tolerance + 1.0e-9
            and _timber_distance(first["centre"], second["centre"])
            <= 0.5 * (float(first["length"]) + float(second["length"])) + minimum_spacing
        ):
            statistics["same_station_conflicts"] += 1
            append_once(_timber_finding(
                "effectively_same_longitudinal_station",
                CROSSOVER_TIMBER_SEVERITY_ADVISORY,
                "Inherited timbers occupy effectively the same longitudinal position within {:.3f} mm: {} and {}.".format(
                    station_difference, first["stable_identity"], second["stable_identity"]
                ),
                first, second,
                _timber_midpoint(first["centre"], second["centre"]),
                {"station_difference_mm": station_difference, "same_station_tolerance_mm": same_station_tolerance},
            ))

    profile_timings["exact_pair_analysis"] = (time.perf_counter() - profile_stage_start) * 1000.0
    profile_stage_start = time.perf_counter()
    for record in records:
        requirements = list(record.get("support_requirements") or [])
        route_headings = [
            (str(requirement.get("route_kind") or requirement.get("route_identity") or "route"), float(requirement.get("rail_heading_radians")))
            for requirement in requirements
            if requirement.get("rail_heading_radians") is not None
        ]
        if bool(record.get("shared_long_timber")) and len(route_headings) >= 2:
            route_skews = [
                (label, math.degrees(_timber_normalised_angle_difference(
                    float(record["angle_radians"]), heading + 0.5 * math.pi
                )))
                for label, heading in route_headings
            ]
            maximum_route_skew = max(value for _label, value in route_skews)
            allowed_shared_skew = float(
                (record.get("source_configuration") or {}).get("maximum_allowed_skew_degrees")
                or CROSSOVER_SHARED_TIMBER_ENVELOPE_MAXIMUM_SKEW_DEGREES
            )
            details = ", ".join("{} {:.3f}°".format(label, value) for label, value in route_skews)
            if maximum_route_skew > allowed_shared_skew + 1.0e-9:
                statistics["skew_warnings"] += 1
                append_once(_timber_finding(
                    "shared_timber_excessive_multi_route_skew",
                    CROSSOVER_TIMBER_SEVERITY_PRODUCTION_CONFLICT,
                    "{} exceeds the shared-timber angular limit: {}; limit {:.3f}°.".format(
                        record["stable_identity"], details, allowed_shared_skew
                    ),
                    record, None, tuple(record["centre"]),
                    {"route_skews_degrees": route_skews, "shared_limit_degrees": allowed_shared_skew},
                ))
            elif maximum_route_skew > math.degrees(maximum_skew) + 1.0e-9:
                append_once(_timber_finding(
                    "shared_timber_multi_route_alignment",
                    CROSSOVER_TIMBER_SEVERITY_INFORMATION,
                    "{} is aligned between its supported roads: {}; accepted against the {:.3f}° shared-timber limit.".format(
                        record["stable_identity"], details, allowed_shared_skew
                    ),
                    record, None, tuple(record["centre"]),
                    {"route_skews_degrees": route_skews, "shared_limit_degrees": allowed_shared_skew},
                ))
            continue
        expected_angle = float(record["local_rail_heading_radians"]) + 0.5 * math.pi
        skew = _timber_normalised_angle_difference(float(record["angle_radians"]), expected_angle)
        if skew > maximum_skew + 1.0e-9:
            statistics["skew_warnings"] += 1
            append_once(_timber_finding(
                "excessive_skew_to_local_formation",
                CROSSOVER_TIMBER_SEVERITY_ADVISORY,
                "{} is skewed {:.3f}° from square to its local rail formation; the advisory limit is {:.3f}°.".format(
                    record["stable_identity"], math.degrees(skew), math.degrees(maximum_skew)
                ),
                record, None, tuple(record["centre"]),
                {"skew_degrees": math.degrees(skew), "advisory_limit_degrees": math.degrees(maximum_skew)},
            ))

    ordered = sorted(records, key=lambda item: (float(item["longitudinal_station"]), item["stable_identity"]))
    for first, second in zip(ordered[:-1], ordered[1:]):
        if first["turnout_side"] == second["turnout_side"]:
            continue
        angular_difference = _timber_normalised_angle_difference(
            float(first["angle_radians"]), float(second["angle_radians"])
        )
        if angular_difference > maximum_skew + 1.0e-9:
            append_once(_timber_finding(
                "excessive_angular_difference_between_candidates",
                CROSSOVER_TIMBER_SEVERITY_ADVISORY,
                "Adjacent inherited timber candidates differ by {:.3f}°: {} and {}.".format(
                    math.degrees(angular_difference), first["stable_identity"], second["stable_identity"]
                ),
                first, second,
                _timber_midpoint(first["centre"], second["centre"]),
                {"angular_difference_degrees": math.degrees(angular_difference), "advisory_limit_degrees": math.degrees(maximum_skew)},
            ))

    for record in records:
        zone = [tuple(point) for point in record.get("support_zone_polygon") or []]
        if len(zone) < 3 or abs(_timber_polygon_area(zone)) <= 1.0e-6:
            statistics["unsupported_protected_locations"] += 1
            append_once(_timber_finding(
                "unsupported_protected_position",
                CROSSOVER_TIMBER_SEVERITY_PRODUCTION_CRITICAL,
                "Protected support zone for {} is missing or degenerate: {}.".format(
                    record["stable_identity"], record.get("supported_feature") or "turnout support"
                ),
                record, None, tuple(record["centre"]),
                {"reason": "missing or degenerate support zone"},
            ))
            continue
        same_parent = records_by_parent.get(record.get("parent_turnout_identity"), [])
        centre = tuple(record["centre"])
        covered = any(
            _timber_point_in_convex_polygon(centre, [tuple(point) for point in candidate["collision_polygon"]], 1.0e-7)
            for candidate in same_parent
        )
        if not covered:
            statistics["unsupported_protected_locations"] += 1
            append_once(_timber_finding(
                "unsupported_protected_position",
                CROSSOVER_TIMBER_SEVERITY_PRODUCTION_CRITICAL,
                "No inherited timber covers the protected support position for {}: {}.".format(
                    record["stable_identity"], record.get("supported_feature") or "turnout support"
                ),
                record, None, centre,
                {"reason": "no timber covers protected support centre"},
            ))

    append_once(_timber_finding(
        "rail_and_flangeway_clearance_deferred",
        CROSSOVER_TIMBER_SEVERITY_INFORMATION,
        "Rail-foot, chair and flangeway envelope intrusion is not yet asserted because timber bodies intentionally pass beneath the rails and chair envelopes have not yet been generated.",
        None, None, (0.0, 0.0),
        {"reliable_check_available": False},
    ))

    profile_timings["alignment_and_support_validation"] = (time.perf_counter() - profile_stage_start) * 1000.0
    severity_counts = {
        CROSSOVER_TIMBER_SEVERITY_INFORMATION: 0,
        CROSSOVER_TIMBER_SEVERITY_ADVISORY: 0,
        CROSSOVER_TIMBER_SEVERITY_PRODUCTION_CONFLICT: 0,
        CROSSOVER_TIMBER_SEVERITY_PRODUCTION_CRITICAL: 0,
    }
    for finding in findings:
        severity_counts[finding["severity"]] = severity_counts.get(finding["severity"], 0) + 1
    if severity_counts[CROSSOVER_TIMBER_SEVERITY_PRODUCTION_CRITICAL] > 0:
        status = CROSSOVER_TIMBER_ANALYSIS_STATUS_CRITICAL
    elif severity_counts[CROSSOVER_TIMBER_SEVERITY_PRODUCTION_CONFLICT] > 0:
        status = CROSSOVER_TIMBER_ANALYSIS_STATUS_CONFLICTS
    else:
        status = CROSSOVER_TIMBER_ANALYSIS_STATUS_CLEAR
    statistics.update({
        "informational_findings": severity_counts[CROSSOVER_TIMBER_SEVERITY_INFORMATION],
        "advisory_findings": severity_counts[CROSSOVER_TIMBER_SEVERITY_ADVISORY],
        "production_conflicts": severity_counts[CROSSOVER_TIMBER_SEVERITY_PRODUCTION_CONFLICT],
        "production_critical_conflicts": severity_counts[CROSSOVER_TIMBER_SEVERITY_PRODUCTION_CRITICAL],
    })
    profile_timings["total"] = (time.perf_counter() - profile_start) * 1000.0
    return {
        "schema_version": CROSSOVER_TIMBER_ANALYSIS_SCHEMA_VERSION,
        "macro_version": MACRO_VERSION_NUMBER,
        "crossover_id": str(config.get("crossover_id") or ""),
        "analysis_status": status,
        "overall_timbering_status": status,
        "production_ready": False,
        "host_integration_allowed": False,
        "host_integration_reason": "Timber analysis is diagnostic only; inherited crossover timber conflicts remain unresolved",
        "settings": settings,
        "statistics": statistics,
        "severity_counts": severity_counts,
        "timbers": records,
        "findings": findings,
        "rail_clearance_checks_reliable": False,
        "source_basis": list(CROSSOVER_TIMBER_ANALYSIS_SOURCE_BASIS),
        "engineering_assumptions": list(CROSSOVER_TIMBER_ANALYSIS_ENGINEERING_ASSUMPTIONS),
        "performance_timings_ms": profile_timings,
    }


def crossover_timber_analysis_summary(result, include_findings=True):
    analysis = dict(result or {})
    statistics = dict(analysis.get("statistics") or {})
    basis = str(analysis.get("analysis_basis") or "Inherited turnout reference timbering")
    production_note = str(
        analysis.get("production_note")
        or "No (timber analysis is read-only)"
    )
    lines = [
        "Version {} — Crossover timber analysis".format(CROSSOVER_OPERATOR_VERSION_NUMBER),
        "Crossover: {}".format(analysis.get("crossover_id") or "Unknown"),
        "Analysis basis: {}".format(basis),
        "Overall timbering status: {}".format(analysis.get("analysis_status") or CROSSOVER_TIMBER_ANALYSIS_STATUS_NOT_ANALYSED),
        "Production ready: {}".format(production_note),
        "Host integration allowed: No",
        "",
        "Timbers examined: {}".format(statistics.get("total_timbers_examined", 0)),
        "Turnout A timbers: {}".format(statistics.get("turnout_a_timber_count", 0)),
        "Turnout B timbers: {}".format(statistics.get("turnout_b_timber_count", 0)),
        "Broad-phase candidate pairs: {}".format(statistics.get("broad_phase_candidate_pairs", 0)),
        "Exact polygon pair tests: {}".format(statistics.get("exact_pair_tests", 0)),
        "Timber-body intersections: {}".format(statistics.get("intersections", 0)),
        "Near-touching ends: {}".format(statistics.get("near_touching_ends", 0)),
        "Spacing conflicts: {}".format(statistics.get("spacing_conflicts", 0)),
        "Same-position findings: {}".format(statistics.get("same_station_conflicts", 0)),
        "Skew warnings: {}".format(statistics.get("skew_warnings", 0)),
        "Unsupported protected locations: {}".format(statistics.get("unsupported_protected_locations", 0)),
        "Informational findings: {}".format(statistics.get("informational_findings", 0)),
        "Advisory findings: {}".format(statistics.get("advisory_findings", 0)),
        "Production conflicts: {}".format(statistics.get("production_conflicts", 0)),
        "Production-critical conflicts: {}".format(statistics.get("production_critical_conflicts", 0)),
    ]
    if analysis.get("cache_reused"):
        lines.append("Analysis cache: reused")
    elif analysis.get("geometry_signature"):
        lines.append("Analysis cache: refreshed")
    timings = dict(analysis.get("performance_timings_ms") or {})
    if timings:
        lines.extend([
            "",
            "Live performance profile:",
            "- Record extraction and settings: {:.1f} ms".format(float(timings.get("record_extraction_and_settings") or 0.0)),
            "- Broad-phase pair generation: {:.1f} ms".format(float(timings.get("core_broad_phase_pair_generation") or timings.get("broad_phase_pair_generation") or 0.0)),
            "- Geometry preparation: {:.1f} ms".format(float(timings.get("core_geometry_preparation") or timings.get("geometry_preparation") or 0.0)),
            "- Exact pair analysis: {:.1f} ms".format(float(timings.get("core_exact_pair_analysis") or timings.get("exact_pair_analysis") or 0.0)),
            "- Alignment and support validation: {:.1f} ms".format(float(timings.get("core_alignment_and_support_validation") or timings.get("alignment_and_support_validation") or 0.0)),
            "- Diagnostic display construction: {:.1f} ms".format(float(timings.get("diagnostic_display_construction") or 0.0)),
            "- Document recompute: {:.1f} ms".format(float(timings.get("document_recompute") or 0.0)),
            "- Total operation: {:.1f} ms".format(float(timings.get("total") or 0.0)),
        ])
    if include_findings:
        lines.extend(["", "Findings:"])
        findings = list(analysis.get("findings") or [])
        if not findings:
            lines.append("- None")
        for finding in findings:
            identities = " / ".join(filter(None, [finding.get("timber_a"), finding.get("timber_b")]))
            lines.append("- [{}] {}{}".format(
                finding.get("severity", ""),
                finding.get("message", ""),
                " ({})".format(identities) if identities else "",
            ))
    return "\n".join(lines)


# Stage A8A6B2A2 complete shared-timber envelope. Candidate generation is entirely
# numeric and uses A8A6B1 oriented rectangles plus the reconstructed crossover
# road. Part geometry is created once after all support and neighbour tests.



def default_crossover_shared_timber_settings():
    return {
        "schema_version": CROSSOVER_SHARED_TIMBER_SCHEMA_VERSION,
        "maximum_station_offset": CROSSOVER_SHARED_TIMBER_MAX_STATION_OFFSET,
        "maximum_angle_difference_degrees": CROSSOVER_SHARED_TIMBER_MAX_ANGLE_DIFFERENCE_DEGREES,
        "maximum_width_expansion": CROSSOVER_SHARED_TIMBER_MAX_WIDTH_EXPANSION,
        "end_allowance": CROSSOVER_SHARED_TIMBER_END_ALLOWANCE,
        "maximum_shared_timber_length": CROSSOVER_SHARED_TIMBER_MAXIMUM_LENGTH,
        "collision_tolerance": CROSSOVER_SHARED_TIMBER_COLLISION_TOLERANCE,
        "envelope_spacing_prototype_inches": CROSSOVER_SHARED_TIMBER_ENVELOPE_SPACING_PROTOTYPE_INCHES,
        "envelope_clearance": CROSSOVER_SHARED_TIMBER_ENVELOPE_CLEARANCE,
        "long_timber_envelope_allowance": CROSSOVER_SHARED_TIMBER_ENVELOPE_ALLOWANCE,
        "envelope_return_confirmation_count": CROSSOVER_SHARED_TIMBER_ENVELOPE_RETURN_CONFIRMATION,
        "maximum_envelope_skew_degrees": CROSSOVER_SHARED_TIMBER_ENVELOPE_MAXIMUM_SKEW_DEGREES,
        "generate_plain_connector_sleepers": True,
        "show_shared_timber_geometry": True,
    }


def normalise_crossover_shared_timber_settings(source=None):
    result = default_crossover_shared_timber_settings()
    if isinstance(source, dict):
        result.update(source)
    specifications = (
        ("maximum_station_offset", 0.01, 20.0),
        ("maximum_angle_difference_degrees", 0.01, 15.0),
        ("maximum_width_expansion", 0.0, 5.0),
        ("end_allowance", 0.0, 20.0),
        ("maximum_shared_timber_length", 0.0, 1000.0),
        ("collision_tolerance", 0.0, 5.0),
        ("envelope_spacing_prototype_inches", 12.0, 36.0),
        ("envelope_clearance", 0.0, 5.0),
        ("long_timber_envelope_allowance", 0.0, 10.0),
        ("maximum_envelope_skew_degrees", 0.25, 30.0),
    )
    defaults = default_crossover_shared_timber_settings()
    for key, minimum, maximum in specifications:
        try:
            value = float(result.get(key))
        except Exception:
            value = float(defaults[key])
        if not math.isfinite(value):
            value = float(defaults[key])
        result[key] = max(minimum, min(maximum, value))
    try:
        confirmation = int(round(float(result.get("envelope_return_confirmation_count"))))
    except Exception:
        confirmation = int(defaults["envelope_return_confirmation_count"])
    result["envelope_return_confirmation_count"] = max(1, min(10, confirmation))
    result["generate_plain_connector_sleepers"] = bool(result.get("generate_plain_connector_sleepers", True))
    result["show_shared_timber_geometry"] = bool(result.get("show_shared_timber_geometry", True))
    result["schema_version"] = CROSSOVER_SHARED_TIMBER_SCHEMA_VERSION
    return result







def _shared_timber_inherited_signature(crossover_config, records):
    config = dict(crossover_config or {})
    payload = {
        "schema_version": CROSSOVER_SHARED_TIMBER_SCHEMA_VERSION,
        "crossover_id": str(config.get("crossover_id") or ""),
        "geometry": [
            {
                "id": str(record.get("stable_identity") or ""),
                "centre": [round(float(value), 6) for value in record.get("centre") or (0.0, 0.0)],
                "angle": round(float(record.get("angle_radians") or 0.0), 9),
                "width": round(float(record.get("width") or 0.0), 6),
                "length": round(float(record.get("length") or 0.0), 6),
                "polygon": [
                    [round(float(point[0]), 6), round(float(point[1]), 6)]
                    for point in record.get("collision_polygon") or []
                ],
                "features": list(record.get("protected_features") or []),
            }
            for record in sorted(records, key=lambda item: str(item.get("stable_identity") or ""))
        ],
    }
    return hashlib.sha256(json.dumps(payload, sort_keys=True, separators=(",", ":")).encode("utf-8")).hexdigest()



def _shared_timber_resolution_signature(
    crossover_config,
    settings,
    inherited_signature,
    shared_records,
    consumed,
    plain_connector_records=None,
    envelope_summary=None,
):
    def serialised_record(record):
        return {
            "id": str(record.get("stable_identity") or ""),
            "members": sorted(str(value) for value in record.get("source_timber_identities") or []),
            "centre": [round(float(value), 6) for value in record.get("centre") or (0.0, 0.0)],
            "angle": round(float(record.get("angle_radians") or 0.0), 9),
            "width": round(float(record.get("width") or 0.0), 6),
            "length": round(float(record.get("length") or 0.0), 6),
            "polygon": [
                [round(float(point[0]), 6), round(float(point[1]), 6)]
                for point in record.get("collision_polygon") or []
            ],
            "features": sorted(str(value) for value in record.get("protected_features") or []),
            "envelope_station": round(float(record.get("envelope_path_station") or 0.0), 6),
            "envelope_kind": str(record.get("envelope_kind") or ""),
            "support_requirements": [
                {
                    "source": str(requirement.get("source_timber_identity") or requirement.get("route_identity") or ""),
                    "centre": [round(float(value), 6) for value in requirement.get("centre") or (0.0, 0.0)],
                    "zone": [
                        [round(float(point[0]), 6), round(float(point[1]), 6)]
                        for point in requirement.get("zone_polygon") or []
                    ],
                    "features": sorted(str(value) for value in requirement.get("features") or []),
                    "template_width": round(float(requirement.get("template_width") or 0.0), 6),
                }
                for requirement in record.get("support_requirements") or []
            ],
        }

    envelope = dict(envelope_summary or {})
    stable_envelope = {
        key: envelope.get(key)
        for key in (
            "path_length", "interval_count", "actual_spacing", "station_count",
            "turnout_a_envelope_timber_count", "turnout_b_envelope_timber_count",
            "three_route_envelope_timber_count", "plain_connector_timber_count",
            "unresolved_station_count", "turnout_a_return_confirmed",
            "turnout_b_return_confirmed", "turnout_a_last_shared_station",
            "turnout_b_first_shared_station", "return_confirmation_count",
            "turnout_a_last_conflict_station", "turnout_b_first_conflict_station",
            "nominal_template_width_a", "nominal_template_width_b",
            "nominal_connector_template_width",
        )
    }
    payload = {
        "schema_version": CROSSOVER_SHARED_TIMBER_SCHEMA_VERSION,
        "crossover_id": str((crossover_config or {}).get("crossover_id") or ""),
        "inherited_signature": str(inherited_signature),
        "settings": normalise_crossover_shared_timber_settings(settings),
        "consumed": sorted(str(value) for value in consumed),
        "shared": [serialised_record(record) for record in shared_records or []],
        "plain_connector": [serialised_record(record) for record in plain_connector_records or []],
        "envelope_summary": stable_envelope,
    }
    return hashlib.sha256(json.dumps(payload, sort_keys=True, separators=(",", ":")).encode("utf-8")).hexdigest()



def _shared_timber_axes(records):
    values = list(records or [])
    if not values:
        return (0.0, 1.0), (1.0, 0.0), math.pi * 0.5
    cosine = 0.0
    sine = 0.0
    for record in values:
        angle = float(record.get("angle_radians") or 0.0)
        weight = 1.0 + 0.1 * len(record.get("protected_features") or [])
        cosine += weight * math.cos(2.0 * angle)
        sine += weight * math.sin(2.0 * angle)
    angle = 0.5 * math.atan2(sine, cosine)
    length_axis = (math.cos(angle), math.sin(angle))
    width_axis = (-length_axis[1], length_axis[0])
    return length_axis, width_axis, angle


def _shared_timber_rectangle(centre, length_axis, width_axis, length, width):
    half_length = 0.5 * float(length)
    half_width = 0.5 * float(width)
    return [
        _timber_add(centre, _timber_add(_timber_scale(length_axis, -half_length), _timber_scale(width_axis, -half_width))),
        _timber_add(centre, _timber_add(_timber_scale(length_axis, -half_length), _timber_scale(width_axis, half_width))),
        _timber_add(centre, _timber_add(_timber_scale(length_axis, half_length), _timber_scale(width_axis, half_width))),
        _timber_add(centre, _timber_add(_timber_scale(length_axis, half_length), _timber_scale(width_axis, -half_width))),
    ]


def _shared_timber_candidate(crossover_config, first, second, settings, sequence):
    settings = normalise_crossover_shared_timber_settings(settings)
    if str(first.get("turnout_side") or "") == str(second.get("turnout_side") or ""):
        return None, "candidate members belong to the same inherited turnout"
    station_offset = abs(float(first.get("longitudinal_station") or 0.0) - float(second.get("longitudinal_station") or 0.0))
    if station_offset > float(settings["maximum_station_offset"]) + 1.0e-9:
        return None, "longitudinal centre offset {:.3f} mm exceeds {:.3f} mm".format(station_offset, settings["maximum_station_offset"])
    angle_difference = math.degrees(_timber_normalised_angle_difference(
        float(first.get("angle_radians") or 0.0), float(second.get("angle_radians") or 0.0)
    ))
    if angle_difference > float(settings["maximum_angle_difference_degrees"]) + 1.0e-9:
        return None, "angular difference {:.3f} degrees exceeds {:.3f} degrees".format(angle_difference, settings["maximum_angle_difference_degrees"])

    members = [first, second]
    length_axis, width_axis, angle = _shared_timber_axes(members)
    points = []
    support_requirements = []
    for record in members:
        points.extend([tuple(point) for point in record.get("collision_polygon") or []])
        zone = [tuple(point) for point in record.get("support_zone_polygon") or []]
        if zone:
            points.extend(zone)
        support_requirements.append({
            "source_timber_identity": str(record.get("stable_identity") or ""),
            "centre": list(record.get("centre") or (0.0, 0.0)),
            "zone_polygon": [list(point) for point in zone],
            "features": list(record.get("protected_features") or []),
            "route_kind": str(record.get("turnout_side") or ""),
            "rail_heading_radians": float(record.get("local_rail_heading_radians") or 0.0),
        })
    if not points:
        return None, "candidate members have no usable polygon geometry"
    length_values = [_timber_dot(point, length_axis) for point in points]
    width_values = [_timber_dot(point, width_axis) for point in points]
    minimum_length = min(length_values) - float(settings["end_allowance"])
    maximum_length = max(length_values) + float(settings["end_allowance"])
    minimum_width = min(width_values)
    maximum_width = max(width_values)
    required_width = maximum_width - minimum_width
    standard_width = max(float(first.get("width") or 0.0), float(second.get("width") or 0.0))
    allowed_width = standard_width + float(settings["maximum_width_expansion"])
    if required_width > allowed_width + 1.0e-7:
        return None, "required width {:.3f} mm exceeds allowed {:.3f} mm".format(required_width, allowed_width)
    width = max(standard_width, required_width)
    raw_length = maximum_length - minimum_length
    gauge = float((crossover_config or {}).get("track_gauge") or TURNOUT_DEFAULT_GAUGE)
    flangeway = float((crossover_config or {}).get("flangeway") or TURNOUT_DEFAULT_FLANGEWAY)
    increment = TURNOUT_TIMBER_LENGTH_INCREMENT_INCHES * rea_c10_dimensions(gauge, flangeway)["inch"]
    length = math.ceil(max(raw_length, increment) / increment - 1.0e-12) * increment
    maximum_allowed_length = float(settings.get("maximum_shared_timber_length") or 0.0)
    if maximum_allowed_length > 0.0 and length > maximum_allowed_length + 1.0e-7:
        return None, "shared length {:.3f} mm exceeds configured maximum {:.3f} mm".format(length, maximum_allowed_length)
    centre_length = 0.5 * (minimum_length + maximum_length)
    centre_width = 0.5 * (minimum_width + maximum_width)
    centre = _timber_add(_timber_scale(length_axis, centre_length), _timber_scale(width_axis, centre_width))
    polygon = _shared_timber_rectangle(centre, length_axis, width_axis, length, width)
    for requirement in support_requirements:
        if not _timber_point_in_convex_polygon(tuple(requirement["centre"]), polygon, 1.0e-7):
            return None, "shared rectangle does not preserve protected support centre {}".format(requirement["source_timber_identity"])
        for point in requirement.get("zone_polygon") or []:
            if not _timber_point_in_convex_polygon(tuple(point), polygon, 1.0e-6):
                return None, "shared rectangle does not contain the protected support zone for {}".format(requirement["source_timber_identity"])
    identity = "{}:SHARED:{:03d}".format(str((crossover_config or {}).get("crossover_id") or "XO"), int(sequence))
    near_start = _timber_add(centre, _timber_add(_timber_scale(length_axis, -0.5 * length), _timber_scale(width_axis, -0.5 * width)))
    near_finish = _timber_add(centre, _timber_add(_timber_scale(length_axis, -0.5 * length), _timber_scale(width_axis, 0.5 * width)))
    far_start = _timber_add(centre, _timber_add(_timber_scale(length_axis, 0.5 * length), _timber_scale(width_axis, -0.5 * width)))
    far_finish = _timber_add(centre, _timber_add(_timber_scale(length_axis, 0.5 * length), _timber_scale(width_axis, 0.5 * width)))
    features = sorted(set(list(first.get("protected_features") or []) + list(second.get("protected_features") or [])))
    station = 0.5 * (float(first.get("longitudinal_station") or 0.0) + float(second.get("longitudinal_station") or 0.0))
    local_heading = 0.5 * (float(first.get("local_rail_heading_radians") or 0.0) + float(second.get("local_rail_heading_radians") or 0.0))
    record = {
        "stable_identity": identity,
        "parent_turnout_identity": "{}:SHARED".format(str((crossover_config or {}).get("crossover_id") or "XO")),
        "crossover_identity": str((crossover_config or {}).get("crossover_id") or ""),
        "turnout_side": "SHARED",
        "identifier": "L{:03d}".format(int(sequence)),
        "prototype_reference": "Shared {} + {}".format(first.get("identifier"), second.get("identifier")),
        "sequence": int(sequence),
        "section": "shared long timber",
        "centre": [centre[0], centre[1]],
        "angle_radians": angle,
        "angle_degrees": math.degrees(angle),
        "width": width,
        "length": length,
        "outline_polygon": [[point[0], point[1]] for point in polygon],
        "collision_polygon": [[point[0], point[1]] for point in polygon],
        "bounding_box": list(_timber_bbox(polygon)),
        "near_end_segment": [[near_start[0], near_start[1]], [near_finish[0], near_finish[1]]],
        "far_end_segment": [[far_start[0], far_start[1]], [far_finish[0], far_finish[1]]],
        "side_segments": [
            [[near_start[0], near_start[1]], [far_start[0], far_start[1]]],
            [[near_finish[0], near_finish[1]], [far_finish[0], far_finish[1]]],
        ],
        "length_axis": [length_axis[0], length_axis[1]],
        "width_axis": [width_axis[0], width_axis[1]],
        "longitudinal_station": station,
        "host_chainage": 0.5 * (float(first.get("host_chainage") or 0.0) + float(second.get("host_chainage") or 0.0)),
        "local_rail_heading_radians": local_heading,
        "local_rail_heading_degrees": math.degrees(local_heading),
        "source_configuration": {
            "source_note": "A8A6B2A2 shared long timber generated from two validated inherited timber records",
            "source_timber_identities": [first.get("stable_identity"), second.get("stable_identity")],
            "station_offset_mm": station_offset,
            "angular_difference_degrees": angle_difference,
            "maximum_allowed_skew_degrees": float(settings["maximum_envelope_skew_degrees"]),
            "length_increment_mm": increment,
            "raw_required_length_mm": raw_length,
            "raw_required_width_mm": required_width,
        },
        "source_timber_identities": [str(first.get("stable_identity") or ""), str(second.get("stable_identity") or "")],
        "protected_support_region": True,
        "protected_features": features,
        "supported_feature": ", ".join(features),
        "support_zone_polygon": [[point[0], point[1]] for point in polygon],
        "support_requirements": support_requirements,
        "shared_long_timber": True,
    }
    return record, ""


def _shared_timber_candidate_collision(candidate, records, ignored_identities, tolerance):
    polygon = [tuple(point) for point in candidate.get("collision_polygon") or []]
    bbox = candidate.get("bounding_box") or _timber_bbox(polygon)
    worst = None
    for record in records:
        identity = str(record.get("stable_identity") or "")
        if identity in ignored_identities:
            continue
        other_polygon = [tuple(point) for point in record.get("collision_polygon") or []]
        if not _timber_bbox_intersects(bbox, record.get("bounding_box") or _timber_bbox(other_polygon), 0.0):
            continue
        intersection = _timber_convex_intersection(polygon, other_polygon)
        area = abs(_timber_polygon_area(intersection)) if len(intersection) >= 3 else 0.0
        if area > float(tolerance) + 1.0e-9:
            if worst is None or area > worst[0]:
                worst = (area, identity)
    return worst



def _shared_timber_polygon_segments(polygon):
    points = [tuple(point) for point in polygon or []]
    return [
        (points[index], points[(index + 1) % len(points)])
        for index in range(len(points))
    ] if len(points) >= 2 else []


def _shared_timber_polygon_clearance(first_polygon, second_polygon):
    first = [tuple(point) for point in first_polygon or []]
    second = [tuple(point) for point in second_polygon or []]
    if len(first) < 3 or len(second) < 3:
        return float("inf")
    intersection = _timber_convex_intersection(first, second)
    if len(intersection) >= 3 and abs(_timber_polygon_area(intersection)) > 1.0e-12:
        return 0.0
    distance, _point_a, _point_b = _timber_segments_minimum_distance(
        _shared_timber_polygon_segments(first),
        _shared_timber_polygon_segments(second),
    )
    return float(distance)


def _shared_timber_clean_points(points, tolerance=1.0e-7):
    result = []
    for point in points or []:
        xy = _timber_xy(point)
        if not result or _timber_distance(result[-1], xy) > float(tolerance):
            result.append(xy)
    return result


def _shared_timber_path_profile(points):
    """Prepare an exact hierarchical index for repeated nearest-path queries.

    The segment mathematics and tie ordering remain identical to the original
    linear scan.  Blocks provide conservative bounding-box lower bounds only;
    they never approximate or remove a segment which can equal or improve the
    current result.
    """
    clean = _shared_timber_clean_points(points)
    if len(clean) < 2:
        raise ValueError("The crossover-road timber path contains fewer than two distinct points.")
    cumulative = [0.0]
    segments = []
    for index, (first, second) in enumerate(zip(clean[:-1], clean[1:])):
        segment_vector = _timber_subtract(second, first)
        dx = float(segment_vector[0])
        dy = float(segment_vector[1])
        length_sq = _timber_dot(segment_vector, segment_vector)
        length = _timber_distance(first, second)
        if length <= 1.0e-9:
            continue
        station_start = cumulative[-1]
        cumulative.append(station_start + length)
        segments.append({
            "index": int(index),
            "start": tuple(first),
            "segment": segment_vector,
            "ax": float(first[0]),
            "ay": float(first[1]),
            "dx": dx,
            "dy": dy,
            "length_sq": length_sq,
            "length": length,
            "station_start": station_start,
            "heading": math.atan2(_timber_unit(segment_vector)[1], _timber_unit(segment_vector)[0]),
            "bbox": (
                min(float(first[0]), float(second[0])),
                min(float(first[1]), float(second[1])),
                max(float(first[0]), float(second[0])),
                max(float(first[1]), float(second[1])),
            ),
        })
    if len(cumulative) != len(clean) or not segments or cumulative[-1] <= 1.0e-9:
        raise ValueError("The crossover-road timber path has no usable length.")
    block_size = 16
    blocks = []
    for start in range(0, len(segments), block_size):
        finish = min(len(segments), start + block_size)
        chunk = segments[start:finish]
        blocks.append({
            "start": start,
            "finish": finish,
            "bbox": (
                min(item["bbox"][0] for item in chunk),
                min(item["bbox"][1] for item in chunk),
                max(item["bbox"][2] for item in chunk),
                max(item["bbox"][3] for item in chunk),
            ),
        })
    return {
        "points": clean,
        "cumulative": cumulative,
        "total": cumulative[-1],
        "segments": segments,
        "projection_blocks": blocks,
    }



def _shared_timber_path_sample(profile, station):
    total = float(profile.get("total") or 0.0)
    value = min(max(float(station), 0.0), total)
    cumulative = profile["cumulative"]
    points = profile["points"]
    index = max(0, min(len(points) - 2, bisect.bisect_right(cumulative, value) - 1))
    start = points[index]
    finish = points[index + 1]
    span = cumulative[index + 1] - cumulative[index]
    fraction = 0.0 if span <= 1.0e-12 else (value - cumulative[index]) / span
    point = (
        start[0] + (finish[0] - start[0]) * fraction,
        start[1] + (finish[1] - start[1]) * fraction,
    )
    tangent = _timber_unit(_timber_subtract(finish, start))
    heading = math.atan2(tangent[1], tangent[0])
    return point, heading


def _shared_timber_nearest_profile_point(profile, point):
    target_x, target_y = _timber_xy(point)
    segments = list((profile or {}).get("segments") or [])
    blocks = list((profile or {}).get("projection_blocks") or [])
    if not segments or not blocks:
        # Compatibility fallback for profiles created by an earlier in-memory
        # caller.  This is the original exact traversal.
        target = (target_x, target_y)
        best = None
        points = profile["points"]
        cumulative = profile["cumulative"]
        for index, (start, finish) in enumerate(zip(points[:-1], points[1:])):
            segment = _timber_subtract(finish, start)
            denominator = _timber_dot(segment, segment)
            fraction = 0.0 if denominator <= 1.0e-18 else max(
                0.0, min(1.0, _timber_dot(_timber_subtract(target, start), segment) / denominator)
            )
            projected = _timber_add(start, _timber_scale(segment, fraction))
            distance = _timber_distance(target, projected)
            station = cumulative[index] + fraction * (cumulative[index + 1] - cumulative[index])
            tangent = _timber_unit(segment)
            candidate = (distance, station, projected, math.atan2(tangent[1], tangent[0]))
            if best is None or candidate[:2] < best[:2]:
                best = candidate
        return best

    ordered_blocks = []
    for block_index, block in enumerate(blocks):
        bbox = block["bbox"]
        dx = 0.0 if bbox[0] <= target_x <= bbox[2] else (
            bbox[0] - target_x if target_x < bbox[0] else target_x - bbox[2]
        )
        dy = 0.0 if bbox[1] <= target_y <= bbox[3] else (
            bbox[1] - target_y if target_y < bbox[1] else target_y - bbox[3]
        )
        ordered_blocks.append((dx * dx + dy * dy, block_index, block))
    ordered_blocks.sort(key=lambda item: (item[0], item[1]))

    best = None
    best_segment_index = None
    for lower_bound_sq, _block_index, block in ordered_blocks:
        if best is not None:
            best_sq = float(best[0]) * float(best[0])
            if lower_bound_sq > best_sq + max(1.0e-18, best_sq * 1.0e-15):
                break
        for segment in segments[int(block["start"]):int(block["finish"])]:
            start = tuple(segment["start"])
            segment_vector = tuple(segment["segment"])
            denominator = float(segment["length_sq"])
            fraction = max(0.0, min(1.0, _timber_dot(
                _timber_subtract((target_x, target_y), start), segment_vector
            ) / denominator))
            projected = _timber_add(start, _timber_scale(segment_vector, fraction))
            distance = _timber_distance((target_x, target_y), projected)
            segment_index = int(segment["index"])
            cumulative = profile["cumulative"]
            station = cumulative[segment_index] + fraction * (
                cumulative[segment_index + 1] - cumulative[segment_index]
            )
            candidate = (distance, station, projected, float(segment["heading"]))
            if (
                best is None
                or (candidate[0], candidate[1], segment_index)
                < (best[0], best[1], best_segment_index)
            ):
                best = candidate
                best_segment_index = segment_index
    return best



def _shared_timber_plain_record(
    crossover_config,
    identity,
    identifier,
    centre,
    rail_heading,
    template_width,
    sleeper_width,
    longitudinal_station,
    path_station,
    route_kind,
    route_identity,
):
    length_axis = (-math.sin(float(rail_heading)), math.cos(float(rail_heading)))
    width_axis = (math.cos(float(rail_heading)), math.sin(float(rail_heading)))
    polygon = _shared_timber_rectangle(centre, length_axis, width_axis, template_width, sleeper_width)
    near_start = polygon[0]
    near_finish = polygon[1]
    far_finish = polygon[2]
    far_start = polygon[3]
    features = ["plain connector rail support", "future plain-track chair datum"]
    return {
        "stable_identity": str(identity),
        "parent_turnout_identity": "{}:CONNECTOR".format(str((crossover_config or {}).get("crossover_id") or "XO")),
        "crossover_identity": str((crossover_config or {}).get("crossover_id") or ""),
        "turnout_side": "CONNECTOR",
        "identifier": str(identifier),
        "prototype_reference": "Nominal connector sleeper",
        "sequence": int(str(identifier).split("-")[-1]) if str(identifier).split("-")[-1].isdigit() else 0,
        "section": "plain connector return",
        "centre": [centre[0], centre[1]],
        "angle_radians": math.atan2(length_axis[1], length_axis[0]),
        "angle_degrees": math.degrees(math.atan2(length_axis[1], length_axis[0])),
        "width": float(sleeper_width),
        "length": float(template_width),
        "outline_polygon": [[point[0], point[1]] for point in polygon],
        "collision_polygon": [[point[0], point[1]] for point in polygon],
        "bounding_box": list(_timber_bbox(polygon)),
        "near_end_segment": [[near_start[0], near_start[1]], [near_finish[0], near_finish[1]]],
        "far_end_segment": [[far_start[0], far_start[1]], [far_finish[0], far_finish[1]]],
        "side_segments": [
            [[near_start[0], near_start[1]], [far_start[0], far_start[1]]],
            [[near_finish[0], near_finish[1]], [far_finish[0], far_finish[1]]],
        ],
        "length_axis": [length_axis[0], length_axis[1]],
        "width_axis": [width_axis[0], width_axis[1]],
        "longitudinal_station": float(longitudinal_station),
        "host_chainage": float(path_station),
        "local_rail_heading_radians": float(rail_heading),
        "local_rail_heading_degrees": math.degrees(float(rail_heading)),
        "source_configuration": {
            "source_note": "A8A6B2A2 nominal-width connector sleeper after shared-envelope clearance",
            "route_kind": str(route_kind),
            "route_identity": str(route_identity),
            "template_width": float(template_width),
            "path_station": float(path_station),
        },
        "protected_support_region": True,
        "protected_features": features,
        "supported_feature": ", ".join(features),
        "support_zone_polygon": [[point[0], point[1]] for point in polygon],
        "support_requirements": [{
            "route_identity": str(route_identity),
            "centre": [centre[0], centre[1]],
            "zone_polygon": [[point[0], point[1]] for point in polygon],
            "features": list(features),
            "template_width": float(template_width),
        }],
        "shared_long_timber": False,
        "plain_connector_timber": True,
        "envelope_timber": False,
        "envelope_kind": "plain connector",
        "envelope_path_station": float(path_station),
    }


def _shared_timber_virtual_route_support(identity, centre, rail_heading, template_width, sleeper_width, route_kind):
    record = _shared_timber_plain_record(
        {}, identity, identity, centre, rail_heading, template_width, sleeper_width,
        0.0, 0.0, route_kind, identity,
    )
    record["turnout_side"] = str(route_kind)
    return record


def _shared_timber_envelope_axis(route_records):
    centres = [tuple(record.get("centre") or (0.0, 0.0)) for record in route_records or []]
    best = None
    for first_index, first in enumerate(centres):
        for second in centres[first_index + 1:]:
            distance = _timber_distance(first, second)
            if best is None or distance > best[0]:
                best = (distance, first, second)
    if best is not None and best[0] > 1.0e-7:
        axis = _timber_unit(_timber_subtract(best[2], best[1]))
    else:
        normals = [
            tuple(record.get("length_axis") or (1.0, 0.0))
            for record in route_records or []
        ]
        axis = _shared_timber_axes([
            {"angle_radians": math.atan2(normal[1], normal[0]), "protected_features": []}
            for normal in normals
        ])[0]
    average_normal = _timber_unit((
        sum(float((record.get("length_axis") or (1.0, 0.0))[0]) for record in route_records or []),
        sum(float((record.get("length_axis") or (1.0, 0.0))[1]) for record in route_records or []),
    ))
    if _timber_dot(axis, average_normal) < 0.0:
        axis = _timber_scale(axis, -1.0)
    return axis


def _shared_timber_envelope_record(crossover_config, route_records, settings, sequence, path_station, longitudinal_station):
    if len(route_records or []) < 2:
        return None, "a shared-envelope sleeper position requires at least two supported routes"
    axis = _shared_timber_envelope_axis(route_records)
    width_axis = (-axis[1], axis[0])
    maximum_skew = 0.0
    length_intervals = []
    width_centres = []
    support_requirements = []
    standard_width = max(float(record.get("width") or 0.0) for record in route_records)
    for record in route_records:
        normal = _timber_unit(tuple(record.get("length_axis") or (1.0, 0.0)))
        alignment = abs(_timber_dot(axis, normal))
        if alignment <= 1.0e-6:
            return None, "the required shared timber would run parallel to a supported route"
        skew = math.degrees(math.acos(max(-1.0, min(1.0, alignment))))
        maximum_skew = max(maximum_skew, skew)
        if skew > float(settings["maximum_envelope_skew_degrees"]) + 1.0e-9:
            return None, "required envelope skew {:.3f} degrees exceeds {:.3f} degrees".format(
                skew, settings["maximum_envelope_skew_degrees"]
            )
        centre = tuple(record.get("centre") or (0.0, 0.0))
        half_projection = 0.5 * float(record.get("length") or 0.0) / alignment
        projected = _timber_dot(centre, axis)
        length_intervals.append((projected - half_projection, projected + half_projection))
        width_centres.append(_timber_dot(centre, width_axis))
        support_requirements.append({
            "route_identity": str(record.get("stable_identity") or ""),
            "source_timber_identity": str(record.get("stable_identity") or ""),
            "centre": [centre[0], centre[1]],
            "zone_polygon": [list(point) for point in record.get("support_zone_polygon") or []],
            "features": list(record.get("protected_features") or []),
            "template_width": float(record.get("length") or 0.0),
            "route_kind": str(record.get("turnout_side") or ""),
            "rail_heading_radians": float(record.get("local_rail_heading_radians") or 0.0),
        })
    minimum_length = min(interval[0] for interval in length_intervals) - float(settings["end_allowance"])
    maximum_length = max(interval[1] for interval in length_intervals) + float(settings["end_allowance"])
    minimum_width = min(width_centres) - 0.5 * standard_width
    maximum_width = max(width_centres) + 0.5 * standard_width
    required_width = maximum_width - minimum_width
    allowed_width = standard_width + float(settings["maximum_width_expansion"])
    if required_width > allowed_width + 1.0e-7:
        return None, "required envelope timber width {:.3f} mm exceeds allowed {:.3f} mm".format(required_width, allowed_width)
    width = max(standard_width, required_width)
    gauge = float((crossover_config or {}).get("track_gauge") or TURNOUT_DEFAULT_GAUGE)
    flangeway = float((crossover_config or {}).get("flangeway") or TURNOUT_DEFAULT_FLANGEWAY)
    increment = TURNOUT_TIMBER_LENGTH_INCREMENT_INCHES * rea_c10_dimensions(gauge, flangeway)["inch"]
    raw_length = maximum_length - minimum_length
    length = math.ceil(max(raw_length, increment) / increment - 1.0e-12) * increment
    maximum_allowed = float(settings.get("maximum_shared_timber_length") or 0.0)
    if maximum_allowed > 0.0 and length > maximum_allowed + 1.0e-7:
        return None, "shared envelope length {:.3f} mm exceeds configured maximum {:.3f} mm".format(length, maximum_allowed)
    centre = _timber_add(
        _timber_scale(axis, 0.5 * (minimum_length + maximum_length)),
        _timber_scale(width_axis, 0.5 * (minimum_width + maximum_width)),
    )
    polygon = _shared_timber_rectangle(centre, axis, width_axis, length, width)
    identity = "{}:ENVELOPE:{:03d}".format(str((crossover_config or {}).get("crossover_id") or "XO"), int(sequence))
    near_start, near_finish, far_finish, far_start = polygon
    features = sorted(set(
        ["shared crossover timber envelope", "future special-chair datum"]
        + [feature for record in route_records for feature in record.get("protected_features") or []]
    ))
    route_kinds = sorted(set(str(record.get("turnout_side") or "") for record in route_records))
    record = {
        "stable_identity": identity,
        "parent_turnout_identity": "{}:ENVELOPE".format(str((crossover_config or {}).get("crossover_id") or "XO")),
        "crossover_identity": str((crossover_config or {}).get("crossover_id") or ""),
        "turnout_side": "ENVELOPE",
        "identifier": "E{:03d}".format(int(sequence)),
        "prototype_reference": "Shared envelope {}".format(" + ".join(route_kinds)),
        "sequence": int(sequence),
        "section": "shared timber envelope",
        "centre": [centre[0], centre[1]],
        "angle_radians": math.atan2(axis[1], axis[0]),
        "angle_degrees": math.degrees(math.atan2(axis[1], axis[0])),
        "width": width,
        "length": length,
        "outline_polygon": [[point[0], point[1]] for point in polygon],
        "collision_polygon": [[point[0], point[1]] for point in polygon],
        "bounding_box": list(_timber_bbox(polygon)),
        "near_end_segment": [[near_start[0], near_start[1]], [near_finish[0], near_finish[1]]],
        "far_end_segment": [[far_start[0], far_start[1]], [far_finish[0], far_finish[1]]],
        "side_segments": [
            [[near_start[0], near_start[1]], [far_start[0], far_start[1]]],
            [[near_finish[0], near_finish[1]], [far_finish[0], far_finish[1]]],
        ],
        "length_axis": [axis[0], axis[1]],
        "width_axis": [width_axis[0], width_axis[1]],
        "longitudinal_station": float(longitudinal_station),
        "host_chainage": float(path_station),
        "local_rail_heading_radians": float(route_records[0].get("local_rail_heading_radians") or 0.0),
        "local_rail_heading_degrees": math.degrees(float(route_records[0].get("local_rail_heading_radians") or 0.0)),
        "source_configuration": {
            "source_note": "A8A6B2A2 shared timber generated inside the complete crossover timbering envelope",
            "route_identities": [record.get("stable_identity") for record in route_records],
            "route_kinds": route_kinds,
            "maximum_skew_degrees": maximum_skew,
            "maximum_allowed_skew_degrees": float(settings["maximum_envelope_skew_degrees"]),
            "length_increment_mm": increment,
            "raw_required_length_mm": raw_length,
            "raw_required_width_mm": required_width,
            "path_station": float(path_station),
        },
        "source_timber_identities": [str(record.get("stable_identity") or "") for record in route_records],
        "protected_support_region": True,
        "protected_features": features,
        "supported_feature": ", ".join(features),
        "support_zone_polygon": [[point[0], point[1]] for point in polygon],
        "support_requirements": support_requirements,
        "shared_long_timber": True,
        "plain_connector_timber": False,
        "envelope_timber": True,
        "envelope_kind": "shared {}".format(" + ".join(route_kinds)),
        "envelope_path_station": float(path_station),
    }
    return record, ""


def _shared_timber_turnout_branch_points(host_data, turnout_config, dimensions, x_start, x_finish):
    start = float(x_start)
    finish = float(x_finish)
    count = max(1, int(math.ceil(abs(finish - start) / 1.5)))
    points = []
    for index in range(count + 1):
        fraction = index / float(count)
        x_value = start + (finish - start) * fraction
        local_x, local_y = _rea_c10_local_point(dimensions, x_value, "turnout_centre")
        points.append(map_turnout_local_point(
            host_data,
            float(turnout_config.get("toe_chainage") or 0.0),
            str(turnout_config.get("orientation") or TURNOUT_ORIENTATION_FACING),
            str(turnout_config.get("handing") or TURNOUT_HAND_LEFT),
            local_x,
            local_y,
        ))
    return points


def _shared_timber_connector_from_config(host_data_a, host_data_b, config, turnout_a, turnout_b, dimensions):
    endpoint_a, tangent_a = _crossover_branch_endpoint(
        host_data_a,
        float(turnout_a.get("toe_chainage") or config.get("toe_chainage_a") or 0.0),
        str(turnout_a.get("orientation") or config.get("orientation_a") or TURNOUT_ORIENTATION_FACING),
        str(turnout_a.get("handing") or config.get("handing") or TURNOUT_HAND_LEFT),
        dimensions,
    )
    endpoint_b, tangent_b_outward = _crossover_branch_endpoint(
        host_data_b,
        float(turnout_b.get("toe_chainage") or config.get("toe_chainage_b") or 0.0),
        str(turnout_b.get("orientation") or config.get("orientation_b") or TURNOUT_ORIENTATION_TRAILING),
        str(turnout_b.get("handing") or config.get("handing") or TURNOUT_HAND_LEFT),
        dimensions,
    )
    connector = _crossover_solve_biarc(endpoint_a, tangent_a, endpoint_b, _crossover_scale(tangent_b_outward, -1.0))
    stored_length = float(config.get("connector_length") or 0.0)
    tolerance = max(0.05, 1.0e-4 * max(1.0, stored_length))
    if stored_length > 0.0 and abs(float(connector.get("length") or 0.0) - stored_length) > tolerance:
        raise ValueError(
            "The reconstructed crossover connector differs from the stored length by {:.3f} mm; recreate or edit the crossover before resolving its timber envelope.".format(
                abs(float(connector.get("length") or 0.0) - stored_length)
            )
        )
    return connector


def crossover_shared_timber_envelope_context(doc, crossover_config, inherited_records):
    config = dict(crossover_config or {})
    identifier = str(config.get("crossover_id") or "").strip()
    host_a = doc.getObject(str(config.get("host_a_object") or ""))
    host_b = doc.getObject(str(config.get("host_b_object") or ""))
    if host_a is None or host_b is None:
        raise ValueError("Both crossover host centrelines are required to calculate the shared timbering envelope.")
    host_data_a = turnout_host_alignment(host_a)
    host_data_b = turnout_host_alignment(host_b)
    turnout_a = dict(config.get("turnout_a_config") or {})
    turnout_b = dict(config.get("turnout_b_config") or {})
    if not turnout_a or not turnout_b:
        raise ValueError("The crossover does not contain both turnout configurations required by the timber envelope.")
    dimensions = rea_c10_dimensions(
        float(config.get("track_gauge") or TURNOUT_DEFAULT_GAUGE),
        float(config.get("flangeway") or TURNOUT_DEFAULT_FLANGEWAY),
    )
    records_a = [record for record in inherited_records or [] if str(record.get("turnout_side") or "") == "A"]
    records_b = [record for record in inherited_records or [] if str(record.get("turnout_side") or "") == "B"]
    if not records_a or not records_b:
        raise ValueError("The inherited crossover timber records do not contain both turnout sides.")
    last_a = max(records_a, key=lambda record: float((record.get("source_configuration") or {}).get("local_x") or -1.0e12))
    last_b = max(records_b, key=lambda record: float((record.get("source_configuration") or {}).get("local_x") or -1.0e12))
    x_a = float((last_a.get("source_configuration") or {}).get("local_x") or dimensions["module_end_x"])
    x_b = float((last_b.get("source_configuration") or {}).get("local_x") or dimensions["module_end_x"])
    connector = _shared_timber_connector_from_config(host_data_a, host_data_b, config, turnout_a, turnout_b, dimensions)
    tail_a = _shared_timber_turnout_branch_points(host_data_a, turnout_a, dimensions, x_a, dimensions["module_end_x"])
    tail_b = _shared_timber_turnout_branch_points(host_data_b, turnout_b, dimensions, dimensions["module_end_x"], x_b)
    path_points = _shared_timber_clean_points(list(tail_a) + list(connector.get("points") or []) + list(tail_b))
    path_profile = _shared_timber_path_profile(path_points)
    host_profile_a = _shared_timber_path_profile([_timber_xy(point) for point in host_data_a.get("points") or []])
    host_profile_b = _shared_timber_path_profile([_timber_xy(point) for point in host_data_b.get("points") or []])
    origin_vector, origin_heading = interpolate_alignment_station(
        host_data_a, float(turnout_a.get("toe_chainage") or config.get("toe_chainage_a") or 0.0)
    )
    if _turnout_orientation_sign(str(turnout_a.get("orientation") or config.get("orientation_a") or TURNOUT_ORIENTATION_FACING)) < 0.0:
        origin_heading += math.pi
    reference_axis = (math.cos(origin_heading), math.sin(origin_heading))
    return {
        "path_profile": path_profile,
        "host_profiles": {
            "A": host_profile_a,
            "B": host_profile_b,
        },
        "template_widths": {
            "A": float(turnout_a.get("template_width") or config.get("connector_width") or DEFAULT_MAIN_TEMPLATE_WIDTH),
            "B": float(turnout_b.get("template_width") or config.get("connector_width") or DEFAULT_MAIN_TEMPLATE_WIDTH),
            "CONNECTOR": float(config.get("connector_width") or max(
                float(turnout_a.get("template_width") or DEFAULT_MAIN_TEMPLATE_WIDTH),
                float(turnout_b.get("template_width") or DEFAULT_MAIN_TEMPLATE_WIDTH),
            )),
        },
        "sleeper_width": TURNOUT_SLEEPER_WIDTH_INCHES * dimensions["inch"],
        "timber_width": TURNOUT_TIMBER_WIDTH_INCHES * dimensions["inch"],
        "inch": float(dimensions["inch"]),
        "reference_origin": _timber_xy(origin_vector),
        "reference_axis": reference_axis,
        "anchor_a_identity": str(last_a.get("stable_identity") or ""),
        "anchor_b_identity": str(last_b.get("stable_identity") or ""),
        "connector_length": float(connector.get("length") or 0.0),
    }



def _shared_timber_record_local_position(record):
    source = dict(record.get("source_configuration") or {})
    value = source.get("local_x")
    if value is None:
        value = record.get("host_chainage")
    try:
        value = float(value)
    except Exception:
        value = 0.0
    return value if math.isfinite(value) else 0.0


def _shared_timber_build_inherited_envelope(crossover_config, base_records, context, settings):
    """Extend inherited turnout timbers through the full crossover interference envelope.

    The timber centre and width-axis position remain unchanged. Only the timber's
    length and centre along its length axis may change, so this remains an A8A6B2
    extension operation rather than B3 timber shoving or interlacing.
    """
    config = dict(crossover_config or {})
    settings = normalise_crossover_shared_timber_settings(settings)
    host_profiles = dict((context or {}).get("host_profiles") or {})
    widths = dict((context or {}).get("template_widths") or {})
    sleeper_width = float((context or {}).get("sleeper_width") or 0.0)
    if sleeper_width <= 0.0 or not isinstance(host_profiles.get("A"), dict) or not isinstance(host_profiles.get("B"), dict):
        return [], set(), [], {
            "available": False,
            "reason": "both host profiles and a valid sleeper width are required for the inherited long-timber envelope",
        }

    physical_clearance = float(settings["envelope_clearance"])
    allowance = float(settings["long_timber_envelope_allowance"])
    trigger_clearance = physical_clearance + allowance
    confirmation = int(settings["envelope_return_confirmation_count"])
    shared = []
    consumed = set()
    rejected = []
    side_summaries = {}
    crossover_id = str(config.get("crossover_id") or "XO")

    for side, other_side in (("A", "B"), ("B", "A")):
        records = [
            record for record in base_records or []
            if str(record.get("turnout_side") or "") == side
            and _shared_timber_record_local_position(record) >= -1.0e-7
        ]
        records.sort(key=lambda record: (_shared_timber_record_local_position(record), str(record.get("stable_identity") or "")))
        entries = []
        other_profile = host_profiles[other_side]
        other_width = float(widths.get(other_side) or widths.get("CONNECTOR") or config.get("connector_width") or DEFAULT_MAIN_TEMPLATE_WIDTH)
        for record in records:
            source_centre = tuple(record.get("centre") or (0.0, 0.0))
            nearest = _shared_timber_nearest_profile_point(other_profile, source_centre)
            if nearest is None:
                entries.append({"record": record, "affected": False, "reason": "opposite host projection unavailable"})
                continue
            distance, other_chainage, other_point, other_heading = nearest
            virtual = _shared_timber_virtual_route_support(
                "{}:VIRTUAL:HOST-{}:{}".format(crossover_id, other_side, record.get("identifier") or len(entries) + 1),
                other_point,
                other_heading,
                other_width,
                sleeper_width,
                "HOST-{}".format(other_side),
            )
            clearance = _shared_timber_polygon_clearance(
                record.get("collision_polygon"), virtual.get("collision_polygon")
            )
            entries.append({
                "record": record,
                "virtual": virtual,
                "distance": float(distance),
                "other_chainage": float(other_chainage),
                "clearance": float(clearance),
                "affected": bool(clearance <= trigger_clearance + 1.0e-9),
            })

        affected_indices = [index for index, item in enumerate(entries) if item.get("affected")]
        if not affected_indices:
            side_summaries[side] = {
                "examined_count": len(entries),
                "affected_count": 0,
                "extended_count": 0,
                "first_affected_identifier": "",
                "clear_positions_before_envelope": len(entries),
                "return_confirmed": True,
            }
            continue

        first_affected = min(affected_indices)
        clear_before = first_affected
        return_confirmed = clear_before >= confirmation
        active_start = first_affected if return_confirmed else 0
        extended_count = 0
        for entry in entries[active_start:]:
            source = entry["record"]
            virtual = entry.get("virtual")
            source_identity = str(source.get("stable_identity") or "")
            if virtual is None:
                rejected.append({
                    "timber_identity": source_identity,
                    "side": side,
                    "reason": entry.get("reason") or "opposite host support could not be reconstructed",
                })
                continue
            sequence = len(shared) + 1
            candidate, reason = _shared_timber_envelope_record(
                config,
                [source, virtual],
                settings,
                sequence,
                _shared_timber_record_local_position(source),
                float(source.get("longitudinal_station") or 0.0),
            )
            if candidate is None:
                rejected.append({
                    "timber_identity": source_identity,
                    "side": side,
                    "reason": reason,
                })
                continue
            candidate["stable_identity"] = "{}:INHERITED-LONG:{}:{:03d}".format(crossover_id, side, sequence)
            candidate["identifier"] = "{}L{:03d}".format(side, sequence)
            candidate["prototype_reference"] = "Extended {} to shared long timber".format(source.get("identifier") or source_identity)
            candidate["envelope_kind"] = "extended inherited {} towards Host {}".format(side, other_side)
            candidate["extended_inherited_timber"] = True
            candidate["extended_source_timber_identity"] = source_identity
            candidate["source_timber_identities"] = [source_identity]
            candidate["source_configuration"].update({
                "source_note": "A8A6B2A2 inherited turnout timber extended through the complete crossover interference envelope",
                "extended_source_timber_identity": source_identity,
                "opposite_host_side": other_side,
                "source_to_opposite_host_distance_mm": float(entry.get("distance") or 0.0),
                "normal_footprint_clearance_mm": float(entry.get("clearance") or 0.0),
                "independent_sleeper_clearance_mm": physical_clearance,
                "long_timber_envelope_allowance_mm": allowance,
                "envelope_trigger_clearance_mm": trigger_clearance,
            })
            remaining = [
                record for record in base_records or []
                if str(record.get("stable_identity") or "") not in consumed
            ]
            collision = _shared_timber_candidate_collision(
                candidate,
                remaining + shared,
                {source_identity},
                settings["collision_tolerance"],
            )
            if collision is not None:
                rejected.append({
                    "timber_identity": source_identity,
                    "side": side,
                    "reason": "extended timber would overlap unaffected timber {} by {:.3f} mm²".format(collision[1], collision[0]),
                })
                continue
            shared.append(candidate)
            consumed.add(source_identity)
            extended_count += 1

        side_summaries[side] = {
            "examined_count": len(entries),
            "affected_count": len(affected_indices),
            "extended_count": extended_count,
            "first_affected_identifier": str(entries[first_affected]["record"].get("identifier") or ""),
            "first_affected_local_position": _shared_timber_record_local_position(entries[first_affected]["record"]),
            "clear_positions_before_envelope": clear_before,
            "return_confirmed": bool(return_confirmed),
            "active_start_identifier": str(entries[active_start]["record"].get("identifier") or "") if entries else "",
        }

    summary = {
        "available": True,
        "independent_sleeper_clearance": physical_clearance,
        "long_timber_envelope_allowance": allowance,
        "envelope_trigger_clearance": trigger_clearance,
        "return_confirmation_count": confirmation,
        "turnout_a_examined_count": int((side_summaries.get("A") or {}).get("examined_count") or 0),
        "turnout_b_examined_count": int((side_summaries.get("B") or {}).get("examined_count") or 0),
        "turnout_a_affected_count": int((side_summaries.get("A") or {}).get("affected_count") or 0),
        "turnout_b_affected_count": int((side_summaries.get("B") or {}).get("affected_count") or 0),
        "turnout_a_extended_count": int((side_summaries.get("A") or {}).get("extended_count") or 0),
        "turnout_b_extended_count": int((side_summaries.get("B") or {}).get("extended_count") or 0),
        "turnout_a_return_confirmed": bool((side_summaries.get("A") or {}).get("return_confirmed", True)),
        "turnout_b_return_confirmed": bool((side_summaries.get("B") or {}).get("return_confirmed", True)),
        "turnout_a_first_affected_identifier": str((side_summaries.get("A") or {}).get("first_affected_identifier") or ""),
        "turnout_b_first_affected_identifier": str((side_summaries.get("B") or {}).get("first_affected_identifier") or ""),
        "turnout_a_clear_positions_before_envelope": int((side_summaries.get("A") or {}).get("clear_positions_before_envelope") or 0),
        "turnout_b_clear_positions_before_envelope": int((side_summaries.get("B") or {}).get("clear_positions_before_envelope") or 0),
        "unresolved_position_count": len(rejected),
    }
    return shared, consumed, rejected, summary


def _shared_timber_build_envelope(crossover_config, base_records, context, settings):
    config = dict(crossover_config or {})
    settings = normalise_crossover_shared_timber_settings(settings)
    profile = context.get("path_profile")
    if not isinstance(profile, dict):
        return [], [], [], {"available": False, "reason": "no crossover-road path context was supplied"}
    total = float(profile.get("total") or 0.0)
    inch = float(context.get("inch") or rea_c10_dimensions(
        float(config.get("track_gauge") or TURNOUT_DEFAULT_GAUGE),
        float(config.get("flangeway") or TURNOUT_DEFAULT_FLANGEWAY),
    )["inch"])
    maximum_spacing = float(settings["envelope_spacing_prototype_inches"]) * inch
    interval_count = max(1, int(math.ceil(total / max(0.01, maximum_spacing) - 1.0e-12)))
    actual_spacing = total / float(interval_count)
    stations = [actual_spacing * index for index in range(1, interval_count)]
    widths = dict(context.get("template_widths") or {})
    connector_width = float(widths.get("CONNECTOR") or config.get("connector_width") or DEFAULT_MAIN_TEMPLATE_WIDTH)
    sleeper_width = float(context.get("sleeper_width") or TURNOUT_SLEEPER_WIDTH_INCHES * inch)
    origin = tuple(context.get("reference_origin") or (0.0, 0.0))
    reference_axis = _timber_unit(tuple(context.get("reference_axis") or (1.0, 0.0)))
    host_profiles = dict(context.get("host_profiles") or {})
    station_data = []
    for sequence, station in enumerate(stations, 1):
        point, heading = _shared_timber_path_sample(profile, station)
        longitudinal = _timber_dot(_timber_subtract(point, origin), reference_axis)
        connector_record = _shared_timber_plain_record(
            config,
            "{}:VIRTUAL:CONNECTOR:{:03d}".format(str(config.get("crossover_id") or "XO"), sequence),
            "VC-{:03d}".format(sequence),
            point,
            heading,
            connector_width,
            sleeper_width,
            longitudinal,
            station,
            "CONNECTOR",
            "crossover connector",
        )
        raw_conflicts = set()
        host_records = {}
        for side in ("A", "B"):
            host_profile = host_profiles.get(side)
            if not isinstance(host_profile, dict):
                continue
            nearest = _shared_timber_nearest_profile_point(host_profile, point)
            if nearest is None:
                continue
            distance, host_station, host_point, host_heading = nearest
            host_width = float(widths.get(side) or connector_width)
            if distance > 0.5 * (host_width + connector_width) + float(settings["envelope_clearance"]) + sleeper_width:
                continue
            host_record = _shared_timber_virtual_route_support(
                "{}:VIRTUAL:HOST-{}:{:03d}".format(str(config.get("crossover_id") or "XO"), side, sequence),
                host_point,
                host_heading,
                host_width,
                sleeper_width,
                "HOST-{}".format(side),
            )
            host_records[side] = host_record
            clearance = _shared_timber_polygon_clearance(
                connector_record.get("collision_polygon"), host_record.get("collision_polygon")
            )
            if clearance < float(settings["envelope_clearance"]) - 1.0e-9:
                raw_conflicts.add(side)
        station_data.append({
            "sequence": sequence,
            "station": station,
            "longitudinal_station": longitudinal,
            "connector": connector_record,
            "host_records": host_records,
            "raw_conflicts": raw_conflicts,
        })

    a_conflicts = [index for index, item in enumerate(station_data) if "A" in item["raw_conflicts"]]
    b_conflicts = [index for index, item in enumerate(station_data) if "B" in item["raw_conflicts"]]
    a_last = max(a_conflicts) if a_conflicts else -1
    b_first = min(b_conflicts) if b_conflicts else len(station_data)
    confirmation = int(settings["envelope_return_confirmation_count"])
    a_clear_after = len(station_data) - (a_last + 1)
    b_clear_before = b_first
    a_confirmed = a_last < 0 or a_clear_after >= confirmation
    b_confirmed = b_first >= len(station_data) or b_clear_before >= confirmation
    # A nominal-width return is accepted only when the requested number of
    # consecutive clear stations exists beyond the final conflict.  Where the
    # connector ends before that look-ahead can be established, retain the
    # shared envelope to the end rather than creating a premature plain sleeper.
    a_active_last = a_last
    if a_last >= 0 and not a_confirmed:
        a_active_last = len(station_data) - 1
    b_active_first = b_first
    if b_first < len(station_data) and not b_confirmed:
        b_active_first = 0

    shared = []
    plain = []
    rejected = []
    current = list(base_records or [])
    count_a = 0
    count_b = 0
    count_three = 0
    for item in station_data:
        index = item["sequence"] - 1
        active = []
        if a_active_last >= 0 and index <= a_active_last:
            active.append("A")
        if b_active_first < len(station_data) and index >= b_active_first:
            active.append("B")
        route_records = [item["connector"]] + [item["host_records"][side] for side in active if side in item["host_records"]]
        if len(route_records) >= 2:
            candidate, reason = _shared_timber_envelope_record(
                config,
                route_records,
                settings,
                len(shared) + 1,
                item["station"],
                item["longitudinal_station"],
            )
            if candidate is None:
                rejected.append({
                    "station": item["station"],
                    "sequence": item["sequence"],
                    "route_kinds": [record.get("turnout_side") for record in route_records],
                    "reason": reason,
                })
                continue
            collision = _shared_timber_candidate_collision(candidate, current + shared + plain, set(), settings["collision_tolerance"])
            if collision is not None:
                rejected.append({
                    "station": item["station"],
                    "sequence": item["sequence"],
                    "route_kinds": [record.get("turnout_side") for record in route_records],
                    "reason": "envelope timber would overlap {} by {:.3f} mm²".format(collision[1], collision[0]),
                })
                continue
            shared.append(candidate)
            if "A" in active:
                count_a += 1
            if "B" in active:
                count_b += 1
            if len(active) == 2:
                count_three += 1
        elif settings.get("generate_plain_connector_sleepers", True):
            connector = dict(item["connector"])
            connector["stable_identity"] = "{}:CONNECTOR:{:03d}".format(str(config.get("crossover_id") or "XO"), len(plain) + 1)
            connector["identifier"] = "P{:03d}".format(len(plain) + 1)
            connector["sequence"] = len(plain) + 1
            collision = _shared_timber_candidate_collision(connector, current + shared + plain, set(), settings["collision_tolerance"])
            if collision is not None:
                rejected.append({
                    "station": item["station"],
                    "sequence": item["sequence"],
                    "route_kinds": ["CONNECTOR"],
                    "reason": "plain connector sleeper would overlap {} by {:.3f} mm²".format(collision[1], collision[0]),
                })
                continue
            plain.append(connector)

    summary = {
        "available": True,
        "path_length": total,
        "interval_count": interval_count,
        "actual_spacing": actual_spacing,
        "maximum_spacing": maximum_spacing,
        "station_count": len(station_data),
        "turnout_a_envelope_timber_count": count_a,
        "turnout_b_envelope_timber_count": count_b,
        "three_route_envelope_timber_count": count_three,
        "plain_connector_timber_count": len(plain),
        "unresolved_station_count": len(rejected),
        "turnout_a_return_confirmed": bool(a_confirmed),
        "turnout_b_return_confirmed": bool(b_confirmed),
        "return_confirmation_count": int(confirmation),
        "turnout_a_last_conflict_station": None if a_last < 0 else float(station_data[a_last]["station"]),
        "turnout_b_first_conflict_station": None if b_first >= len(station_data) else float(station_data[b_first]["station"]),
        "turnout_a_last_shared_station": None if a_active_last < 0 else float(station_data[a_active_last]["station"]),
        "turnout_b_first_shared_station": None if b_active_first >= len(station_data) else float(station_data[b_active_first]["station"]),
        "nominal_template_width_a": float(widths.get("A") or connector_width),
        "nominal_template_width_b": float(widths.get("B") or connector_width),
        "nominal_connector_template_width": connector_width,
        "anchor_a_identity": str(context.get("anchor_a_identity") or ""),
        "anchor_b_identity": str(context.get("anchor_b_identity") or ""),
    }
    return shared, plain, rejected, summary


def apply_shared_timber_result_to_records(inherited_records, result):
    consumed = set(str(value) for value in (result or {}).get("consumed_timber_identities") or [])
    effective = [dict(record) for record in inherited_records if str(record.get("stable_identity") or "") not in consumed]
    effective.extend([dict(record) for record in (result or {}).get("shared_timbers") or []])
    effective.extend([dict(record) for record in (result or {}).get("plain_connector_timbers") or []])
    effective.sort(key=lambda item: (float(item.get("longitudinal_station") or 0.0), str(item.get("stable_identity") or "")))
    return effective




def propose_crossover_shared_long_timbers(
    crossover_config,
    inherited_records,
    analysis_result=None,
    settings=None,
    envelope_context=None,
):
    profile_start = time.perf_counter()
    profile_stage_start = profile_start
    profile_timings = {}
    config = dict(crossover_config or {})
    inherited = [dict(record) for record in inherited_records or []]
    settings = normalise_crossover_shared_timber_settings(settings if settings is not None else config.get("shared_timber_settings"))
    analysis = dict(analysis_result or analyse_crossover_timber_records(config, inherited))
    by_id = {str(record.get("stable_identity") or ""): record for record in inherited}
    pair_codes = {}
    pair_severity = {}
    severity_rank = {
        CROSSOVER_TIMBER_SEVERITY_PRODUCTION_CRITICAL: 0,
        CROSSOVER_TIMBER_SEVERITY_PRODUCTION_CONFLICT: 1,
        CROSSOVER_TIMBER_SEVERITY_ADVISORY: 2,
        CROSSOVER_TIMBER_SEVERITY_INFORMATION: 3,
    }
    for finding in analysis.get("findings") or []:
        first_id = str(finding.get("timber_a") or "")
        second_id = str(finding.get("timber_b") or "")
        code = str(finding.get("code") or "")
        if code not in CROSSOVER_SHARED_TIMBER_TARGET_CODES or not first_id or not second_id:
            continue
        first = by_id.get(first_id)
        second = by_id.get(second_id)
        if first is None or second is None or str(first.get("turnout_side")) == str(second.get("turnout_side")):
            continue
        pair = tuple(sorted((first_id, second_id)))
        pair_codes.setdefault(pair, set()).add(code)
        rank = severity_rank.get(str(finding.get("severity") or ""), 9)
        pair_severity[pair] = min(pair_severity.get(pair, 9), rank)
    profile_timings["input_and_candidate_preparation"] = (time.perf_counter() - profile_stage_start) * 1000.0
    profile_stage_start = time.perf_counter()
    ordered_pairs = sorted(
        pair_codes,
        key=lambda pair: (
            pair_severity.get(pair, 9),
            abs(float(by_id[pair[0]].get("longitudinal_station") or 0.0) - float(by_id[pair[1]].get("longitudinal_station") or 0.0)),
            pair,
        ),
    )
    inherited_shared = []
    consumed = set()
    rejected = []
    current_records = list(inherited)
    for pair in ordered_pairs:
        if pair[0] in consumed or pair[1] in consumed:
            rejected.append({"timber_identities": list(pair), "reason": "one inherited timber was already replaced by a higher-priority shared pair", "finding_codes": sorted(pair_codes[pair])})
            continue
        candidate, reason = _shared_timber_candidate(config, by_id[pair[0]], by_id[pair[1]], settings, len(inherited_shared) + 1)
        if candidate is None:
            rejected.append({"timber_identities": list(pair), "reason": reason, "finding_codes": sorted(pair_codes[pair])})
            continue
        collision = _shared_timber_candidate_collision(candidate, current_records + inherited_shared, set(pair) | set(consumed), settings["collision_tolerance"])
        if collision is not None:
            rejected.append({
                "timber_identities": list(pair),
                "reason": "candidate would overlap unaffected timber {} by {:.3f} mm²".format(collision[1], collision[0]),
                "finding_codes": sorted(pair_codes[pair]),
            })
            continue
        candidate["resolved_finding_codes"] = sorted(pair_codes[pair])
        candidate["envelope_kind"] = "inherited A/B pair"
        inherited_shared.append(candidate)
        consumed.update(pair)

    profile_timings["inherited_pair_resolution"] = (time.perf_counter() - profile_stage_start) * 1000.0
    profile_stage_start = time.perf_counter()
    base_after_pairs = apply_shared_timber_result_to_records(inherited, {
        "consumed_timber_identities": sorted(consumed),
        "shared_timbers": inherited_shared,
    })
    inherited_envelope_shared = []
    inherited_envelope_consumed = set()
    inherited_envelope_rejected = []
    inherited_envelope_summary = {"available": False, "reason": "envelope context was not supplied"}
    if envelope_context is not None:
        inherited_envelope_shared, inherited_envelope_consumed, inherited_envelope_rejected, inherited_envelope_summary = _shared_timber_build_inherited_envelope(
            config, base_after_pairs, envelope_context, settings
        )
        consumed.update(inherited_envelope_consumed)

    profile_timings["inherited_long_timber_envelope"] = (time.perf_counter() - profile_stage_start) * 1000.0
    profile_stage_start = time.perf_counter()
    base_effective = apply_shared_timber_result_to_records(inherited, {
        "consumed_timber_identities": sorted(consumed),
        "shared_timbers": inherited_shared + inherited_envelope_shared,
    })
    connector_shared = []
    plain_connector = []
    connector_rejected = []
    connector_summary = {"available": False, "reason": "envelope context was not supplied"}
    if envelope_context is not None:
        connector_shared, plain_connector, connector_rejected, connector_summary = _shared_timber_build_envelope(
            config, base_effective, envelope_context, settings
        )

    profile_timings["connector_long_timber_envelope"] = (time.perf_counter() - profile_stage_start) * 1000.0
    profile_stage_start = time.perf_counter()
    envelope_summary = dict(connector_summary or {})
    envelope_summary["inherited_envelope"] = dict(inherited_envelope_summary or {})
    envelope_summary["connector_host_a_return_confirmed"] = bool(connector_summary.get("turnout_a_return_confirmed", True))
    envelope_summary["connector_host_b_return_confirmed"] = bool(connector_summary.get("turnout_b_return_confirmed", True))
    envelope_summary["turnout_a_return_confirmed"] = bool(inherited_envelope_summary.get("turnout_a_return_confirmed", True))
    envelope_summary["turnout_b_return_confirmed"] = bool(inherited_envelope_summary.get("turnout_b_return_confirmed", True))
    envelope_summary["return_confirmation_count"] = int(settings["envelope_return_confirmation_count"])
    envelope_summary["independent_sleeper_clearance"] = float(settings["envelope_clearance"])
    envelope_summary["long_timber_envelope_allowance"] = float(settings["long_timber_envelope_allowance"])
    envelope_summary["unresolved_position_count"] = len(inherited_envelope_rejected) + len(connector_rejected)
    envelope_summary["unresolved_station_count"] = envelope_summary["unresolved_position_count"]

    all_shared = inherited_shared + inherited_envelope_shared + connector_shared
    inherited_signature = _shared_timber_inherited_signature(config, inherited)
    effective = apply_shared_timber_result_to_records(inherited, {
        "consumed_timber_identities": sorted(consumed),
        "shared_timbers": all_shared,
        "plain_connector_timbers": plain_connector,
    })
    analysis_settings = normalise_crossover_timber_analysis_settings(analysis.get("settings"))
    profile_timings["effective_record_assembly"] = (time.perf_counter() - profile_stage_start) * 1000.0
    profile_stage_start = time.perf_counter()
    resolved_analysis = analyse_crossover_timber_records(config, effective, analysis_settings)
    profile_timings["resolved_conflict_analysis"] = (time.perf_counter() - profile_stage_start) * 1000.0
    resolved_analysis["analysis_basis"] = "Effective shared long-timber arrangement"
    resolved_analysis["production_note"] = "No (the shared long-timber result remains a preview pending automatic resolution and host integration)"
    original_counts = dict(analysis.get("severity_counts") or {})
    resolved_counts = dict(resolved_analysis.get("severity_counts") or {})
    original_critical = int(original_counts.get(CROSSOVER_TIMBER_SEVERITY_PRODUCTION_CRITICAL, 0))
    resolved_critical = int(resolved_counts.get(CROSSOVER_TIMBER_SEVERITY_PRODUCTION_CRITICAL, 0))
    if resolved_critical > original_critical:
        raise ValueError("The shared-timber envelope introduced additional production-critical findings and was rejected.")
    resolution_signature = _shared_timber_resolution_signature(
        config, settings, inherited_signature, all_shared, consumed, plain_connector, envelope_summary
    )
    remaining_conflicts = int(resolved_counts.get(CROSSOVER_TIMBER_SEVERITY_PRODUCTION_CONFLICT, 0))
    remaining_critical = int(resolved_counts.get(CROSSOVER_TIMBER_SEVERITY_PRODUCTION_CRITICAL, 0))
    generated_count = len(all_shared) + len(plain_connector)
    unresolved_envelope = int(envelope_summary.get("unresolved_position_count") or 0)
    return_confirmed = bool(envelope_summary.get("turnout_a_return_confirmed", True)) and bool(envelope_summary.get("turnout_b_return_confirmed", True))
    status = CROSSOVER_SHARED_TIMBER_STATUS_NOT_APPLIED
    if generated_count:
        if remaining_conflicts or remaining_critical:
            status = CROSSOVER_SHARED_TIMBER_STATUS_CONFLICTS
        elif unresolved_envelope:
            status = CROSSOVER_SHARED_TIMBER_STATUS_REQUIRES_B3
        elif not return_confirmed:
            status = CROSSOVER_SHARED_TIMBER_STATUS_RETURN_UNCONFIRMED
        else:
            status = CROSSOVER_SHARED_TIMBER_STATUS_CLEAR
    profile_timings["total"] = (time.perf_counter() - profile_start) * 1000.0
    return {
        "schema_version": CROSSOVER_SHARED_TIMBER_SCHEMA_VERSION,
        "macro_version": MACRO_VERSION_NUMBER,
        "crossover_id": str(config.get("crossover_id") or ""),
        "applied": bool(generated_count),
        "status": status,
        "settings": settings,
        "inherited_signature": inherited_signature,
        "resolution_signature": resolution_signature,
        "candidate_pair_count": len(ordered_pairs),
        "inherited_shared_timber_count": len(inherited_shared),
        "inherited_envelope_shared_timber_count": len(inherited_envelope_shared),
        "connector_envelope_shared_timber_count": len(connector_shared),
        "envelope_shared_timber_count": len(inherited_envelope_shared) + len(connector_shared),
        "shared_timber_count": len(all_shared),
        "plain_connector_timber_count": len(plain_connector),
        "generated_timber_count": generated_count,
        "consumed_timber_identities": sorted(consumed),
        "consumed_inherited_timber_count": len(consumed),
        "shared_timbers": all_shared,
        "plain_connector_timbers": plain_connector,
        "rejected_candidates": rejected,
        "inherited_envelope_rejections": inherited_envelope_rejected,
        "envelope_rejected_stations": connector_rejected,
        "envelope_summary": envelope_summary,
        "effective_timber_count": len(effective),
        "original_analysis": analysis,
        "resolved_analysis": resolved_analysis,
        "remaining_production_conflicts": remaining_conflicts,
        "remaining_production_critical_conflicts": remaining_critical,
        "source_basis": list(CROSSOVER_SHARED_TIMBER_SOURCE_BASIS),
        "engineering_assumptions": list(CROSSOVER_SHARED_TIMBER_ENGINEERING_ASSUMPTIONS),
        "host_integration_allowed": False,
        "host_integration_reason": "The inherited and connector shared-timber envelope is complete; controlled timber adjustment, automatic resolution and exact host sleeper replacement remain separate operations",
        "production_ready": False,
        "performance_timings_ms": profile_timings,
    }




def crossover_shared_timber_summary(result, include_rejections=True):
    data = dict(result or {})
    envelope = dict(data.get("envelope_summary") or {})
    inherited_envelope = dict(envelope.get("inherited_envelope") or {})
    connector_shared = int(data.get("connector_envelope_shared_timber_count") or 0)
    plain_count = int(data.get("plain_connector_timber_count") or 0)
    lines = [
        "Version {} — Shared long-timber envelope".format(CROSSOVER_OPERATOR_VERSION_NUMBER),
        "Crossover: {}".format(data.get("crossover_id") or "Unknown"),
        "Status: {}".format(data.get("status") or CROSSOVER_SHARED_TIMBER_STATUS_NOT_APPLIED),
        "Candidate inherited A/B pairs: {}".format(data.get("candidate_pair_count", 0)),
        "Inherited-pair shared timbers: {}".format(data.get("inherited_shared_timber_count", 0)),
        "Inherited timbers extended to long timbers: {}".format(data.get("inherited_envelope_shared_timber_count", 0)),
        "Connector-gap shared timbers: {}".format(connector_shared),
        "Total shared long timbers: {}".format(data.get("shared_timber_count", 0)),
        "Nominal connector sleepers: {}{}".format(
            plain_count,
            " (not required because the connector remains fully within the shared envelope)"
            if plain_count == 0 and connector_shared > 0 else "",
        ),
        "Inherited timbers replaced: {}".format(data.get("consumed_inherited_timber_count", 0)),
        "Effective timber count: {}".format(data.get("effective_timber_count", 0)),
        "Remaining production conflicts: {}".format(data.get("remaining_production_conflicts", 0)),
        "Remaining production-critical conflicts: {}".format(data.get("remaining_production_critical_conflicts", 0)),
        "Production ready: No",
        "Host integration allowed: No",
    ]
    if envelope.get("available"):
        lines.extend([
            "",
            "Shared-timber envelope:",
            "- Long-timber envelope allowance: {:.3f} mm beyond the {:.3f} mm independent-sleeper clearance".format(
                float(envelope.get("long_timber_envelope_allowance") or 0.0),
                float(envelope.get("independent_sleeper_clearance") or 0.0),
            ),
            "- Nominal Main template widths: A {:.3f} mm; B {:.3f} mm; connector {:.3f} mm".format(
                float(envelope.get("nominal_template_width_a") or 0.0),
                float(envelope.get("nominal_template_width_b") or 0.0),
                float(envelope.get("nominal_connector_template_width") or 0.0),
            ),
            "- Host A return to nominal sleeper width confirmed: {}".format("Yes" if envelope.get("turnout_a_return_confirmed") else "No"),
            "- Host B return to nominal sleeper width confirmed: {}".format("Yes" if envelope.get("turnout_b_return_confirmed") else "No"),
            "- Consecutive clear sleeper positions required: {}".format(int(envelope.get("return_confirmation_count") or 0)),
            "- Connector-road length: {:.3f} mm".format(float(envelope.get("path_length") or 0.0)),
            "- Fitted connector sleeper spacing: {:.3f} mm across {} intervals".format(
                float(envelope.get("actual_spacing") or 0.0), int(envelope.get("interval_count") or 0)
            ),
            "- Three-route shared connector positions: {}".format(int(envelope.get("three_route_envelope_timber_count") or 0)),
            "- Unresolved envelope positions: {}".format(int(envelope.get("unresolved_position_count") or envelope.get("unresolved_station_count") or 0)),
        ])
        if inherited_envelope:
            lines.extend([
                "- Host A inherited timbers extended: {}".format(int(inherited_envelope.get("turnout_a_extended_count") or 0)),
                "- Host B inherited timbers extended: {}".format(int(inherited_envelope.get("turnout_b_extended_count") or 0)),
            ])
    elif envelope.get("reason"):
        lines.extend(["", "Shared-timber envelope unavailable: {}".format(envelope.get("reason"))])
    if data.get("shared_timbers"):
        lines.extend(["", "Created shared timbers:"])
        for timber in data.get("shared_timbers") or []:
            lines.append("- {}: {} mm long × {} mm wide ({})".format(
                timber.get("stable_identity"),
                "{:.3f}".format(float(timber.get("length") or 0.0)),
                "{:.3f}".format(float(timber.get("width") or 0.0)),
                timber.get("envelope_kind") or "shared",
            ))
    timings = dict(data.get("performance_timings_ms") or {})
    if timings:
        lines.extend([
            "",
            "Live performance profile:",
            "- Input and candidate preparation: {:.1f} ms".format(float(timings.get("input_and_candidate_preparation") or 0.0)),
            "- Inherited-pair resolution: {:.1f} ms".format(float(timings.get("inherited_pair_resolution") or 0.0)),
            "- Inherited long-timber envelope: {:.1f} ms".format(float(timings.get("inherited_long_timber_envelope") or 0.0)),
            "- Connector long-timber envelope: {:.1f} ms".format(float(timings.get("connector_long_timber_envelope") or 0.0)),
            "- Resolved conflict analysis: {:.1f} ms".format(float(timings.get("resolved_conflict_analysis") or 0.0)),
            "- Total shared-envelope calculation: {:.1f} ms".format(float(timings.get("total") or 0.0)),
        ])
    if include_rejections:
        lines.extend(["", "Rejected inherited-pair candidates:"])
        for rejection in data.get("rejected_candidates") or []:
            lines.append("- {}: {}".format(" / ".join(rejection.get("timber_identities") or []), rejection.get("reason") or "rejected"))
    if include_rejections and data.get("inherited_envelope_rejections"):
        lines.extend(["", "Inherited timbers requiring later resolution:"])
        for rejection in data.get("inherited_envelope_rejections") or []:
            lines.append("- {}: {}".format(rejection.get("timber_identity") or "unknown timber", rejection.get("reason") or "rejected"))
    if include_rejections and data.get("envelope_rejected_stations"):
        lines.extend(["", "Unresolved connector-envelope positions:"])
        for rejection in data.get("envelope_rejected_stations") or []:
            lines.append("- {:.3f} mm along the connector ({}): {}".format(
                float(rejection.get("station") or 0.0),
                " + ".join(rejection.get("route_kinds") or []),
                rejection.get("reason") or "rejected",
            ))
    return "\n".join(lines)



def _shared_timber_shape_from_records(records, z_value=0.0):
    wires = []
    for record in records or []:
        points = [tuple(point) for point in record.get("outline_polygon") or []]
        if len(points) < 3:
            continue
        vectors = [App.Vector(float(point[0]), float(point[1]), float(z_value)) for point in points]
        vectors.append(vectors[0])
        wires.append(Part.makePolygon(vectors))
    return Part.makeCompound(wires) if wires else None


def _crossover_group_object(doc, crossover_id):
    for obj in _crossover_objects(doc, crossover_id):
        if object_string_property(obj, "GeneratedRole", "") == CROSSOVER_GROUP_ROLE:
            return obj
    return None


def _crossover_shared_timber_object(doc, crossover_id):
    for obj in _crossover_objects(doc, crossover_id):
        if object_string_property(obj, "GeneratedRole", "") == CROSSOVER_SHARED_TIMBER_ROLE:
            return obj
    return None



def _write_crossover_shared_timber_metadata(doc, config, result):
    updated = dict(config or {})
    updated["shared_timber_schema_version"] = CROSSOVER_SHARED_TIMBER_SCHEMA_VERSION
    updated["shared_timber_status"] = str(result.get("status") or CROSSOVER_SHARED_TIMBER_STATUS_NOT_APPLIED)
    updated["shared_timber_signature"] = str(result.get("resolution_signature") or "")
    updated["shared_timber_settings"] = normalise_crossover_shared_timber_settings(result.get("settings"))
    updated["shared_timber_summary"] = {
        "candidate_pair_count": int(result.get("candidate_pair_count") or 0),
        "inherited_shared_timber_count": int(result.get("inherited_shared_timber_count") or 0),
        "inherited_envelope_shared_timber_count": int(result.get("inherited_envelope_shared_timber_count") or 0),
        "connector_envelope_shared_timber_count": int(result.get("connector_envelope_shared_timber_count") or 0),
        "envelope_shared_timber_count": int(result.get("envelope_shared_timber_count") or 0),
        "shared_timber_count": int(result.get("shared_timber_count") or 0),
        "plain_connector_timber_count": int(result.get("plain_connector_timber_count") or 0),
        "generated_timber_count": int(result.get("generated_timber_count") or 0),
        "consumed_inherited_timber_count": int(result.get("consumed_inherited_timber_count") or 0),
        "effective_timber_count": int(result.get("effective_timber_count") or 0),
        "remaining_production_conflicts": int(result.get("remaining_production_conflicts") or 0),
        "remaining_production_critical_conflicts": int(result.get("remaining_production_critical_conflicts") or 0),
        "envelope_unresolved_station_count": int((result.get("envelope_summary") or {}).get("unresolved_position_count") or (result.get("envelope_summary") or {}).get("unresolved_station_count") or 0),
        "turnout_a_return_confirmed": bool((result.get("envelope_summary") or {}).get("turnout_a_return_confirmed", False)),
        "turnout_b_return_confirmed": bool((result.get("envelope_summary") or {}).get("turnout_b_return_confirmed", False)),
    }
    updated["shared_timber_result"] = dict(result)
    updated["b3_status"] = CROSSOVER_B3_STATUS_NOT_APPLIED
    updated["b3_signature"] = ""
    updated["b3_summary"] = {}
    updated["b3_result"] = {}
    updated["b4_status"] = CROSSOVER_B4_STATUS_NOT_APPLIED
    updated["b4_signature"] = ""
    updated["b4_summary"] = {}
    updated["b4_result"] = {}
    updated["timbering_status"] = str(result.get("status") or CROSSOVER_SHARED_TIMBER_STATUS_NOT_APPLIED)
    # The caller immediately writes a fresh effective analysis in the same transaction.
    updated["timber_analysis_status"] = CROSSOVER_TIMBER_ANALYSIS_STATUS_STALE
    updated["timber_analysis_signature"] = ""
    updated["timber_analysis_summary"] = {}
    updated["timber_analysis_result_cached"] = False
    updated["production_ready"] = False
    updated["host_integration_allowed"] = False
    if not updated.get("integration_active"):
        updated["integration_status"] = CROSSOVER_INTEGRATION_STATUS_NOT_INTEGRATED
    updated["host_integration_reason"] = "The shared long-timber envelope is a validated preview; resolve remaining conflicts automatically before host integration"
    settings_object = None
    for obj in _crossover_objects(doc, updated.get("crossover_id")):
        if object_string_property(obj, "GeneratedRole", "") == CROSSOVER_SETTINGS_ROLE:
            settings_object = obj
        _crossover_add_identity_properties(obj, updated.get("crossover_id"), updated)
    if settings_object is None:
        raise ValueError("The crossover settings object is missing.")
    properties = [
        ensure_property(settings_object, "App::PropertyString", CROSSOVER_SHARED_TIMBER_SETTINGS_PROPERTY, "Crossover shared timbers", "Validated shared long-timber settings"),
        ensure_property(settings_object, "App::PropertyString", CROSSOVER_SHARED_TIMBER_RESULT_PROPERTY, "Crossover shared timbers", "Complete shared long-timber envelope result"),
    ]
    setattr(settings_object, CROSSOVER_SHARED_TIMBER_SETTINGS_PROPERTY, json.dumps(updated["shared_timber_settings"], sort_keys=True))
    setattr(settings_object, CROSSOVER_SHARED_TIMBER_RESULT_PROPERTY, json.dumps(result, sort_keys=True))
    if CROSSOVER_B3_RESULT_PROPERTY in getattr(settings_object, "PropertiesList", []):
        setattr(settings_object, CROSSOVER_B3_RESULT_PROPERTY, "")
    if CROSSOVER_B4_RESULT_PROPERTY in getattr(settings_object, "PropertiesList", []):
        setattr(settings_object, CROSSOVER_B4_RESULT_PROPERTY, "")
    set_read_only(settings_object, properties)
    _crossover_store_catalogue(doc, str(updated.get("template_set_id") or ""))
    return updated




def apply_crossover_shared_long_timbers(doc, crossover_id, settings=None):
    clear_chair_analysis_display(doc, "crossover", str(crossover_id or "").strip())
    existing_config = crossover_config_by_id(doc, str(crossover_id or "").strip())
    if existing_config is not None and bool(existing_config.get("integration_active", False)):
        raise ValueError("Remove the crossover host integration before changing the resolved timber arrangement.")
    identifier = str(crossover_id or "").strip()
    config = crossover_config_by_id(doc, identifier)
    if config is None:
        raise ValueError("Crossover {} was not found.".format(identifier or "selection"))
    inherited = crossover_inherited_timber_records(doc, config)
    analysis_settings = normalise_crossover_timber_analysis_settings(config.get("timber_analysis_settings"))
    inherited_analysis = analyse_crossover_timber_records(config, inherited, analysis_settings)
    envelope_context = crossover_shared_timber_envelope_context(doc, config, inherited)
    result = propose_crossover_shared_long_timbers(config, inherited, inherited_analysis, settings, envelope_context)
    if not result.get("generated_timber_count"):
        return result
    effective_records = apply_shared_timber_result_to_records(inherited, result)
    shape = _shared_timber_shape_from_records(
        effective_records,
        float(config.get("template_thickness") or TEMPLATE_THICKNESS) + 0.020,
    )
    if shape is None or _shape_is_null(shape):
        raise ValueError("FreeCAD could not create the complete shared timbering-envelope display geometry.")
    transaction_open = False
    try:
        doc.openTransaction("Apply Version {} shared timber envelope {}".format(MACRO_VERSION_NUMBER, identifier))
        transaction_open = True
        previous_b4 = _crossover_b4_object(doc, identifier)
        if previous_b4 is not None:
            doc.removeObject(str(previous_b4.Name))
        previous_b3 = _crossover_b3_object(doc, identifier)
        if previous_b3 is not None:
            doc.removeObject(str(previous_b3.Name))
        previous = _crossover_shared_timber_object(doc, identifier)
        if previous is not None:
            doc.removeObject(str(previous.Name))
        group = _crossover_group_object(doc, identifier)
        if group is None:
            raise ValueError("The crossover document group is missing.")
        obj = doc.addObject("Part::Feature", unique_internal_name(doc, "RailwayCrossoverSharedTimbers_{}".format(identifier.replace("-", "_"))))
        obj.Label = "{} Effective Shared Timbering Envelope".format(identifier)
        obj.Shape = shape
        tag_generated_object(obj, CROSSOVER_SHARED_TIMBER_ROLE, config.get("template_set_id"))
        tag_route_metadata(obj, identifier, "Managed REA C10 crossover")
        updated = _write_crossover_shared_timber_metadata(doc, config, result)
        _crossover_add_identity_properties(obj, identifier, updated)
        properties = [
            ensure_property(obj, "App::PropertyString", "SharedTimberSourceIdentitiesJSON", "Crossover shared timbers", "Inherited timber identities replaced by the shared long-timber envelope"),
            ensure_property(obj, "App::PropertyString", "SharedTimberRecordsJSON", "Crossover shared timbers", "Stable shared long-timber records including the complete envelope"),
            ensure_property(obj, "App::PropertyString", "PlainConnectorTimberRecordsJSON", "Crossover shared timbers", "Nominal-width connector sleeper records after envelope clearance"),
            ensure_property(obj, "App::PropertyString", "SharedTimberEnvelopeSummaryJSON", "Crossover shared timbers", "Complete inherited and connector envelope extents"),
        ]
        obj.SharedTimberSourceIdentitiesJSON = json.dumps(result.get("consumed_timber_identities") or [], sort_keys=True)
        obj.SharedTimberRecordsJSON = json.dumps(result.get("shared_timbers") or [], sort_keys=True)
        obj.PlainConnectorTimberRecordsJSON = json.dumps(result.get("plain_connector_timbers") or [], sort_keys=True)
        obj.SharedTimberEnvelopeSummaryJSON = json.dumps(result.get("envelope_summary") or {}, sort_keys=True)
        set_read_only(obj, properties)
        group.addObject(obj)
        try:
            obj.ViewObject.LineColor = (0.10, 0.60, 0.25)
            obj.ViewObject.LineWidth = 2.5
            obj.ViewObject.Visibility = bool(result.get("settings", {}).get("show_shared_timber_geometry", True))
        except Exception:
            pass
        reference = next((item for item in _crossover_objects(doc, identifier) if object_string_property(item, "GeneratedRole", "") == CROSSOVER_TIMBER_REFERENCE_ROLE), None)
        if reference is not None:
            try:
                reference.ViewObject.Visibility = False
            except Exception:
                pass
        _remove_crossover_timber_analysis_objects(doc, identifier)
        resolved_analysis = dict(result.get("resolved_analysis") or analyse_crossover_timber_records(updated, effective_records, analysis_settings))
        resolved_analysis["settings"] = analysis_settings
        resolved_analysis["geometry_signature"] = _timber_geometry_signature(updated, analysis_settings, effective_records)
        resolved_analysis["cache_reused"] = False
        resolved_analysis["analysis_basis"] = "Effective shared long-timber arrangement"
        resolved_analysis["production_note"] = "No (the shared long-timber result remains a preview pending automatic resolution and host integration)"
        resolved_analysis["host_integration_reason"] = updated.get("host_integration_reason")
        updated = _write_crossover_timber_analysis_metadata(doc, updated, resolved_analysis)
        _create_crossover_timber_analysis_display(doc, updated, resolved_analysis)
        _document_recompute(doc)
        doc.commitTransaction()
        transaction_open = False
    except Exception:
        if transaction_open:
            try:
                doc.abortTransaction()
            except Exception:
                pass
        raise
    result["resolved_analysis"] = resolved_analysis
    return result



def clear_crossover_shared_long_timbers(doc, crossover_id):
    clear_chair_analysis_display(doc, "crossover", str(crossover_id or "").strip())
    existing_config = crossover_config_by_id(doc, str(crossover_id or "").strip())
    if existing_config is not None and bool(existing_config.get("integration_active", False)):
        raise ValueError("Remove the crossover host integration before changing the resolved timber arrangement.")
    identifier = str(crossover_id or "").strip()
    config = crossover_config_by_id(doc, identifier)
    if config is None:
        raise ValueError("Crossover {} was not found.".format(identifier or "selection"))
    transaction_open = False
    try:
        doc.openTransaction("Remove Version {} shared timber envelope {}".format(MACRO_VERSION_NUMBER, identifier))
        transaction_open = True
        b4_object = _crossover_b4_object(doc, identifier)
        if b4_object is not None:
            doc.removeObject(str(b4_object.Name))
        b3_object = _crossover_b3_object(doc, identifier)
        if b3_object is not None:
            doc.removeObject(str(b3_object.Name))
        shared = _crossover_shared_timber_object(doc, identifier)
        if shared is not None:
            doc.removeObject(str(shared.Name))
        updated = dict(config)
        updated["shared_timber_status"] = CROSSOVER_SHARED_TIMBER_STATUS_NOT_APPLIED
        updated["shared_timber_signature"] = ""
        updated["shared_timber_summary"] = {}
        updated["shared_timber_result"] = {}
        updated["b3_status"] = CROSSOVER_B3_STATUS_NOT_APPLIED
        updated["b3_signature"] = ""
        updated["b3_summary"] = {}
        updated["b3_result"] = {}
        updated["b4_status"] = CROSSOVER_B4_STATUS_NOT_APPLIED
        updated["b4_signature"] = ""
        updated["b4_summary"] = {}
        updated["b4_result"] = {}
        updated["timbering_status"] = CROSSOVER_TIMBER_STATUS_UNRESOLVED
        updated["timber_analysis_status"] = CROSSOVER_TIMBER_ANALYSIS_STATUS_STALE
        updated["timber_analysis_signature"] = ""
        updated["timber_analysis_summary"] = {}
        updated["timber_analysis_result_cached"] = False
        updated["production_ready"] = False
        updated["host_integration_allowed"] = False
        if not updated.get("integration_active"):
            updated["integration_status"] = CROSSOVER_INTEGRATION_STATUS_NOT_INTEGRATED
        updated["host_integration_reason"] = "Automatic crossover timber resolution is not yet complete"
        for obj in _crossover_objects(doc, identifier):
            _crossover_add_identity_properties(obj, identifier, updated)
            if object_string_property(obj, "GeneratedRole", "") == CROSSOVER_SETTINGS_ROLE:
                if CROSSOVER_SHARED_TIMBER_RESULT_PROPERTY in getattr(obj, "PropertiesList", []):
                    setattr(obj, CROSSOVER_SHARED_TIMBER_RESULT_PROPERTY, "")
                if CROSSOVER_B3_RESULT_PROPERTY in getattr(obj, "PropertiesList", []):
                    setattr(obj, CROSSOVER_B3_RESULT_PROPERTY, "")
                if CROSSOVER_B4_RESULT_PROPERTY in getattr(obj, "PropertiesList", []):
                    setattr(obj, CROSSOVER_B4_RESULT_PROPERTY, "")
        reference = next((item for item in _crossover_objects(doc, identifier) if object_string_property(item, "GeneratedRole", "") == CROSSOVER_TIMBER_REFERENCE_ROLE), None)
        if reference is not None:
            try:
                reference.ViewObject.Visibility = True
            except Exception:
                pass
        _remove_crossover_timber_analysis_objects(doc, identifier)
        inherited = crossover_inherited_timber_records(doc, updated)
        analysis_settings = normalise_crossover_timber_analysis_settings(updated.get("timber_analysis_settings"))
        inherited_analysis = analyse_crossover_timber_records(updated, inherited, analysis_settings)
        inherited_analysis["settings"] = analysis_settings
        inherited_analysis["geometry_signature"] = _timber_geometry_signature(updated, analysis_settings, inherited)
        inherited_analysis["cache_reused"] = False
        inherited_analysis["analysis_basis"] = "Inherited turnout reference timbering"
        inherited_analysis["production_note"] = "No (timber analysis is diagnostic only)"
        inherited_analysis["host_integration_reason"] = updated.get("host_integration_reason")
        updated = _write_crossover_timber_analysis_metadata(doc, updated, inherited_analysis)
        _create_crossover_timber_analysis_display(doc, updated, inherited_analysis)
        _document_recompute(doc)
        doc.commitTransaction()
        transaction_open = False
    except Exception:
        if transaction_open:
            try:
                doc.abortTransaction()
            except Exception:
                pass
        raise
    return identifier


def set_crossover_shared_timber_visibility(doc, crossover_id, visible):
    obj = _crossover_shared_timber_object(doc, crossover_id)
    if obj is None:
        return False
    try:
        obj.ViewObject.Visibility = bool(visible)
        return True
    except Exception:
        return False


def crossover_shared_timber_effective_status(doc, crossover_config):
    config = dict(crossover_config or {})
    result = config.get("shared_timber_result")
    if not isinstance(result, dict) or not result.get("applied"):
        return CROSSOVER_SHARED_TIMBER_STATUS_NOT_APPLIED
    stored_signature = str(config.get("shared_timber_signature") or "")
    if not stored_signature:
        return CROSSOVER_SHARED_TIMBER_STATUS_STALE
    try:
        inherited = crossover_inherited_timber_records(doc, config)
        inherited_signature = _shared_timber_inherited_signature(config, inherited)
        expected_signature = _shared_timber_resolution_signature(
            config,
            result.get("settings"),
            inherited_signature,
            result.get("shared_timbers") or [],
            result.get("consumed_timber_identities") or [],
            result.get("plain_connector_timbers") or [],
            result.get("envelope_summary") or {},
        )
    except Exception:
        return CROSSOVER_SHARED_TIMBER_STATUS_STALE
    if str(result.get("inherited_signature") or "") != inherited_signature:
        return CROSSOVER_SHARED_TIMBER_STATUS_STALE
    if str(result.get("resolution_signature") or "") != expected_signature or stored_signature != expected_signature:
        return CROSSOVER_SHARED_TIMBER_STATUS_STALE
    return str(config.get("shared_timber_status") or result.get("status") or CROSSOVER_SHARED_TIMBER_STATUS_APPLIED)




# Stage A8A6B3 controlled interlacing and longitudinal timber shoving.


def default_crossover_b3_settings():
    return {
        "schema_version": CROSSOVER_B3_SCHEMA_VERSION,
        "maximum_timber_movement": CROSSOVER_B3_MAXIMUM_MOVEMENT,
        "movement_increment": CROSSOVER_B3_MOVEMENT_INCREMENT,
        "minimum_clear_spacing": CROSSOVER_B3_MINIMUM_CLEAR_SPACING,
        "maximum_interlacing_separation": CROSSOVER_B3_MAXIMUM_INTERLACING_SEPARATION,
        "maximum_angle_difference_degrees": CROSSOVER_B3_MAXIMUM_ANGLE_DIFFERENCE_DEGREES,
        "protected_support_movement_allowance": CROSSOVER_B3_PROTECTED_MOVEMENT_ALLOWANCE,
        "collision_tolerance": CROSSOVER_B3_COLLISION_TOLERANCE,
        "resolve_advisory_same_position": False,
        "show_b3_geometry": True,
    }


def normalise_crossover_b3_settings(source=None):
    result = default_crossover_b3_settings()
    if isinstance(source, dict):
        result.update(source)
    specifications = (
        ("maximum_timber_movement", 0.0, 10.0),
        ("movement_increment", 0.01, 2.0),
        ("minimum_clear_spacing", 0.0, 10.0),
        ("maximum_interlacing_separation", 0.0, 20.0),
        ("maximum_angle_difference_degrees", 0.1, 30.0),
        ("protected_support_movement_allowance", 0.0, 5.0),
        ("collision_tolerance", 0.0, 5.0),
    )
    defaults = default_crossover_b3_settings()
    for key, minimum, maximum in specifications:
        try:
            value = float(result.get(key))
        except Exception:
            value = float(defaults[key])
        if not math.isfinite(value):
            value = float(defaults[key])
        result[key] = max(minimum, min(maximum, value))
    result["movement_increment"] = min(
        max(0.01, result["movement_increment"]),
        max(0.01, result["maximum_timber_movement"] or result["movement_increment"]),
    )
    result["resolve_advisory_same_position"] = bool(result.get("resolve_advisory_same_position", False))
    result["show_b3_geometry"] = bool(result.get("show_b3_geometry", True))
    result["schema_version"] = CROSSOVER_B3_SCHEMA_VERSION
    return result


def _b3_stable_record(record):
    return {
        "id": str(record.get("stable_identity") or ""),
        "centre": [round(float(value), 6) for value in record.get("centre") or (0.0, 0.0)],
        "angle": round(float(record.get("angle_radians") or 0.0), 9),
        "width": round(float(record.get("width") or 0.0), 6),
        "length": round(float(record.get("length") or 0.0), 6),
        "polygon": [
            [round(float(point[0]), 6), round(float(point[1]), 6)]
            for point in record.get("collision_polygon") or []
        ],
        "side": str(record.get("turnout_side") or ""),
        "movement": round(float(record.get("b3_total_movement_mm") or 0.0), 6),
        "operation": str(record.get("b3_operation") or ""),
        "features": sorted(str(value) for value in record.get("protected_features") or []),
    }


def _b3_base_signature(crossover_config, records):
    payload = {
        "schema_version": CROSSOVER_B3_SCHEMA_VERSION,
        "crossover_id": str((crossover_config or {}).get("crossover_id") or ""),
        "shared_timber_signature": str((crossover_config or {}).get("shared_timber_signature") or ""),
        "records": [_b3_stable_record(record) for record in sorted(records or [], key=lambda item: str(item.get("stable_identity") or ""))],
    }
    return hashlib.sha256(json.dumps(payload, sort_keys=True, separators=(",", ":")).encode("utf-8")).hexdigest()


def _b3_resolution_signature(crossover_config, settings, base_signature, records, operations, unresolved):
    payload = {
        "schema_version": CROSSOVER_B3_SCHEMA_VERSION,
        "crossover_id": str((crossover_config or {}).get("crossover_id") or ""),
        "base_signature": str(base_signature),
        "settings": normalise_crossover_b3_settings(settings),
        "records": [_b3_stable_record(record) for record in sorted(records or [], key=lambda item: str(item.get("stable_identity") or ""))],
        "operations": [
            {
                "kind": str(item.get("kind") or ""),
                "timbers": sorted(str(value) for value in item.get("timber_identities") or []),
                "movements": {
                    str(key): round(float(value), 6)
                    for key, value in sorted(dict(item.get("movements_mm") or {}).items())
                },
                "reason": str(item.get("reason") or ""),
            }
            for item in operations or []
        ],
        "unresolved": [
            {
                "timbers": sorted(str(value) for value in item.get("timber_identities") or []),
                "reason": str(item.get("reason") or ""),
                "source": str(item.get("source") or ""),
            }
            for item in unresolved or []
        ],
    }
    return hashlib.sha256(json.dumps(payload, sort_keys=True, separators=(",", ":")).encode("utf-8")).hexdigest()


def _b3_deepcopy(value):
    return json.loads(json.dumps(value))


def _b3_is_movable(record):
    return str(record.get("turnout_side") or "") in ("A", "B") and not bool(
        record.get("shared_long_timber") or record.get("plain_connector_sleeper")
    )


def _b3_protected_limit(record, settings):
    settings = normalise_crossover_b3_settings(settings)
    maximum = float(settings["maximum_timber_movement"])
    features = set(str(value) for value in record.get("protected_features") or [])
    if features.intersection(CROSSOVER_B3_STRICT_PROTECTED_FEATURES):
        return min(maximum, float(settings["protected_support_movement_allowance"]))
    return maximum


def _b3_shift_points(points, delta):
    dx, dy = float(delta[0]), float(delta[1])
    return [[float(point[0]) + dx, float(point[1]) + dy] for point in points or []]


def _b3_shift_segments(segments, delta):
    return [_b3_shift_points(segment, delta) for segment in segments or []]


def _b3_shift_record(record, movement, operation_kind, paired_identity=""):
    shifted = _b3_deepcopy(record)
    movement = float(movement)
    heading = float(record.get("local_rail_heading_radians") or 0.0)
    delta = (movement * math.cos(heading), movement * math.sin(heading))
    old_centre = tuple(float(value) for value in record.get("centre") or (0.0, 0.0))
    new_centre = (old_centre[0] + delta[0], old_centre[1] + delta[1])
    original_support_centre = list(
        record.get("b3_original_support_centre")
        or (record.get("source_configuration") or {}).get("b3_original_support_centre")
        or record.get("centre")
        or (0.0, 0.0)
    )
    shifted["centre"] = [new_centre[0], new_centre[1]]
    shifted["outline_polygon"] = _b3_shift_points(record.get("outline_polygon"), delta)
    shifted["collision_polygon"] = _b3_shift_points(record.get("collision_polygon"), delta)
    shifted["bounding_box"] = list(_timber_bbox([tuple(point) for point in shifted["collision_polygon"]]))
    shifted["near_end_segment"] = _b3_shift_points(record.get("near_end_segment"), delta)
    shifted["far_end_segment"] = _b3_shift_points(record.get("far_end_segment"), delta)
    shifted["side_segments"] = _b3_shift_segments(record.get("side_segments"), delta)
    previous_total = float(record.get("b3_total_movement_mm") or 0.0)
    total = previous_total + movement
    reference_axis = tuple(
        record.get("longitudinal_reference_axis")
        or (record.get("source_configuration") or {}).get("longitudinal_reference_axis")
        or record.get("width_axis")
        or (math.cos(heading), math.sin(heading))
    )
    try:
        reference_axis = _timber_unit(reference_axis)
    except Exception:
        reference_axis = (math.cos(heading), math.sin(heading))
    station_movement = _timber_dot(delta, reference_axis)
    shifted["longitudinal_reference_axis"] = [reference_axis[0], reference_axis[1]]
    shifted["longitudinal_station"] = float(record.get("longitudinal_station") or 0.0) + station_movement
    shifted["host_chainage"] = float(record.get("host_chainage") or 0.0) + movement
    shifted["b3_original_support_centre"] = original_support_centre
    shifted["b3_total_movement_mm"] = total
    shifted["b3_last_movement_mm"] = movement
    shifted["b3_operation"] = str(operation_kind)
    shifted["b3_paired_identity"] = str(paired_identity or "")
    shifted["controlled_shove"] = abs(total) > 1.0e-9
    shifted["interlaced_timber"] = str(operation_kind).startswith("interlac")
    source = dict(shifted.get("source_configuration") or {})
    source.update({
        "source_note": "A8A6B3 controlled longitudinal timber movement; original rail and timber solvers unchanged",
        "b3_original_support_centre": original_support_centre,
        "b3_total_movement_mm": total,
        "b3_last_movement_mm": movement,
        "b3_operation": str(operation_kind),
        "b3_paired_identity": str(paired_identity or ""),
        "longitudinal_reference_axis": [reference_axis[0], reference_axis[1]],
    })
    shifted["source_configuration"] = source
    return shifted


def _b3_support_preserved(record, settings):
    if not _b3_is_movable(record):
        return True, ""
    movement = abs(float(record.get("b3_total_movement_mm") or 0.0))
    limit = _b3_protected_limit(record, settings)
    if movement > limit + 1.0e-9:
        return False, "movement {:.3f} mm exceeds the {:.3f} mm support limit".format(movement, limit)
    support = tuple(record.get("b3_original_support_centre") or record.get("centre") or (0.0, 0.0))
    polygon = [tuple(point) for point in record.get("collision_polygon") or []]
    if len(polygon) < 3 or not _timber_point_in_convex_polygon(support, polygon, 1.0e-7):
        return False, "the original protected support centre would no longer lie inside the moved timber"
    return True, ""


def _b3_polygon_clearance(first_polygon, second_polygon):
    first = [tuple(point) for point in first_polygon or []]
    second = [tuple(point) for point in second_polygon or []]
    if len(first) < 3 or len(second) < 3:
        return float("inf")
    intersection = _timber_convex_intersection(first, second)
    if len(intersection) >= 3 and abs(_timber_polygon_area(intersection)) > 1.0e-12:
        return 0.0
    best = float("inf")
    for point in first:
        for start, finish in _shared_timber_polygon_segments(second):
            distance, _nearest = _timber_point_segment_distance(point, start, finish)
            best = min(best, float(distance))
    for point in second:
        for start, finish in _shared_timber_polygon_segments(first):
            distance, _nearest = _timber_point_segment_distance(point, start, finish)
            best = min(best, float(distance))
    return best


def _b3_aligned_longitudinal_axes(first, second):
    heading_a = float(first.get("local_rail_heading_radians") or 0.0)
    heading_b = float(second.get("local_rail_heading_radians") or 0.0)
    axis_a = (math.cos(heading_a), math.sin(heading_a))
    axis_b = (math.cos(heading_b), math.sin(heading_b))
    direction_relationship = 1.0
    if _timber_dot(axis_a, axis_b) < 0.0:
        axis_b = (-axis_b[0], -axis_b[1])
        direction_relationship = -1.0
    combined = _timber_add(axis_a, axis_b)
    try:
        physical_axis = _timber_unit(combined)
    except Exception:
        physical_axis = axis_a
    return axis_a, axis_b, physical_axis, direction_relationship


def _b3_pair_geometry(first, second, minimum_spacing, collision_tolerance):
    polygon_a = [tuple(point) for point in first.get("collision_polygon") or []]
    polygon_b = [tuple(point) for point in second.get("collision_polygon") or []]
    intersection = _timber_convex_intersection(polygon_a, polygon_b)
    overlap = abs(_timber_polygon_area(intersection)) if len(intersection) >= 3 else 0.0
    clearance = _b3_polygon_clearance(polygon_a, polygon_b)
    required_centre_spacing = 0.5 * (float(first.get("width") or 0.0) + float(second.get("width") or 0.0)) + float(minimum_spacing)
    _axis_a, _axis_b, physical_axis, direction_relationship = _b3_aligned_longitudinal_axes(first, second)
    centre_a = tuple(float(value) for value in first.get("centre") or (0.0, 0.0))
    centre_b = tuple(float(value) for value in second.get("centre") or (0.0, 0.0))
    longitudinal_difference = abs(_timber_dot(_timber_subtract(centre_b, centre_a), physical_axis))
    clear = overlap <= float(collision_tolerance) + 1.0e-9 and clearance + 1.0e-9 >= float(minimum_spacing) and longitudinal_difference + 1.0e-9 >= required_centre_spacing
    return {
        "clear": bool(clear),
        "overlap_area_mm2": overlap,
        "clearance_mm": clearance,
        "longitudinal_difference_mm": longitudinal_difference,
        "required_centre_spacing_mm": required_centre_spacing,
        "physical_longitudinal_axis": [physical_axis[0], physical_axis[1]],
        "host_travel_direction_relationship": direction_relationship,
    }


def _b3_production_conflict_keys(analysis):
    keys = set()
    for finding in (analysis or {}).get("findings") or []:
        if str(finding.get("severity") or "") not in (
            CROSSOVER_TIMBER_SEVERITY_PRODUCTION_CONFLICT,
            CROSSOVER_TIMBER_SEVERITY_PRODUCTION_CRITICAL,
        ):
            continue
        pair = tuple(sorted(filter(None, [str(finding.get("timber_a") or ""), str(finding.get("timber_b") or "")])))
        keys.add((str(finding.get("code") or ""), pair))
    return keys


def _b3_filter_interlaced_findings(analysis, records, settings):
    # The input analysis is read-only. A shallow result copy avoids serialising
    # every timber and finding merely to remove findings already proven clear.
    result = dict(analysis or {})
    by_id = {str(record.get("stable_identity") or ""): record for record in records or []}
    removable_codes = {
        "timber_body_intersection",
        "timber_fully_covers_another",
        "duplicate_conflicting_support",
        "near_touching_timber_ends",
        "inadequate_facing_end_clearance",
        "insufficient_side_to_side_spacing",
        "effectively_same_longitudinal_station",
    }
    retained = []
    for finding in result.get("findings") or []:
        code = str(finding.get("code") or "")
        first = by_id.get(str(finding.get("timber_a") or ""))
        second = by_id.get(str(finding.get("timber_b") or ""))
        remove = False
        if code in removable_codes and first is not None and second is not None and str(first.get("turnout_side") or "") != str(second.get("turnout_side") or ""):
            geometry = _b3_pair_geometry(first, second, settings["minimum_clear_spacing"], settings["collision_tolerance"])
            remove = bool(geometry["clear"])
        if not remove:
            retained.append(finding)
    result["findings"] = _b3_deepcopy(retained)
    severity_counts = {
        CROSSOVER_TIMBER_SEVERITY_INFORMATION: 0,
        CROSSOVER_TIMBER_SEVERITY_ADVISORY: 0,
        CROSSOVER_TIMBER_SEVERITY_PRODUCTION_CONFLICT: 0,
        CROSSOVER_TIMBER_SEVERITY_PRODUCTION_CRITICAL: 0,
    }
    for finding in retained:
        severity = str(finding.get("severity") or "")
        severity_counts[severity] = severity_counts.get(severity, 0) + 1
    result["severity_counts"] = severity_counts
    statistics = dict(result.get("statistics") or {})
    statistics["informational_findings"] = severity_counts[CROSSOVER_TIMBER_SEVERITY_INFORMATION]
    statistics["advisory_findings"] = severity_counts[CROSSOVER_TIMBER_SEVERITY_ADVISORY]
    statistics["production_conflicts"] = severity_counts[CROSSOVER_TIMBER_SEVERITY_PRODUCTION_CONFLICT]
    statistics["production_critical_conflicts"] = severity_counts[CROSSOVER_TIMBER_SEVERITY_PRODUCTION_CRITICAL]
    result["statistics"] = statistics
    if severity_counts[CROSSOVER_TIMBER_SEVERITY_PRODUCTION_CRITICAL] > 0:
        status = CROSSOVER_TIMBER_ANALYSIS_STATUS_CRITICAL
    elif severity_counts[CROSSOVER_TIMBER_SEVERITY_PRODUCTION_CONFLICT] > 0:
        status = CROSSOVER_TIMBER_ANALYSIS_STATUS_CONFLICTS
    else:
        status = CROSSOVER_TIMBER_ANALYSIS_STATUS_CLEAR
    result["analysis_status"] = status
    result["overall_timbering_status"] = status
    result["b3_interlacing_filter_applied"] = True
    return result


def _b3_analysis_for_records(
    crossover_config, records, analysis_settings, b3_settings,
    reusable_raw_analysis=None, include_raw=False,
):
    settings = normalise_crossover_timber_analysis_settings(analysis_settings)
    settings["minimum_clear_spacing"] = float(b3_settings["minimum_clear_spacing"])
    raw_analysis = None
    if isinstance(reusable_raw_analysis, dict) and reusable_raw_analysis.get("timbers"):
        try:
            expected = _timber_geometry_signature(crossover_config, settings, records)
            supplied = _timber_geometry_signature(
                crossover_config, settings, reusable_raw_analysis.get("timbers") or []
            )
            if expected == supplied:
                raw_analysis = dict(reusable_raw_analysis)
                for key in (
                    "analysis_basis", "production_note", "cache_reused",
                    "geometry_signature",
                ):
                    raw_analysis.pop(key, None)
        except Exception:
            raw_analysis = None
    if raw_analysis is None:
        raw_analysis = analyse_crossover_timber_records(crossover_config, records, settings)
    filtered = _b3_filter_interlaced_findings(
        raw_analysis, records, normalise_crossover_b3_settings(b3_settings)
    )
    return (filtered, raw_analysis) if include_raw else filtered


def _b3_replace_records(records, replacements):
    return [replacements.get(str(record.get("stable_identity") or ""), record) for record in records]


def _b3_trial_acceptable(crossover_config, current_records, replacements, target_pair, current_analysis, analysis_settings, settings):
    trial_records = _b3_replace_records(current_records, replacements)
    for record in replacements.values():
        preserved, reason = _b3_support_preserved(record, settings)
        if not preserved:
            return None, reason
    by_id = {str(record.get("stable_identity") or ""): record for record in trial_records}
    first = by_id.get(target_pair[0])
    second = by_id.get(target_pair[1])
    if first is None or second is None:
        return None, "one target timber is no longer present"
    geometry = _b3_pair_geometry(
        first, second, settings["minimum_clear_spacing"], settings["collision_tolerance"]
    )
    if not geometry["clear"]:
        return None, "target pair remains within the configured interlacing clearance"
    trial_analysis, raw_analysis = _b3_analysis_for_records(
        crossover_config, trial_records, analysis_settings, settings, include_raw=True
    )
    old_keys = _b3_production_conflict_keys(current_analysis)
    new_keys = _b3_production_conflict_keys(trial_analysis)
    introduced = new_keys - old_keys
    if introduced:
        return None, "trial introduces a new production conflict"
    old_counts = dict((current_analysis or {}).get("severity_counts") or {})
    new_counts = dict(trial_analysis.get("severity_counts") or {})
    if int(new_counts.get(CROSSOVER_TIMBER_SEVERITY_PRODUCTION_CRITICAL, 0)) > int(old_counts.get(CROSSOVER_TIMBER_SEVERITY_PRODUCTION_CRITICAL, 0)):
        return None, "trial increases production-critical findings"
    return {
        "records": trial_records,
        "analysis": trial_analysis,
        "raw_analysis": raw_analysis,
        "geometry": geometry,
    }, ""


def _b3_candidate_distances(limit, increment):
    limit = max(0.0, float(limit))
    increment = max(0.01, float(increment))
    count = int(math.floor(limit / increment + 1.0e-9))
    values = [increment * index for index in range(1, count + 1)]
    if limit > 1.0e-9 and (not values or limit - values[-1] > 1.0e-9):
        values.append(limit)
    return values


def _b3_target_pairs(base_records, analysis, shared_result, settings):
    settings = normalise_crossover_b3_settings(settings)
    by_id = {str(record.get("stable_identity") or ""): record for record in base_records or []}
    targets = {}

    def add_pair(first_id, second_id, source, reason, finding_codes=None):
        pair = tuple(sorted(filter(None, [str(first_id or ""), str(second_id or "")])))
        if len(pair) != 2 or pair[0] == pair[1]:
            return
        first = by_id.get(pair[0])
        second = by_id.get(pair[1])
        if first is None or second is None:
            return
        if not (_b3_is_movable(first) and _b3_is_movable(second)):
            return
        if str(first.get("turnout_side") or "") == str(second.get("turnout_side") or ""):
            return
        entry = targets.setdefault(pair, {
            "timber_identities": list(pair),
            "sources": [],
            "reasons": [],
            "finding_codes": set(),
        })
        if source not in entry["sources"]:
            entry["sources"].append(source)
        if reason and reason not in entry["reasons"]:
            entry["reasons"].append(reason)
        entry["finding_codes"].update(finding_codes or [])

    for finding in (analysis or {}).get("findings") or []:
        code = str(finding.get("code") or "")
        severity = str(finding.get("severity") or "")
        eligible = code in CROSSOVER_B3_TARGET_CODES and (
            severity in (CROSSOVER_TIMBER_SEVERITY_PRODUCTION_CONFLICT, CROSSOVER_TIMBER_SEVERITY_PRODUCTION_CRITICAL)
            or (settings["resolve_advisory_same_position"] and code == "effectively_same_longitudinal_station")
        )
        if eligible:
            add_pair(finding.get("timber_a"), finding.get("timber_b"), "A8A6B1 analysis", finding.get("message"), [code])

    shared = dict(shared_result or {})
    for rejection in shared.get("rejected_candidates") or []:
        identities = list(rejection.get("timber_identities") or [])
        if len(identities) >= 2:
            add_pair(identities[0], identities[1], "A8A6B2 inherited-pair rejection", rejection.get("reason"), rejection.get("finding_codes"))

    for rejection in shared.get("inherited_envelope_rejections") or []:
        first_id = str(rejection.get("timber_identity") or "")
        reason = str(rejection.get("reason") or "")
        matches = re.findall(r"timber\s+([^\s,;]+)", reason)
        second_id = next((value for value in matches if value in by_id and value != first_id), "")
        if not second_id and first_id in by_id:
            first = by_id[first_id]
            opposite = [
                record for record in base_records or []
                if _b3_is_movable(record)
                and str(record.get("turnout_side") or "") != str(first.get("turnout_side") or "")
            ]
            if opposite:
                second = min(opposite, key=lambda record: abs(float(record.get("longitudinal_station") or 0.0) - float(first.get("longitudinal_station") or 0.0)))
                second_id = str(second.get("stable_identity") or "")
        if second_id:
            add_pair(first_id, second_id, "A8A6B2 inherited-envelope rejection", reason, [])

    ordered = []
    for pair, entry in targets.items():
        entry["finding_codes"] = sorted(entry["finding_codes"])
        first, second = by_id[pair[0]], by_id[pair[1]]
        entry["longitudinal_difference_mm"] = abs(float(first.get("longitudinal_station") or 0.0) - float(second.get("longitudinal_station") or 0.0))
        ordered.append(entry)
    ordered.sort(key=lambda item: (item["longitudinal_difference_mm"], item["timber_identities"]))
    return ordered


def _b3_resolve_pair(crossover_config, current_records, target, current_analysis, current_raw_analysis, analysis_settings, settings):
    settings = normalise_crossover_b3_settings(settings)
    pair = tuple(target.get("timber_identities") or [])
    by_id = {str(record.get("stable_identity") or ""): record for record in current_records}
    if len(pair) != 2 or pair[0] not in by_id or pair[1] not in by_id:
        return None, "target pair is unavailable"
    first, second = by_id[pair[0]], by_id[pair[1]]
    angle_difference = math.degrees(_timber_normalised_angle_difference(
        float(first.get("angle_radians") or 0.0), float(second.get("angle_radians") or 0.0)
    ))
    if angle_difference > float(settings["maximum_angle_difference_degrees"]) + 1.0e-9:
        return None, "angular difference {:.3f}° exceeds the {:.3f}° controlled-movement limit".format(angle_difference, settings["maximum_angle_difference_degrees"])

    existing = _b3_pair_geometry(first, second, settings["minimum_clear_spacing"], settings["collision_tolerance"])
    if existing["clear"]:
        return {
            "records": current_records,
            "analysis": current_analysis,
            "raw_analysis": current_raw_analysis,
            "operation": {
                "kind": "interlaced-existing",
                "timber_identities": list(pair),
                "movements_mm": {pair[0]: 0.0, pair[1]: 0.0},
                "reason": "existing stagger already satisfies the configured interlacing clearance",
                "geometry": existing,
                "sources": list(target.get("sources") or []),
            },
        }, ""

    increment = float(settings["movement_increment"])
    limit_first = max(0.0, _b3_protected_limit(first, settings) - abs(float(first.get("b3_total_movement_mm") or 0.0)))
    limit_second = max(0.0, _b3_protected_limit(second, settings) - abs(float(second.get("b3_total_movement_mm") or 0.0)))
    max_pair = min(float(settings["maximum_interlacing_separation"]), limit_first + limit_second)
    _axis_a, _axis_b, _physical_axis, direction_relationship = _b3_aligned_longitudinal_axes(first, second)

    # Candidate distances are already ordered from the smallest movement upward.
    # Stop at the first distance which yields a valid symmetric interlace: any
    # larger candidate has a higher cost, and symmetric interlacing outranks a
    # single-timber shove at equal total movement.  This avoids repeatedly
    # reanalysing the complete crossover after a minimum solution is known.
    for separation in _b3_candidate_distances(max_pair, increment):
        half = 0.5 * separation
        move_first = min(limit_first, half)
        move_second = min(limit_second, separation - move_first)
        if move_first + move_second + 1.0e-9 < separation:
            continue
        accepted_at_distance = []
        for direction in (-1.0, 1.0):
            movements = (
                direction * move_first,
                -direction * direction_relationship * move_second,
            )
            replacements = {
                pair[0]: _b3_shift_record(first, movements[0], "interlaced-pair", pair[1]),
                pair[1]: _b3_shift_record(second, movements[1], "interlaced-pair", pair[0]),
            }
            accepted, _reason = _b3_trial_acceptable(
                crossover_config, current_records, replacements, pair, current_analysis, analysis_settings, settings
            )
            if accepted is not None:
                accepted_at_distance.append((movements, accepted))
        if accepted_at_distance:
            movements, accepted = min(accepted_at_distance, key=lambda item: (abs(item[0][0] - item[0][1]), item[0]))
            operation = {
                "kind": "interlaced-pair",
                "timber_identities": list(pair),
                "movements_mm": {pair[0]: float(movements[0]), pair[1]: float(movements[1])},
                "total_movement_mm": float(abs(movements[0]) + abs(movements[1])),
                "reason": "smallest accepted B3 movement",
                "geometry": accepted["geometry"],
                "sources": list(target.get("sources") or []),
            }
            return {
                "records": accepted["records"],
                "analysis": accepted["analysis"],
                "raw_analysis": accepted.get("raw_analysis"),
                "operation": operation,
            }, ""

    movable_order = sorted(
        ((first, pair[0]), (second, pair[1])),
        key=lambda item: (-_b3_protected_limit(item[0], settings), len(item[0].get("protected_features") or []), item[1]),
    )
    available_by_id = {
        identity: max(0.0, _b3_protected_limit(record, settings) - abs(float(record.get("b3_total_movement_mm") or 0.0)))
        for record, identity in movable_order
    }
    maximum_single = max(available_by_id.values() or [0.0])
    for distance in _b3_candidate_distances(maximum_single, increment):
        accepted_at_distance = []
        for record, identity in movable_order:
            if distance > available_by_id[identity] + 1.0e-9:
                continue
            other_identity = pair[1] if identity == pair[0] else pair[0]
            for direction in (-1.0, 1.0):
                movement = direction * distance
                replacements = {identity: _b3_shift_record(record, movement, "controlled-shove", other_identity)}
                accepted, _reason = _b3_trial_acceptable(
                    crossover_config, current_records, replacements, pair, current_analysis, analysis_settings, settings
                )
                if accepted is not None:
                    movements = (movement, 0.0) if identity == pair[0] else (0.0, movement)
                    accepted_at_distance.append((movements, accepted))
        if accepted_at_distance:
            movements, accepted = min(accepted_at_distance, key=lambda item: (abs(item[0][0] - item[0][1]), item[0]))
            operation = {
                "kind": "controlled-shove",
                "timber_identities": list(pair),
                "movements_mm": {pair[0]: float(movements[0]), pair[1]: float(movements[1])},
                "total_movement_mm": float(abs(movements[0]) + abs(movements[1])),
                "reason": "smallest accepted B3 movement",
                "geometry": accepted["geometry"],
                "sources": list(target.get("sources") or []),
            }
            return {
                "records": accepted["records"],
                "analysis": accepted["analysis"],
                "raw_analysis": accepted.get("raw_analysis"),
                "operation": operation,
            }, ""

    return None, "no permitted longitudinal movement resolves the pair without creating a new conflict or losing protected support"

def resolve_crossover_b3_timbering(
    crossover_config, base_records, shared_result, analysis_settings=None,
    settings=None, initial_raw_analysis=None,
):
    config = dict(crossover_config or {})
    settings = normalise_crossover_b3_settings(settings)
    if not isinstance(shared_result, dict) or not shared_result.get("applied"):
        raise ValueError("Build the complete shared long-timber envelope before applying controlled interlacing and timber movement.")
    records = _b3_deepcopy(list(base_records or []))
    if not records:
        raise ValueError("The current shared long-timber arrangement contains no timber records.")
    analysis_settings = normalise_crossover_timber_analysis_settings(analysis_settings)
    current_analysis, current_raw_analysis = _b3_analysis_for_records(
        config, records, analysis_settings, settings,
        reusable_raw_analysis=initial_raw_analysis, include_raw=True,
    )
    original_analysis = _b3_deepcopy(current_analysis)
    targets = _b3_target_pairs(records, current_analysis, shared_result, settings)
    operations = []
    unresolved = []
    for target in targets:
        resolved, reason = _b3_resolve_pair(
            config, records, target, current_analysis, current_raw_analysis,
            analysis_settings, settings
        )
        if resolved is None:
            unresolved.append({
                "timber_identities": list(target.get("timber_identities") or []),
                "source": ", ".join(target.get("sources") or []),
                "reason": reason,
                "original_reasons": list(target.get("reasons") or []),
            })
            continue
        records = resolved["records"]
        current_analysis = resolved["analysis"]
        current_raw_analysis = resolved.get("raw_analysis") or current_raw_analysis
        operations.append(resolved["operation"])

    for rejection in shared_result.get("envelope_rejected_stations") or []:
        unresolved.append({
            "timber_identities": [],
            "source": "A8A6B2 connector-envelope rejection",
            "reason": str(rejection.get("reason") or "connector position has no movable inherited A/B timber pair"),
            "connector_position_mm": float(rejection.get("station") or 0.0),
        })

    # Every accepted movement already returned a complete analysis for the new
    # record set. No geometry changes after the loop, so a duplicate full pass
    # would add cost without adding validation.
    final_analysis = current_analysis
    final_raw_analysis = current_raw_analysis
    final_counts = dict(final_analysis.get("severity_counts") or {})
    production_conflicts = int(final_counts.get(CROSSOVER_TIMBER_SEVERITY_PRODUCTION_CONFLICT, 0))
    critical_conflicts = int(final_counts.get(CROSSOVER_TIMBER_SEVERITY_PRODUCTION_CRITICAL, 0))
    if production_conflicts or critical_conflicts:
        status = CROSSOVER_B3_STATUS_CONFLICTS
    elif unresolved:
        status = CROSSOVER_B3_STATUS_PARTIAL
    else:
        status = CROSSOVER_B3_STATUS_CLEAR
    moved_ids = sorted({
        identity
        for operation in operations
        for identity, movement in dict(operation.get("movements_mm") or {}).items()
        if abs(float(movement)) > 1.0e-9
    })
    interlaced_pairs = sum(1 for operation in operations if str(operation.get("kind") or "").startswith("interlaced"))
    zero_movement_pairs = sum(1 for operation in operations if operation.get("kind") == "interlaced-existing")
    base_signature = _b3_base_signature(config, base_records)
    resolution_signature = _b3_resolution_signature(
        config, settings, base_signature, records, operations, unresolved
    )
    return {
        "schema_version": CROSSOVER_B3_SCHEMA_VERSION,
        "macro_version": MACRO_VERSION_NUMBER,
        "crossover_id": str(config.get("crossover_id") or ""),
        "applied": True,
        "status": status,
        "settings": settings,
        "base_signature": base_signature,
        "resolution_signature": resolution_signature,
        "target_pair_count": len(targets),
        "resolved_pair_count": len(operations),
        "interlaced_pair_count": interlaced_pairs,
        "existing_interlaced_pair_count": zero_movement_pairs,
        "shoved_timber_count": len(moved_ids),
        "shoved_timber_identities": moved_ids,
        "operations": operations,
        "unresolved": unresolved,
        "unresolved_count": len(unresolved),
        "resolved_timbers": records,
        "effective_timber_count": len(records),
        "original_analysis": original_analysis,
        "resolved_analysis": final_analysis,
        "resolved_unfiltered_analysis": final_raw_analysis,
        "remaining_production_conflicts": production_conflicts,
        "remaining_production_critical_conflicts": critical_conflicts,
        "maximum_absolute_movement_mm": max([abs(float(record.get("b3_total_movement_mm") or 0.0)) for record in records] or [0.0]),
        "total_absolute_movement_mm": sum(abs(float(record.get("b3_total_movement_mm") or 0.0)) for record in records),
        "source_basis": list(CROSSOVER_B3_SOURCE_BASIS),
        "engineering_assumptions": list(CROSSOVER_B3_ENGINEERING_ASSUMPTIONS),
        "host_integration_allowed": False,
        "host_integration_reason": "Eligible inherited timber positions have been adjusted, but automatic final resolution and exact host sleeper integration remain incomplete",
        "production_ready": False,
    }


def crossover_b3_summary(result, include_unresolved=True):
    data = dict(result or {})
    lines = [
        "Version {} — Controlled interlacing and timber movement".format(CROSSOVER_OPERATOR_VERSION_NUMBER),
        "Crossover: {}".format(data.get("crossover_id") or "Unknown"),
        "Status: {}".format(data.get("status") or CROSSOVER_B3_STATUS_NOT_APPLIED),
        "Target A/B timber pairs: {}".format(data.get("target_pair_count", 0)),
        "Resolved pairs: {}".format(data.get("resolved_pair_count", 0)),
        "Interlaced pairs: {}".format(data.get("interlaced_pair_count", 0)),
        "Existing stagger accepted without movement: {}".format(data.get("existing_interlaced_pair_count", 0)),
        "Timbers moved longitudinally: {}".format(data.get("shoved_timber_count", 0)),
        "Maximum absolute timber movement: {:.3f} mm".format(float(data.get("maximum_absolute_movement_mm") or 0.0)),
        "Total absolute timber movement: {:.3f} mm".format(float(data.get("total_absolute_movement_mm") or 0.0)),
        "Unresolved positions: {}".format(data.get("unresolved_count", 0)),
        "Remaining production conflicts: {}".format(data.get("remaining_production_conflicts", 0)),
        "Remaining production-critical conflicts: {}".format(data.get("remaining_production_critical_conflicts", 0)),
        "Production ready: No",
        "Host integration allowed: No",
    ]
    if data.get("operations"):
        lines.extend(["", "Accepted operations:"])
        for operation in data.get("operations") or []:
            moves = ", ".join(
                "{} {:+.3f} mm".format(identity, float(movement))
                for identity, movement in sorted(dict(operation.get("movements_mm") or {}).items())
            )
            lines.append("- {}: {} ({})".format(
                operation.get("kind") or "operation",
                " / ".join(operation.get("timber_identities") or []),
                moves or "no movement",
            ))
    if include_unresolved and data.get("unresolved"):
        lines.extend(["", "Unresolved positions retained for automatic resolution:"])
        for item in data.get("unresolved") or []:
            identities = " / ".join(item.get("timber_identities") or []) or "connector position"
            lines.append("- {}: {}".format(identities, item.get("reason") or "unresolved"))
    return "\n".join(lines)


def _crossover_b3_object(doc, crossover_id):
    for obj in _crossover_objects(doc, crossover_id):
        if object_string_property(obj, "GeneratedRole", "") == CROSSOVER_B3_ROLE:
            return obj
    return None


def _write_crossover_b3_metadata(doc, config, result):
    updated = dict(config or {})
    updated["b3_schema_version"] = CROSSOVER_B3_SCHEMA_VERSION
    updated["b3_status"] = str(result.get("status") or CROSSOVER_B3_STATUS_NOT_APPLIED)
    updated["b3_signature"] = str(result.get("resolution_signature") or "")
    updated["b3_settings"] = normalise_crossover_b3_settings(result.get("settings"))
    updated["b3_summary"] = {
        "target_pair_count": int(result.get("target_pair_count") or 0),
        "resolved_pair_count": int(result.get("resolved_pair_count") or 0),
        "interlaced_pair_count": int(result.get("interlaced_pair_count") or 0),
        "existing_interlaced_pair_count": int(result.get("existing_interlaced_pair_count") or 0),
        "shoved_timber_count": int(result.get("shoved_timber_count") or 0),
        "unresolved_count": int(result.get("unresolved_count") or 0),
        "remaining_production_conflicts": int(result.get("remaining_production_conflicts") or 0),
        "remaining_production_critical_conflicts": int(result.get("remaining_production_critical_conflicts") or 0),
        "maximum_absolute_movement_mm": float(result.get("maximum_absolute_movement_mm") or 0.0),
    }
    updated["b3_result"] = dict(result)
    updated["b4_status"] = CROSSOVER_B4_STATUS_NOT_APPLIED
    updated["b4_signature"] = ""
    updated["b4_summary"] = {}
    updated["b4_result"] = {}
    updated["timbering_status"] = updated["b3_status"]
    updated["timber_analysis_status"] = CROSSOVER_TIMBER_ANALYSIS_STATUS_STALE
    updated["timber_analysis_signature"] = ""
    updated["timber_analysis_summary"] = {}
    updated["timber_analysis_result_cached"] = False
    updated["production_ready"] = False
    updated["host_integration_allowed"] = False
    if not updated.get("integration_active"):
        updated["integration_status"] = CROSSOVER_INTEGRATION_STATUS_NOT_INTEGRATED
    updated["host_integration_reason"] = str(result.get("host_integration_reason") or "Automatic final resolution and host integration remain required")
    settings_object = None
    for obj in _crossover_objects(doc, updated.get("crossover_id")):
        if object_string_property(obj, "GeneratedRole", "") == CROSSOVER_SETTINGS_ROLE:
            settings_object = obj
        _crossover_add_identity_properties(obj, updated.get("crossover_id"), updated)
    if settings_object is None:
        raise ValueError("The crossover settings object is missing.")
    properties = [
        ensure_property(settings_object, "App::PropertyString", CROSSOVER_B3_SETTINGS_PROPERTY, "Crossover timber adjustment", "Validated interlacing and timber-movement settings"),
        ensure_property(settings_object, "App::PropertyString", CROSSOVER_B3_RESULT_PROPERTY, "Crossover timber adjustment", "Controlled interlacing and timber-movement result"),
    ]
    setattr(settings_object, CROSSOVER_B3_SETTINGS_PROPERTY, json.dumps(updated["b3_settings"], sort_keys=True))
    setattr(settings_object, CROSSOVER_B3_RESULT_PROPERTY, json.dumps(result, sort_keys=True))
    if CROSSOVER_B4_RESULT_PROPERTY in getattr(settings_object, "PropertiesList", []):
        setattr(settings_object, CROSSOVER_B4_RESULT_PROPERTY, "")
    set_read_only(settings_object, properties)
    _crossover_store_catalogue(doc, str(updated.get("template_set_id") or ""))
    return updated


def apply_crossover_b3_timbering(doc, crossover_id, settings=None):
    clear_chair_analysis_display(doc, "crossover", str(crossover_id or "").strip())
    existing_config = crossover_config_by_id(doc, str(crossover_id or "").strip())
    if existing_config is not None and bool(existing_config.get("integration_active", False)):
        raise ValueError("Remove the crossover host integration before changing the resolved timber arrangement.")
    identifier = str(crossover_id or "").strip()
    config = crossover_config_by_id(doc, identifier)
    if config is None:
        raise ValueError("Crossover {} was not found.".format(identifier or "selection"))
    shared_result = config.get("shared_timber_result")
    if crossover_shared_timber_effective_status(doc, config) == CROSSOVER_SHARED_TIMBER_STATUS_STALE:
        raise ValueError("The shared long-timber envelope is stale. Rebuild it before applying controlled timber adjustment.")
    if not isinstance(shared_result, dict) or not shared_result.get("applied"):
        raise ValueError("Build the complete shared long-timber envelope before applying controlled timber adjustment.")
    base_records = _crossover_b2_effective_timber_records(doc, config)
    analysis_settings = normalise_crossover_timber_analysis_settings(config.get("timber_analysis_settings"))
    result = resolve_crossover_b3_timbering(config, base_records, shared_result, analysis_settings, settings)
    # This verified raw analysis is an internal hand-off used by the automatic B4
    # workflow.  Standalone B3 must not persist a duplicate analysis tree.
    result.pop("resolved_unfiltered_analysis", None)
    shape = _shared_timber_shape_from_records(
        result.get("resolved_timbers") or [],
        float(config.get("template_thickness") or TEMPLATE_THICKNESS) + 0.030,
    )
    if shape is None:
        raise ValueError("FreeCAD could not build the adjusted timbering display.")
    group = _crossover_group_object(doc, identifier)
    if group is None:
        raise ValueError("The crossover group is missing.")
    transaction_open = False
    resolved_analysis = None
    try:
        doc.openTransaction("Apply Version {} controlled timber adjustment {}".format(MACRO_VERSION_NUMBER, identifier))
        transaction_open = True
        previous_b4 = _crossover_b4_object(doc, identifier)
        if previous_b4 is not None:
            doc.removeObject(str(previous_b4.Name))
        previous = _crossover_b3_object(doc, identifier)
        if previous is not None:
            doc.removeObject(str(previous.Name))
        obj = doc.addObject("Part::Feature", unique_internal_name(doc, "CrossoverB3Timbering_{}".format(identifier.replace("-", "_"))))
        obj.Label = "{} Interlaced and Adjusted Timbering".format(identifier)
        obj.Shape = shape
        tag_generated_object(obj, CROSSOVER_B3_ROLE, config.get("template_set_id"))
        properties = [
            ensure_property(obj, "App::PropertyString", CROSSOVER_ID_PROPERTY, "Crossover identity", "Stable crossover identifier"),
            ensure_property(obj, "App::PropertyString", "GeneratedSubtype", "Generated metadata", "Generated object subtype"),
            ensure_property(obj, "App::PropertyString", "B3TimberRecordsJSON", "Crossover timber adjustment", "Complete effective adjusted timber records"),
            ensure_property(obj, "App::PropertyString", "B3OperationsJSON", "Crossover timber adjustment", "Accepted interlacing and timber-movement operations"),
        ]
        setattr(obj, CROSSOVER_ID_PROPERTY, identifier)
        obj.GeneratedSubtype = CROSSOVER_B3_SUBTYPE
        obj.B3TimberRecordsJSON = json.dumps(result.get("resolved_timbers") or [], sort_keys=True)
        obj.B3OperationsJSON = json.dumps(result.get("operations") or [], sort_keys=True)
        set_read_only(obj, properties)
        group.addObject(obj)
        try:
            obj.ViewObject.LineColor = (0.45, 0.20, 0.75)
            obj.ViewObject.LineWidth = 2.8
            obj.ViewObject.Visibility = bool(result.get("settings", {}).get("show_b3_geometry", True))
        except Exception:
            pass
        shared_obj = _crossover_shared_timber_object(doc, identifier)
        if shared_obj is not None:
            try:
                shared_obj.ViewObject.Visibility = False
            except Exception:
                pass
        updated = _write_crossover_b3_metadata(doc, config, result)
        _remove_crossover_timber_analysis_objects(doc, identifier)
        effective_records = list(result.get("resolved_timbers") or [])
        resolved_analysis = dict(result.get("resolved_analysis") or _b3_analysis_for_records(updated, effective_records, analysis_settings, result.get("settings")))
        resolved_analysis["settings"] = normalise_crossover_timber_analysis_settings(resolved_analysis.get("settings") or analysis_settings)
        resolved_analysis["geometry_signature"] = _timber_geometry_signature(updated, resolved_analysis["settings"], effective_records)
        resolved_analysis["cache_reused"] = False
        resolved_analysis["analysis_basis"] = "Effective interlaced and longitudinally adjusted timber arrangement"
        resolved_analysis["production_note"] = "No (automatic resolution and host integration remain outstanding)"
        resolved_analysis["host_integration_reason"] = updated.get("host_integration_reason")
        updated = _write_crossover_timber_analysis_metadata(doc, updated, resolved_analysis)
        _create_crossover_timber_analysis_display(doc, updated, resolved_analysis)
        _document_recompute(doc)
        doc.commitTransaction()
        transaction_open = False
    except Exception:
        if transaction_open:
            try:
                doc.abortTransaction()
            except Exception:
                pass
        raise
    result["resolved_analysis"] = resolved_analysis
    return result


def clear_crossover_b3_timbering(doc, crossover_id):
    clear_chair_analysis_display(doc, "crossover", str(crossover_id or "").strip())
    existing_config = crossover_config_by_id(doc, str(crossover_id or "").strip())
    if existing_config is not None and bool(existing_config.get("integration_active", False)):
        raise ValueError("Remove the crossover host integration before changing the resolved timber arrangement.")
    identifier = str(crossover_id or "").strip()
    config = crossover_config_by_id(doc, identifier)
    if config is None:
        raise ValueError("Crossover {} was not found.".format(identifier or "selection"))
    transaction_open = False
    try:
        doc.openTransaction("Remove Version {} controlled timber adjustment {}".format(MACRO_VERSION_NUMBER, identifier))
        transaction_open = True
        b4_obj = _crossover_b4_object(doc, identifier)
        if b4_obj is not None:
            doc.removeObject(str(b4_obj.Name))
        obj = _crossover_b3_object(doc, identifier)
        if obj is not None:
            doc.removeObject(str(obj.Name))
        updated = dict(config)
        updated["b3_status"] = CROSSOVER_B3_STATUS_NOT_APPLIED
        updated["b3_signature"] = ""
        updated["b3_summary"] = {}
        updated["b3_result"] = {}
        updated["b4_status"] = CROSSOVER_B4_STATUS_NOT_APPLIED
        updated["b4_signature"] = ""
        updated["b4_summary"] = {}
        updated["b4_result"] = {}
        updated["timbering_status"] = str(updated.get("shared_timber_status") or CROSSOVER_SHARED_TIMBER_STATUS_NOT_APPLIED)
        updated["production_ready"] = False
        updated["host_integration_allowed"] = False
        if not updated.get("integration_active"):
            updated["integration_status"] = CROSSOVER_INTEGRATION_STATUS_NOT_INTEGRATED
        updated["host_integration_reason"] = "Controlled timber adjustment is not applied; automatic final resolution and host integration remain required"
        for current in _crossover_objects(doc, identifier):
            _crossover_add_identity_properties(current, identifier, updated)
            if object_string_property(current, "GeneratedRole", "") == CROSSOVER_SETTINGS_ROLE:
                if CROSSOVER_B3_RESULT_PROPERTY in getattr(current, "PropertiesList", []):
                    setattr(current, CROSSOVER_B3_RESULT_PROPERTY, "")
                if CROSSOVER_B4_RESULT_PROPERTY in getattr(current, "PropertiesList", []):
                    setattr(current, CROSSOVER_B4_RESULT_PROPERTY, "")
        shared_obj = _crossover_shared_timber_object(doc, identifier)
        if shared_obj is not None:
            try:
                shared_obj.ViewObject.Visibility = bool((updated.get("shared_timber_settings") or {}).get("show_shared_timber_geometry", True))
            except Exception:
                pass
        _remove_crossover_timber_analysis_objects(doc, identifier)
        base_records = _crossover_b2_effective_timber_records(doc, updated)
        analysis_settings = normalise_crossover_timber_analysis_settings(updated.get("timber_analysis_settings"))
        analysis = analyse_crossover_timber_records(updated, base_records, analysis_settings)
        analysis["settings"] = analysis_settings
        analysis["geometry_signature"] = _timber_geometry_signature(updated, analysis_settings, base_records)
        analysis["cache_reused"] = False
        analysis["analysis_basis"] = "Effective shared long-timber arrangement"
        analysis["production_note"] = "No (automatic resolution and host integration remain outstanding)"
        analysis["host_integration_reason"] = updated.get("host_integration_reason")
        updated = _write_crossover_timber_analysis_metadata(doc, updated, analysis)
        _create_crossover_timber_analysis_display(doc, updated, analysis)
        _crossover_store_catalogue(doc, str(updated.get("template_set_id") or ""))
        _document_recompute(doc)
        doc.commitTransaction()
        transaction_open = False
    except Exception:
        if transaction_open:
            try:
                doc.abortTransaction()
            except Exception:
                pass
        raise
    return identifier


def set_crossover_b3_visibility(doc, crossover_id, visible):
    obj = _crossover_b3_object(doc, crossover_id)
    if obj is None:
        return False
    try:
        obj.ViewObject.Visibility = bool(visible)
        return True
    except Exception:
        return False


def crossover_b3_effective_status(doc, crossover_config):
    config = dict(crossover_config or {})
    result = config.get("b3_result")
    if not isinstance(result, dict) or not result.get("applied"):
        return CROSSOVER_B3_STATUS_NOT_APPLIED
    try:
        base_records = _crossover_b2_effective_timber_records(doc, config)
        base_signature = _b3_base_signature(config, base_records)
        expected = _b3_resolution_signature(
            config,
            result.get("settings"),
            base_signature,
            result.get("resolved_timbers") or [],
            result.get("operations") or [],
            result.get("unresolved") or [],
        )
    except Exception:
        return CROSSOVER_B3_STATUS_STALE
    if (
        str(result.get("base_signature") or "") != base_signature
        or str(result.get("resolution_signature") or "") != expected
        or str(config.get("b3_signature") or "") != expected
    ):
        return CROSSOVER_B3_STATUS_STALE
    return str(config.get("b3_status") or result.get("status") or CROSSOVER_B3_STATUS_NOT_APPLIED)


# Stage A8A6B4 hybrid automatic timber resolver.


def default_crossover_b4_settings():
    return {
        "schema_version": CROSSOVER_B4_SCHEMA_VERSION,
        "show_b4_geometry": True,
    }


def normalise_crossover_b4_settings(source=None):
    result = default_crossover_b4_settings()
    if isinstance(source, dict):
        result.update(source)
    result["show_b4_geometry"] = bool(result.get("show_b4_geometry", True))
    result["schema_version"] = CROSSOVER_B4_SCHEMA_VERSION
    return result


def _b4_stable_record(record):
    return _b3_stable_record(record)


def _b4_resolution_signature(crossover_config, settings, inherited_signature, shared_result, b3_result, records, unresolved):
    payload = {
        "schema_version": CROSSOVER_B4_SCHEMA_VERSION,
        "crossover_id": str((crossover_config or {}).get("crossover_id") or ""),
        "settings": normalise_crossover_b4_settings(settings),
        "inherited_signature": str(inherited_signature),
        "shared_resolution_signature": str((shared_result or {}).get("resolution_signature") or ""),
        "b3_resolution_signature": str((b3_result or {}).get("resolution_signature") or ""),
        "records": [_b4_stable_record(record) for record in sorted(records or [], key=lambda item: str(item.get("stable_identity") or ""))],
        "unresolved": [
            {
                "timbers": sorted(str(value) for value in item.get("timber_identities") or []),
                "source": str(item.get("source") or ""),
                "reason": str(item.get("reason") or ""),
                "position": round(float(item.get("connector_position_mm") or item.get("station") or 0.0), 6),
            }
            for item in unresolved or []
        ],
    }
    return hashlib.sha256(json.dumps(payload, sort_keys=True, separators=(",", ":")).encode("utf-8")).hexdigest()


def resolve_crossover_b4_timbering(
    crossover_config,
    inherited_records,
    analysis_settings=None,
    shared_settings=None,
    b3_settings=None,
    b4_settings=None,
    envelope_context=None,
):
    overall_start = time.perf_counter()
    timings = {}
    config = dict(crossover_config or {})
    inherited = _b3_deepcopy(list(inherited_records or []))
    if not inherited:
        raise ValueError("The crossover contains no inherited timber records.")
    analysis_settings = normalise_crossover_timber_analysis_settings(analysis_settings or config.get("timber_analysis_settings"))
    shared_settings = normalise_crossover_shared_timber_settings(shared_settings or config.get("shared_timber_settings"))
    b3_settings = normalise_crossover_b3_settings(b3_settings or config.get("b3_settings"))
    b4_settings = normalise_crossover_b4_settings(b4_settings or config.get("b4_settings"))

    stage_start = time.perf_counter()
    inherited_analysis = analyse_crossover_timber_records(config, inherited, analysis_settings)
    timings["inherited_analysis"] = (time.perf_counter() - stage_start) * 1000.0

    stage_start = time.perf_counter()
    shared_result = propose_crossover_shared_long_timbers(
        config,
        inherited,
        inherited_analysis,
        shared_settings,
        envelope_context,
    )
    shared_records = apply_shared_timber_result_to_records(inherited, shared_result)
    timings["shared_long_timber_envelope"] = (time.perf_counter() - stage_start) * 1000.0

    b3_config = dict(config)
    b3_config["shared_timber_signature"] = str(shared_result.get("resolution_signature") or "")
    b3_config["shared_timber_result"] = dict(shared_result)
    shared_for_b3 = dict(shared_result)
    shared_for_b3["applied"] = True

    stage_start = time.perf_counter()
    b3_result = resolve_crossover_b3_timbering(
        b3_config,
        shared_records,
        shared_for_b3,
        analysis_settings,
        b3_settings,
        initial_raw_analysis=shared_result.get("resolved_analysis"),
    )
    timings["interlacing_and_controlled_movement"] = (time.perf_counter() - stage_start) * 1000.0

    records = _b3_deepcopy(list(b3_result.get("resolved_timbers") or shared_records))
    final_analysis = dict(
        b3_result.pop("resolved_unfiltered_analysis", None)
        or analyse_crossover_timber_records(config, records, analysis_settings)
    )
    final_counts = dict(final_analysis.get("severity_counts") or {})
    production_conflicts = int(final_counts.get(CROSSOVER_TIMBER_SEVERITY_PRODUCTION_CONFLICT, 0))
    critical_conflicts = int(final_counts.get(CROSSOVER_TIMBER_SEVERITY_PRODUCTION_CRITICAL, 0))
    unresolved = _b3_deepcopy(list(b3_result.get("unresolved") or []))
    if critical_conflicts or production_conflicts:
        status = CROSSOVER_B4_STATUS_CONFLICTS
    elif unresolved:
        status = CROSSOVER_B4_STATUS_PARTIAL
    else:
        status = CROSSOVER_B4_STATUS_CLEAR

    original_counts = dict(inherited_analysis.get("severity_counts") or {})
    original_critical = int(original_counts.get(CROSSOVER_TIMBER_SEVERITY_PRODUCTION_CRITICAL, 0))
    if critical_conflicts > original_critical:
        raise ValueError("The automatic timber resolver introduced an additional production-critical finding and was rejected.")

    inherited_signature = _shared_timber_inherited_signature(config, inherited)
    resolution_signature = _b4_resolution_signature(
        config, b4_settings, inherited_signature, shared_result, b3_result, records, unresolved
    )
    timings["total_solver"] = (time.perf_counter() - overall_start) * 1000.0
    return {
        "schema_version": CROSSOVER_B4_SCHEMA_VERSION,
        "macro_version": MACRO_VERSION_NUMBER,
        "crossover_id": str(config.get("crossover_id") or ""),
        "applied": True,
        "status": status,
        "settings": b4_settings,
        "analysis_settings": analysis_settings,
        "shared_settings": shared_settings,
        "b3_settings": b3_settings,
        "inherited_signature": inherited_signature,
        "resolution_signature": resolution_signature,
        "shared_result": shared_result,
        "b3_result": b3_result,
        "resolved_timbers": records,
        "effective_timber_count": len(records),
        "shared_timber_count": int(shared_result.get("shared_timber_count") or 0),
        "plain_connector_timber_count": int(shared_result.get("plain_connector_timber_count") or 0),
        "interlaced_pair_count": int(b3_result.get("interlaced_pair_count") or 0),
        "existing_interlaced_pair_count": int(b3_result.get("existing_interlaced_pair_count") or 0),
        "shoved_timber_count": int(b3_result.get("shoved_timber_count") or 0),
        "maximum_absolute_movement_mm": float(b3_result.get("maximum_absolute_movement_mm") or 0.0),
        "unresolved": unresolved,
        "unresolved_count": len(unresolved),
        "remaining_production_conflicts": production_conflicts,
        "remaining_production_critical_conflicts": critical_conflicts,
        "timber_resolution_complete": not unresolved and production_conflicts == 0 and critical_conflicts == 0,
        "inherited_analysis": inherited_analysis,
        "resolved_analysis": final_analysis,
        "performance_timings_ms": timings,
        "source_basis": list(CROSSOVER_B4_SOURCE_BASIS),
        "engineering_assumptions": list(CROSSOVER_B4_ENGINEERING_ASSUMPTIONS),
        "production_ready": False,
        "host_integration_allowed": False,
        "host_integration_reason": "The preview timber arrangement is resolved; exact host integration and chair validation remain required",
    }


def _crossover_b4_result_is_current(crossover_config, inherited_records, result):
    config = dict(crossover_config or {})
    if not isinstance(result, dict) or not result.get("applied"):
        return False
    inherited_signature = _shared_timber_inherited_signature(config, inherited_records)
    if str(result.get("inherited_signature") or "") != inherited_signature:
        return False
    shared_result = result.get("shared_result") or {}
    expected_shared = _shared_timber_resolution_signature(
        config,
        shared_result.get("settings"),
        inherited_signature,
        shared_result.get("shared_timbers") or [],
        shared_result.get("consumed_timber_identities") or [],
        shared_result.get("plain_connector_timbers") or [],
        shared_result.get("envelope_summary") or {},
    )
    if str(shared_result.get("resolution_signature") or "") != expected_shared:
        return False
    shared_records = apply_shared_timber_result_to_records(inherited_records, shared_result)
    b3_result = result.get("b3_result") or {}
    b3_config = dict(config)
    b3_config["shared_timber_signature"] = expected_shared
    expected_base = _b3_base_signature(b3_config, shared_records)
    expected_b3 = _b3_resolution_signature(
        b3_config,
        b3_result.get("settings"),
        expected_base,
        b3_result.get("resolved_timbers") or [],
        b3_result.get("operations") or [],
        b3_result.get("unresolved") or [],
    )
    if str(b3_result.get("base_signature") or "") != expected_base or str(b3_result.get("resolution_signature") or "") != expected_b3:
        return False
    expected_b4 = _b4_resolution_signature(
        config,
        result.get("settings"),
        inherited_signature,
        shared_result,
        b3_result,
        result.get("resolved_timbers") or [],
        result.get("unresolved") or [],
    )
    return str(result.get("resolution_signature") or "") == expected_b4 and str(config.get("b4_signature") or expected_b4) == expected_b4


def crossover_b4_summary(result, include_unresolved=True):
    data = dict(result or {})
    lines = [
        "Version {} — Automatic crossover timber resolution".format(CROSSOVER_OPERATOR_VERSION_NUMBER),
        "Crossover: {}".format(data.get("crossover_id") or "Unknown"),
        "Status: {}".format(data.get("status") or CROSSOVER_B4_STATUS_NOT_APPLIED),
        "Effective timbers: {}".format(data.get("effective_timber_count", 0)),
        "Shared long timbers: {}".format(data.get("shared_timber_count", 0)),
        "Nominal connector sleepers: {}".format(data.get("plain_connector_timber_count", 0)),
        "Interlaced pairs: {}".format(data.get("interlaced_pair_count", 0)),
        "Existing stagger accepted without movement: {}".format(data.get("existing_interlaced_pair_count", 0)),
        "Timbers moved longitudinally: {}".format(data.get("shoved_timber_count", 0)),
        "Maximum absolute timber movement: {:.3f} mm".format(float(data.get("maximum_absolute_movement_mm") or 0.0)),
        "Unresolved positions: {}".format(data.get("unresolved_count", 0)),
        "Remaining production conflicts: {}".format(data.get("remaining_production_conflicts", 0)),
        "Remaining production-critical conflicts: {}".format(data.get("remaining_production_critical_conflicts", 0)),
        "Timber resolution complete: {}".format("Yes" if data.get("timber_resolution_complete") else "No"),
        "Measured timber-solver time: {:.1f} ms".format(
            float((data.get("performance_timings_ms") or {}).get("total_solver") or 0.0)
        ),
        "Complete timbering pipeline time: {:.1f} ms".format(
            float((data.get("performance_timings_ms") or {}).get("pipeline_total") or 0.0)
        ),
        "Unchanged result reused: {}".format("Yes" if data.get("cache_reused") else "No"),
        "Production ready: No (chair validation remains outstanding)",
        "Host integration allowed: {}".format("Yes" if data.get("timber_resolution_complete") and not data.get("remaining_production_conflicts") and not data.get("remaining_production_critical_conflicts") else "No"),
    ]
    timings = dict(data.get("performance_timings_ms") or {})
    shared_timings = dict((data.get("shared_result") or {}).get("performance_timings_ms") or {})
    lines.extend([
        "",
        "Live performance profile:",
        "- Data and settings preparation: {:.1f} ms".format(float(timings.get("record_extraction_and_settings") or 0.0) + float(timings.get("envelope_context_preparation") or 0.0)),
        "- Inherited timber conflict analysis: {:.1f} ms".format(float(timings.get("inherited_analysis") or 0.0)),
        "- Shared long-timber solving: {:.1f} ms".format(float(timings.get("shared_long_timber_envelope") or shared_timings.get("total") or 0.0)),
        "- Interlacing and controlled movement: {:.1f} ms".format(float(timings.get("interlacing_and_controlled_movement") or 0.0)),
        "- FreeCAD Part shape construction: {:.1f} ms".format(float(timings.get("freecad_shape_construction") or 0.0)),
        "- Metadata updates: {:.1f} ms".format(float(timings.get("metadata_updates") or 0.0)),
        "  - Final state assembly: {:.1f} ms".format(float(timings.get("metadata_state_assembly") or 0.0)),
        "  - Persistent payload serialisation: {:.1f} ms".format(float(timings.get("metadata_payload_serialisation") or 0.0)),
        "  - Identity and status propagation: {:.1f} ms".format(float(timings.get("metadata_identity_propagation") or 0.0)),
        "  - Settings payload update: {:.1f} ms".format(float(timings.get("metadata_settings_payload_update") or 0.0)),
        "  - Catalogue update: {:.1f} ms".format(float(timings.get("metadata_catalogue_update") or 0.0)),
        "- Metadata property writes performed: {}".format(int((data.get("metadata_update_statistics") or {}).get("property_writes_performed") or 0)),
        "- Unchanged metadata writes skipped: {}".format(int((data.get("metadata_update_statistics") or {}).get("unchanged_property_writes_skipped") or 0)),
        "- Diagnostic display construction: {:.1f} ms".format(float(timings.get("diagnostic_display_construction") or 0.0)),
        "- Document recompute: {:.1f} ms".format(float(timings.get("document_recompute") or 0.0)),
    ])
    if include_unresolved and data.get("unresolved"):
        lines.extend(["", "Unresolved positions retained for engineering review:"])
        for item in data.get("unresolved") or []:
            identities = " / ".join(item.get("timber_identities") or []) or "connector position"
            lines.append("- {}: {}".format(identities, item.get("reason") or "unresolved"))
    return "\n".join(lines)


def _crossover_b4_object(doc, crossover_id):
    for obj in _crossover_objects(doc, crossover_id):
        if object_string_property(obj, "GeneratedRole", "") == CROSSOVER_B4_ROLE:
            return obj
    return None


def _crossover_config_with_b4_metadata(config, result):
    """Build the exact persistent B4 state without touching the FreeCAD document."""
    updated = dict(config or {})
    updated["b4_schema_version"] = CROSSOVER_B4_SCHEMA_VERSION
    updated["b4_status"] = str(result.get("status") or CROSSOVER_B4_STATUS_NOT_APPLIED)
    updated["b4_signature"] = str(result.get("resolution_signature") or "")
    updated["b4_settings"] = normalise_crossover_b4_settings(result.get("settings"))
    updated["b4_summary"] = {
        "effective_timber_count": int(result.get("effective_timber_count") or 0),
        "shared_timber_count": int(result.get("shared_timber_count") or 0),
        "plain_connector_timber_count": int(result.get("plain_connector_timber_count") or 0),
        "interlaced_pair_count": int(result.get("interlaced_pair_count") or 0),
        "shoved_timber_count": int(result.get("shoved_timber_count") or 0),
        "unresolved_count": int(result.get("unresolved_count") or 0),
        "remaining_production_conflicts": int(result.get("remaining_production_conflicts") or 0),
        "remaining_production_critical_conflicts": int(result.get("remaining_production_critical_conflicts") or 0),
        "timber_resolution_complete": bool(result.get("timber_resolution_complete")),
    }
    updated["b4_result"] = dict(result)
    updated["timbering_status"] = updated["b4_status"]
    updated["timber_analysis_status"] = CROSSOVER_TIMBER_ANALYSIS_STATUS_STALE
    updated["timber_analysis_signature"] = ""
    updated["timber_analysis_summary"] = {}
    updated["timber_analysis_result_cached"] = False
    updated["production_ready"] = False
    integration_ready = bool(result.get("timber_resolution_complete")) and int(result.get("remaining_production_conflicts") or 0) == 0 and int(result.get("remaining_production_critical_conflicts") or 0) == 0
    updated["host_integration_allowed"] = integration_ready
    updated["host_integration_reason"] = (
        "Automatic timbering is resolved and ready for reversible host integration"
        if integration_ready else
        str(result.get("host_integration_reason") or "Complete automatic timber resolution before host integration")
    )
    if not updated.get("integration_active"):
        updated["integration_status"] = CROSSOVER_INTEGRATION_STATUS_READY if integration_ready else CROSSOVER_INTEGRATION_STATUS_NOT_INTEGRATED
    return updated


def _write_crossover_b4_metadata(doc, config, result):
    updated = _crossover_config_with_b4_metadata(config, result)
    settings_object = None
    configuration_json = json.dumps(updated, sort_keys=True)
    write_statistics = {}
    for obj in _crossover_objects(doc, updated.get("crossover_id")):
        if object_string_property(obj, "GeneratedRole", "") == CROSSOVER_SETTINGS_ROLE:
            settings_object = obj
        _crossover_add_identity_properties(
            obj, updated.get("crossover_id"), updated,
            configuration_json=configuration_json,
            write_statistics=write_statistics,
        )
    if settings_object is None:
        raise ValueError("The crossover settings object is missing.")
    properties = [
        ensure_property(settings_object, "App::PropertyString", CROSSOVER_B4_SETTINGS_PROPERTY, "Crossover automatic timbering", "Validated automatic timber-resolution settings"),
        ensure_property(settings_object, "App::PropertyString", CROSSOVER_B4_RESULT_PROPERTY, "Crossover automatic timbering", "Complete automatic timber-resolution result"),
    ]
    _set_persistent_property_if_changed(
        settings_object, CROSSOVER_B4_SETTINGS_PROPERTY,
        json.dumps(updated["b4_settings"], sort_keys=True), write_statistics,
    )
    _set_persistent_property_if_changed(
        settings_object, CROSSOVER_B4_RESULT_PROPERTY,
        json.dumps(result, sort_keys=True), write_statistics,
    )
    set_read_only(settings_object, properties)
    _crossover_store_catalogue(
        doc, str(updated.get("template_set_id") or ""), write_statistics
    )
    return updated


def apply_crossover_b4_timbering(doc, crossover_id, shared_settings=None, b3_settings=None, b4_settings=None):
    overall_start = time.perf_counter()
    pipeline_timings = {}
    identifier = str(crossover_id or "").strip()
    existing_config = crossover_config_by_id(doc, identifier)
    if existing_config is not None and bool(existing_config.get("integration_active", False)):
        raise ValueError("Remove the crossover host integration before changing the resolved timber arrangement.")
    config = existing_config
    if config is None:
        raise ValueError("Crossover {} was not found.".format(identifier or "selection"))

    stage_start = time.perf_counter()
    inherited = crossover_inherited_timber_records(doc, config)
    analysis_settings = normalise_crossover_timber_analysis_settings(config.get("timber_analysis_settings"))
    shared_settings = normalise_crossover_shared_timber_settings(shared_settings or config.get("shared_timber_settings"))
    b3_settings = normalise_crossover_b3_settings(b3_settings or config.get("b3_settings"))
    b4_settings = normalise_crossover_b4_settings(b4_settings or config.get("b4_settings"))
    pipeline_timings["record_extraction_and_settings"] = (time.perf_counter() - stage_start) * 1000.0

    stage_start = time.perf_counter()
    stored_result = config.get("b4_result") if isinstance(config.get("b4_result"), dict) else None
    existing_object = _crossover_b4_object(doc, identifier)
    stored_settings_match = bool(stored_result) and (
        normalise_crossover_timber_analysis_settings(stored_result.get("analysis_settings")) == analysis_settings
        and normalise_crossover_shared_timber_settings(stored_result.get("shared_settings")) == shared_settings
        and normalise_crossover_b3_settings(stored_result.get("b3_settings")) == b3_settings
        and normalise_crossover_b4_settings(stored_result.get("settings")) == b4_settings
    )
    if (
        stored_settings_match
        and existing_object is not None
        and _crossover_b4_result_is_current(config, inherited, stored_result)
    ):
        result = dict(stored_result)
        result["cache_reused"] = True
        try:
            existing_object.ViewObject.Visibility = bool(b4_settings.get("show_b4_geometry", True))
        except Exception:
            pass
        pipeline_timings["incremental_reuse_lookup"] = (time.perf_counter() - stage_start) * 1000.0
        pipeline_timings["pipeline_total"] = (time.perf_counter() - overall_start) * 1000.0
        result["performance_timings_ms"] = dict(result.get("performance_timings_ms") or {}, **pipeline_timings)
        return result
    pipeline_timings["incremental_reuse_lookup"] = (time.perf_counter() - stage_start) * 1000.0

    stage_start = time.perf_counter()
    context = crossover_shared_timber_envelope_context(doc, config, inherited)
    pipeline_timings["envelope_context_preparation"] = (time.perf_counter() - stage_start) * 1000.0

    stage_start = time.perf_counter()
    result = resolve_crossover_b4_timbering(
        config, inherited, analysis_settings, shared_settings, b3_settings, b4_settings, context
    )
    result["cache_reused"] = False
    pipeline_timings["solver_and_envelope"] = (time.perf_counter() - stage_start) * 1000.0

    stage_start = time.perf_counter()
    shape = _shared_timber_shape_from_records(
        result.get("resolved_timbers") or [],
        float(config.get("template_thickness") or TEMPLATE_THICKNESS) + 0.045,
    )
    if shape is None or _shape_is_null(shape):
        raise ValueError("FreeCAD could not build the automatically resolved timbering display.")
    pipeline_timings["freecad_shape_construction"] = (time.perf_counter() - stage_start) * 1000.0

    group = _crossover_group_object(doc, identifier)
    if group is None:
        raise ValueError("The crossover group is missing.")
    transaction_open = False
    resolved_analysis = None
    try:
        stage_start = time.perf_counter()
        doc.openTransaction("Apply Version {} hybrid timbering {}".format(MACRO_VERSION_NUMBER, identifier))
        transaction_open = True
        clear_chair_analysis_display(doc, "crossover", identifier)
        pipeline_timings["transaction_and_chair_invalidation"] = (time.perf_counter() - stage_start) * 1000.0

        stage_start = time.perf_counter()
        obj = existing_object
        created_object = obj is None
        if obj is None:
            obj = doc.addObject("Part::Feature", unique_internal_name(doc, "CrossoverB4Timbering_{}".format(identifier.replace("-", "_"))))
        obj.Label = "{} Automatically Resolved Timbering".format(identifier)
        obj.Shape = shape
        tag_generated_object(obj, CROSSOVER_B4_ROLE, config.get("template_set_id"))
        properties = [
            ensure_property(obj, "App::PropertyString", CROSSOVER_ID_PROPERTY, "Crossover identity", "Stable crossover identifier"),
            ensure_property(obj, "App::PropertyString", "GeneratedSubtype", "Generated metadata", "Generated object subtype"),
            ensure_property(obj, "App::PropertyString", "B4TimberRecordsJSON", "Crossover automatic timbering", "Complete effective automatically resolved timber records"),
            ensure_property(obj, "App::PropertyString", "B4HybridResultSummaryJSON", "Crossover automatic timbering", "Automatic envelope and movement summary"),
        ]
        setattr(obj, CROSSOVER_ID_PROPERTY, identifier)
        obj.GeneratedSubtype = CROSSOVER_B4_SUBTYPE
        obj.B4TimberRecordsJSON = json.dumps(result.get("resolved_timbers") or [], sort_keys=True)
        obj.B4HybridResultSummaryJSON = json.dumps({
            "shared_timber_count": result.get("shared_timber_count", 0),
            "interlaced_pair_count": result.get("interlaced_pair_count", 0),
            "shoved_timber_count": result.get("shoved_timber_count", 0),
            "unresolved_count": result.get("unresolved_count", 0),
        }, sort_keys=True)
        set_read_only(obj, properties)
        if created_object:
            group.addObject(obj)
        try:
            obj.ViewObject.LineColor = (0.10, 0.35, 0.85)
            obj.ViewObject.LineWidth = 3.0
            obj.ViewObject.Visibility = bool(result.get("settings", {}).get("show_b4_geometry", True))
        except Exception:
            pass
        pipeline_timings["resolved_timber_object_update"] = (time.perf_counter() - stage_start) * 1000.0

        stage_start = time.perf_counter()
        for hidden in (_crossover_shared_timber_object(doc, identifier), _crossover_b3_object(doc, identifier)):
            if hidden is not None:
                try:
                    hidden.ViewObject.Visibility = False
                except Exception:
                    pass
        reference = next((item for item in _crossover_objects(doc, identifier) if object_string_property(item, "GeneratedRole", "") == CROSSOVER_TIMBER_REFERENCE_ROLE), None)
        if reference is not None:
            try:
                reference.ViewObject.Visibility = False
            except Exception:
                pass
        pipeline_timings["visibility_updates"] = (time.perf_counter() - stage_start) * 1000.0

        stage_start = time.perf_counter()
        result["performance_timings_ms"] = dict(result.get("performance_timings_ms") or {}, **pipeline_timings)
        preliminary_updated = _crossover_config_with_b4_metadata(config, result)
        _remove_crossover_timber_analysis_objects(doc, identifier)
        effective_records = list(result.get("resolved_timbers") or [])
        resolved_analysis = dict(result.get("resolved_analysis") or analyse_crossover_timber_records(preliminary_updated, effective_records, analysis_settings))
        resolved_analysis["settings"] = analysis_settings
        resolved_analysis["geometry_signature"] = _timber_geometry_signature(preliminary_updated, analysis_settings, effective_records)
        resolved_analysis["cache_reused"] = False
        resolved_analysis["analysis_basis"] = "Effective automatically resolved timber arrangement"
        resolved_analysis["production_note"] = "No (host integration and chair validation remain outstanding)"
        resolved_analysis["host_integration_reason"] = preliminary_updated.get("host_integration_reason")
        updated, metadata_detail, metadata_statistics = _write_crossover_b4_and_timber_analysis_metadata(
            doc, config, result, resolved_analysis
        )
        pipeline_timings.update(metadata_detail)
        pipeline_timings["metadata_updates"] = (time.perf_counter() - stage_start) * 1000.0
        result["metadata_update_statistics"] = metadata_statistics

        stage_start = time.perf_counter()
        _create_crossover_timber_analysis_display(doc, updated, resolved_analysis)
        pipeline_timings["diagnostic_display_construction"] = (time.perf_counter() - stage_start) * 1000.0

        stage_start = time.perf_counter()
        _document_recompute(doc)
        pipeline_timings["document_recompute"] = (time.perf_counter() - stage_start) * 1000.0
        pipeline_timings["metadata_objects_and_recompute"] = (
            pipeline_timings["resolved_timber_object_update"]
            + pipeline_timings["visibility_updates"]
            + pipeline_timings["metadata_updates"]
            + pipeline_timings["diagnostic_display_construction"]
            + pipeline_timings["document_recompute"]
        )

        stage_start = time.perf_counter()
        doc.commitTransaction()
        transaction_open = False
        pipeline_timings["transaction_commit"] = (time.perf_counter() - stage_start) * 1000.0
    except Exception:
        if transaction_open:
            try:
                doc.abortTransaction()
            except Exception:
                pass
        raise
    pipeline_timings["pipeline_total"] = (time.perf_counter() - overall_start) * 1000.0
    result["performance_timings_ms"] = dict(result.get("performance_timings_ms") or {}, **pipeline_timings)
    result["resolved_analysis"] = resolved_analysis
    return result



def clear_crossover_b4_timbering(doc, crossover_id):
    clear_chair_analysis_display(doc, "crossover", str(crossover_id or "").strip())
    existing_config = crossover_config_by_id(doc, str(crossover_id or "").strip())
    if existing_config is not None and bool(existing_config.get("integration_active", False)):
        raise ValueError("Remove the crossover host integration before changing the resolved timber arrangement.")
    identifier = str(crossover_id or "").strip()
    config = crossover_config_by_id(doc, identifier)
    if config is None:
        raise ValueError("Crossover {} was not found.".format(identifier or "selection"))
    transaction_open = False
    try:
        doc.openTransaction("Remove Version {} hybrid timbering {}".format(MACRO_VERSION_NUMBER, identifier))
        transaction_open = True
        obj = _crossover_b4_object(doc, identifier)
        if obj is not None:
            doc.removeObject(str(obj.Name))
        updated = dict(config)
        updated["b4_status"] = CROSSOVER_B4_STATUS_NOT_APPLIED
        updated["b4_signature"] = ""
        updated["b4_summary"] = {}
        updated["b4_result"] = {}
        b3_current = crossover_b3_effective_status(doc, updated)
        b2_current = crossover_shared_timber_effective_status(doc, updated)
        if b3_current not in (CROSSOVER_B3_STATUS_NOT_APPLIED, CROSSOVER_B3_STATUS_STALE):
            updated["timbering_status"] = str(updated.get("b3_status") or b3_current)
            effective_records = list((updated.get("b3_result") or {}).get("resolved_timbers") or _crossover_b2_effective_timber_records(doc, updated))
            basis = "Effective interlaced and longitudinally adjusted timber arrangement"
            restore = _crossover_b3_object(doc, identifier)
        elif b2_current not in (CROSSOVER_SHARED_TIMBER_STATUS_NOT_APPLIED, CROSSOVER_SHARED_TIMBER_STATUS_STALE):
            updated["timbering_status"] = str(updated.get("shared_timber_status") or b2_current)
            effective_records = _crossover_b2_effective_timber_records(doc, updated)
            basis = "Effective shared long-timber arrangement"
            restore = _crossover_shared_timber_object(doc, identifier)
        else:
            updated["timbering_status"] = CROSSOVER_TIMBER_STATUS_UNRESOLVED
            effective_records = crossover_inherited_timber_records(doc, updated)
            basis = "Inherited turnout reference timbering"
            restore = next((item for item in _crossover_objects(doc, identifier) if object_string_property(item, "GeneratedRole", "") == CROSSOVER_TIMBER_REFERENCE_ROLE), None)
        updated["production_ready"] = False
        updated["host_integration_allowed"] = False
        if not updated.get("integration_active"):
            updated["integration_status"] = CROSSOVER_INTEGRATION_STATUS_NOT_INTEGRATED
        updated["host_integration_reason"] = "Automatic timber resolution is not applied; host integration and chair validation remain outstanding"
        for current in _crossover_objects(doc, identifier):
            _crossover_add_identity_properties(current, identifier, updated)
            if object_string_property(current, "GeneratedRole", "") == CROSSOVER_SETTINGS_ROLE and CROSSOVER_B4_RESULT_PROPERTY in getattr(current, "PropertiesList", []):
                setattr(current, CROSSOVER_B4_RESULT_PROPERTY, "")
        if restore is not None:
            try:
                restore.ViewObject.Visibility = True
            except Exception:
                pass
        _remove_crossover_timber_analysis_objects(doc, identifier)
        analysis_settings = normalise_crossover_timber_analysis_settings(updated.get("timber_analysis_settings"))
        analysis = analyse_crossover_timber_records(updated, effective_records, analysis_settings)
        analysis["settings"] = analysis_settings
        analysis["geometry_signature"] = _timber_geometry_signature(updated, analysis_settings, effective_records)
        analysis["cache_reused"] = False
        analysis["analysis_basis"] = basis
        analysis["production_note"] = "No (host integration and chair validation remain outstanding)"
        analysis["host_integration_reason"] = updated.get("host_integration_reason")
        updated = _write_crossover_timber_analysis_metadata(doc, updated, analysis)
        _create_crossover_timber_analysis_display(doc, updated, analysis)
        _crossover_store_catalogue(doc, str(updated.get("template_set_id") or ""))
        _document_recompute(doc)
        doc.commitTransaction()
        transaction_open = False
    except Exception:
        if transaction_open:
            try:
                doc.abortTransaction()
            except Exception:
                pass
        raise
    return identifier


def set_crossover_b4_visibility(doc, crossover_id, visible):
    obj = _crossover_b4_object(doc, crossover_id)
    if obj is None:
        return False
    try:
        obj.ViewObject.Visibility = bool(visible)
        return True
    except Exception:
        return False


def crossover_b4_effective_status(doc, crossover_config):
    config = dict(crossover_config or {})
    result = config.get("b4_result")
    if not isinstance(result, dict) or not result.get("applied"):
        return CROSSOVER_B4_STATUS_NOT_APPLIED
    try:
        inherited = crossover_inherited_timber_records(doc, config)
        if not _crossover_b4_result_is_current(config, inherited, result):
            return CROSSOVER_B4_STATUS_STALE
    except Exception:
        return CROSSOVER_B4_STATUS_STALE
    return str(config.get("b4_status") or result.get("status") or CROSSOVER_B4_STATUS_NOT_APPLIED)



def _crossover_integration_objects(doc, crossover_id):
    identifier = str(crossover_id or "").strip()
    roles = {
        CROSSOVER_INTEGRATION_GROUP_ROLE,
        CROSSOVER_INTEGRATION_SETTINGS_ROLE,
        CROSSOVER_INTEGRATED_DISPLAY_ROLE,
        CROSSOVER_INTEGRATED_TEMPLATE_ROLE,
        CROSSOVER_INTEGRATED_OUTLINE_ROLE,
        CROSSOVER_INTEGRATED_TIMBER_ROLE,
    }
    return [
        obj for obj in list(doc.Objects)
        if object_string_property(obj, CROSSOVER_ID_PROPERTY, "") == identifier
        and object_string_property(obj, "GeneratedRole", "") in roles
    ]


def crossover_host_integration_by_id(doc, crossover_id):
    for obj in _crossover_integration_objects(doc, crossover_id):
        if object_string_property(obj, "GeneratedRole", "") != CROSSOVER_INTEGRATION_SETTINGS_ROLE:
            continue
        stored = object_string_property(obj, CROSSOVER_INTEGRATION_PROPERTY, "")
        try:
            data = json.loads(stored)
        except Exception:
            return None
        return data if isinstance(data, dict) else None
    return None


def _crossover_integration_alignment_signature(doc, config):
    payload = []
    for side in ("a", "b"):
        host_name = str(config.get("host_{}_object".format(side)) or "")
        host = doc.getObject(host_name) if host_name else None
        if host is None or not is_turnout_host_centreline(host):
            raise ValueError("The Host {} centreline is no longer available.".format(side.upper()))
        data = turnout_host_alignment(host)
        interval = list(config.get("host_{}_station_interval".format(side)) or [])
        if len(interval) != 2:
            raise ValueError("The Host {} replacement interval is missing.".format(side.upper()))
        samples = []
        for value in (float(interval[0]), 0.5 * (float(interval[0]) + float(interval[1])), float(interval[1])):
            point, heading = interpolate_alignment_station(data, value)
            samples.append([round(float(point.x), 6), round(float(point.y), 6), round(float(heading), 9)])
        payload.append({
            "side": side,
            "host": host_name,
            "total": round(float(data.get("total") or 0.0), 6),
            "interval": [round(float(interval[0]), 6), round(float(interval[1]), 6)],
            "samples": samples,
        })
    return hashlib.sha256(json.dumps(payload, sort_keys=True, separators=(",", ":")).encode("utf-8")).hexdigest()


def _crossover_integration_signature(doc, config, b4_result, source_record_ids, section_number):
    payload = {
        "schema_version": CROSSOVER_INTEGRATION_SCHEMA_VERSION,
        "crossover_id": str(config.get("crossover_id") or ""),
        "b4_signature": str((b4_result or {}).get("resolution_signature") or config.get("b4_signature") or ""),
        "alignment_signature": _crossover_integration_alignment_signature(doc, config),
        "source_record_ids": sorted(str(value) for value in source_record_ids or []),
        "section_number": int(section_number or 0),
    }
    return hashlib.sha256(json.dumps(payload, sort_keys=True, separators=(",", ":")).encode("utf-8")).hexdigest()


def _crossover_record_metadata_copy(record):
    copied = dict(record or {})
    copied.pop("shape", None)
    copied.pop("hydration_error", None)
    copied.pop("hydration_repair", None)
    return copied


def _crossover_add_integration_identity(obj, crossover_id, integration_config, crossover_config):
    prop = ensure_property(obj, "App::PropertyString", CROSSOVER_INTEGRATION_PROPERTY, "Crossover host integration", "Validated reversible crossover host-integration configuration")
    setattr(obj, CROSSOVER_INTEGRATION_PROPERTY, json.dumps(integration_config, sort_keys=True))
    _crossover_add_identity_properties(obj, crossover_id, crossover_config)
    set_read_only(obj, [prop])


def _crossover_add_integrated_feature(doc, group, config, role, label, stem, shape, subtype, category, section_number=0):
    identifier = str(config.get("crossover_id") or "")
    obj = doc.addObject("Part::Feature", unique_internal_name(doc, "{}_{}".format(stem, identifier.replace("-", "_"))))
    obj.Label = label
    obj.Shape = shape
    tag_generated_object(obj, role, str(config.get("template_set_id") or ""))
    tag_route_metadata(obj, identifier, "Integrated managed crossover")
    tag_export_metadata(
        obj, subtype, category,
        section_number=int(section_number or 0),
        travel_order_number=int(section_number or 0),
        feature_number=_crossover_number_from_identifier(identifier),
        section_length=float(config.get("overall_crossover_length") or 0.0),
    )
    group.addObject(obj)
    return obj


def _crossover_integration_record(obj, config, role, subtype, category, selection_key, shape, section_number):
    return {
        "role": role,
        "subtype": subtype,
        "category": category,
        "selection_key": selection_key,
        "route_id": str(config.get("crossover_id") or ""),
        "route_name": "Integrated managed crossover",
        "track_number": 0,
        "track_name": "Integrated crossover assembly",
        "platform_number": 0,
        "platform_name": "",
        "section_number": int(section_number or 0),
        "travel_order_number": int(section_number or 0),
        "feature_number": _crossover_number_from_identifier(config.get("crossover_id")),
        "section_length": float(config.get("overall_crossover_length") or 0.0),
        "template_thickness": float(config.get("template_thickness") or TEMPLATE_THICKNESS),
        "source_name": str(obj.Name),
        "source_label": str(getattr(obj, "Label", obj.Name)),
        "shape": shape.copy(),
    }


def _crossover_source_records_for_side(records, config, side, section_number, sectioned):
    internal = dict(config.get("turnout_{}_config".format(side)) or {})
    route_id = str(internal.get("route_id") or "")
    track_number = int(internal.get("track_number") or 0)
    matched = []
    for record in records:
        subtype = str(record.get("subtype") or "")
        if sectioned:
            if subtype != "TrackTemplateSection" or int(record.get("section_number") or 0) != int(section_number or 0):
                continue
        else:
            if subtype != "TrackTemplateCompound":
                continue
        if str(record.get("route_id") or "") != route_id:
            continue
        if int(record.get("track_number") or 0) not in (0, track_number):
            continue
        matched.append(record)
    return matched


def _crossover_find_host_source(doc, config, side, host_data, interval, width, thickness):
    internal = dict(config.get("turnout_{}_config".format(side)) or {})
    unsplit, sections = _turnout_host_template_sources(doc, internal)
    replacement = _turnout_corridor_shape(
        host_data,
        max(0.0, float(interval[0]) - CROSSOVER_INTEGRATION_CLEARANCE),
        min(float(host_data["total"]), float(interval[1]) + CROSSOVER_INTEGRATION_CLEARANCE),
        float(width) + (2.0 * CROSSOVER_INTEGRATION_CLEARANCE),
        thickness,
    )
    full_corridor = _turnout_corridor_shape(
        host_data, 0.0, float(host_data["total"]),
        float(width) + (2.0 * CROSSOVER_INTEGRATION_CLEARANCE), thickness,
    )
    candidates = []
    source_list = sections if sections else unsplit
    for source in source_list:
        shape = getattr(source, "Shape", None)
        if _shape_is_null(shape):
            continue
        selected_piece = _turnout_shape_common(shape, full_corridor, "Host {} track template".format(side.upper()))
        affected_piece = _turnout_shape_common(selected_piece, replacement, "Host {} crossover interval".format(side.upper()))
        if not _turnout_shape_has_material(affected_piece):
            continue
        station_start, station_finish = _turnout_station_range_from_shape(host_data, selected_piece)
        if station_start > float(interval[0]) + CROSSOVER_INTEGRATION_CLEARANCE or station_finish < float(interval[1]) - CROSSOVER_INTEGRATION_CLEARANCE:
            raise ValueError("Host {} crossover interval is not contained inside one existing template section.".format(side.upper()))
        candidates.append({
            "source": source,
            "source_shape": shape,
            "selected_track_piece": selected_piece,
            "replacement_corridor": replacement,
            "sectioned": bool(sections),
            "section_number": _integer_object_property(source, "SectionNumber", 0) if sections else 0,
            "section_length": quantity_value(source, "SectionLength", max(0.0, station_finish - station_start)),
            "source_visibility": _turnout_visibility_state(source),
        })
    if len(candidates) != 1:
        raise ValueError("Host {} integration requires exactly one affected {}template source; found {}.".format(side.upper(), "sectioned " if sections else "", len(candidates)))
    return candidates[0]


def build_crossover_host_integration(doc, crossover_id):
    identifier = str(crossover_id or "").strip()
    config = crossover_config_by_id(doc, identifier)
    if config is None:
        raise ValueError("Crossover {} was not found.".format(identifier or "selection"))
    if crossover_host_integration_by_id(doc, identifier) is not None or bool(config.get("integration_active", False)):
        raise ValueError("{} is already integrated with its host templates.".format(identifier))
    inherited = crossover_inherited_timber_records(doc, config)
    b4_result = dict(config.get("b4_result") or {})
    if not _crossover_b4_result_is_current(config, inherited, b4_result):
        raise ValueError("Run the automatic timber resolver again before host integration.")
    if not b4_result.get("timber_resolution_complete") or int(b4_result.get("remaining_production_conflicts") or 0) or int(b4_result.get("remaining_production_critical_conflicts") or 0):
        raise ValueError("Host integration requires a complete automatic timbering result with no production conflicts.")
    roles = {object_string_property(obj, "GeneratedRole", ""): obj for obj in _crossover_objects(doc, identifier)}
    template_obj = roles.get(CROSSOVER_TEMPLATE_ROLE)
    outline_obj = roles.get(CROSSOVER_OUTLINE_ROLE)
    b4_obj = roles.get(CROSSOVER_B4_ROLE)
    if template_obj is None or outline_obj is None or b4_obj is None:
        raise ValueError("The crossover is missing its template, cutting footprint or final resolved timber object.")
    template_shape = getattr(template_obj, "Shape", None)
    if _shape_is_null(template_shape):
        raise ValueError("The crossover template solid is empty.")
    resolved_records = list(b4_result.get("resolved_timbers") or [])
    timber_shape = _shared_timber_shape_from_records(resolved_records, z_value=0.03)
    if _shape_is_null(timber_shape):
        raise ValueError("The final resolved timber geometry is empty.")

    thickness = float(config.get("template_thickness") or TEMPLATE_THICKNESS)
    source_specs = {}
    for side in ("a", "b"):
        host_name = str(config.get("host_{}_object".format(side)) or "")
        host = doc.getObject(host_name) if host_name else None
        if host is None or not is_turnout_host_centreline(host):
            raise ValueError("The Host {} centreline is no longer available.".format(side.upper()))
        host_data = turnout_host_alignment(host)
        interval = list(config.get("host_{}_station_interval".format(side)) or [])
        internal = dict(config.get("turnout_{}_config".format(side)) or {})
        width = float(internal.get("template_width") or config.get("connector_width") or DEFAULT_MAIN_TEMPLATE_WIDTH)
        source_specs[side] = _crossover_find_host_source(doc, config, side, host_data, interval, width, thickness)

    if source_specs["a"]["sectioned"] != source_specs["b"]["sectioned"]:
        raise ValueError("Both crossover hosts must use the same sectioning mode for reversible integration.")
    sectioned = bool(source_specs["a"]["sectioned"])
    section_number = int(source_specs["a"]["section_number"] or 0)
    if sectioned and int(source_specs["b"]["section_number"] or 0) != section_number:
        raise ValueError("Both affected host tracks must lie in the same universal section before crossover integration.")

    # Preserve the complete visible source section(s), remove only each selected
    # host corridor, then add the crossover assembly once.
    unique_sources = {}
    for side, spec in source_specs.items():
        unique_sources.setdefault(str(spec["source"].Name), {"source": spec["source"], "shape": spec["source_shape"].copy(), "corridors": []})
        unique_sources[str(spec["source"].Name)]["corridors"].append(spec["replacement_corridor"])
    display_base = None
    for item in unique_sources.values():
        shape = item["shape"]
        for corridor in item["corridors"]:
            shape = _turnout_shape_cut(shape, corridor, "affected host display", allow_empty=True)
        display_base = _turnout_shape_fuse(display_base, shape, "combined unaffected host display") if shape is not None else display_base
    display_shape = _turnout_shape_fuse(display_base, template_shape, "integrated crossover host display")

    production_base = None
    for side, spec in source_specs.items():
        piece = _turnout_shape_cut(spec["selected_track_piece"], spec["replacement_corridor"], "Host {} production track".format(side.upper()), allow_empty=True)
        if piece is not None:
            production_base = _turnout_shape_fuse(production_base, piece, "combined unaffected host production tracks")
    production_shape = _turnout_shape_fuse(production_base, template_shape, "integrated crossover production assembly")
    cutting_shape = plan_profile_from_shape(production_shape)
    if cutting_shape is None or _shape_is_null(cutting_shape):
        raise ValueError("FreeCAD could not derive the integrated crossover cutting profile.")

    settings = settings_for_template_set(doc, str(config.get("template_set_id") or ""))
    if settings is None:
        raise ValueError("The template set has no persistent production catalogue.")
    index_payload = read_production_record_index(settings)
    if not index_payload:
        raise ValueError("The template set has no production-record index to integrate safely.")
    current_records = hydrate_production_index_records(doc, index_payload)
    host_records = []
    for side in ("a", "b"):
        host_records.extend(_crossover_source_records_for_side(current_records, config, side, section_number, sectioned))
    host_record_ids = {str(record.get("record_id") or "") for record in host_records if str(record.get("record_id") or "")}
    if not host_record_ids:
        raise ValueError("No host-template production records matched the affected crossover tracks.")
    crossover_records = [
        record for record in current_records
        if str(record.get("subtype") or "") == CROSSOVER_SUBTYPE_TEMPLATE
        and int(record.get("feature_number") or 0) == _crossover_number_from_identifier(identifier)
    ]
    crossover_record_ids = {str(record.get("record_id") or "") for record in crossover_records if str(record.get("record_id") or "")}
    stored_by_id = {str(item.get("record_id") or ""): dict(item) for item in index_payload.get("records", []) if str(item.get("record_id") or "")}
    all_removed_ids = sorted(host_record_ids | crossover_record_ids)
    return {
        "crossover_id": identifier,
        "config": config,
        "b4_result": b4_result,
        "resolved_records": resolved_records,
        "display_shape": display_shape,
        "production_shape": production_shape,
        "cutting_shape": cutting_shape,
        "timber_shape": timber_shape,
        "sectioned": sectioned,
        "section_number": section_number,
        "section_length": max(float(source_specs["a"].get("section_length") or 0.0), float(source_specs["b"].get("section_length") or 0.0)),
        "source_specs": source_specs,
        "source_visibility": {str(spec["source"].Name): spec["source_visibility"] for spec in source_specs.values()},
        "crossover_visibility": {str(obj.Name): _turnout_visibility_state(obj) for obj in (template_obj, outline_obj, b4_obj)},
        "current_records": current_records,
        "removed_record_ids": all_removed_ids,
        "original_host_record_metadata": [stored_by_id[value] for value in sorted(host_record_ids) if value in stored_by_id],
        "original_crossover_record_metadata": [stored_by_id[value] for value in sorted(crossover_record_ids) if value in stored_by_id],
        "source_record_ids": all_removed_ids,
    }


def create_crossover_host_integration(doc, crossover_id):
    clear_chair_analysis_display(doc, "crossover", str(crossover_id or "").strip())
    prepared = build_crossover_host_integration(doc, crossover_id)
    identifier = prepared["crossover_id"]
    config = dict(prepared["config"])
    set_id = str(config.get("template_set_id") or "")
    signature = _crossover_integration_signature(doc, config, prepared["b4_result"], prepared["source_record_ids"], prepared["section_number"])
    transaction_open = False
    try:
        doc.openTransaction("Integrate Version {} crossover {} with host templates".format(MACRO_VERSION_NUMBER, identifier))
        transaction_open = True
        parent = _crossover_group_object(doc, identifier)
        group = doc.addObject("App::DocumentObjectGroup", unique_internal_name(doc, "RailwayCrossoverHostIntegration_{}".format(identifier.replace("-", "_"))))
        group.Label = "{} Reversible Host Integration".format(identifier)
        tag_generated_object(group, CROSSOVER_INTEGRATION_GROUP_ROLE, set_id)
        if parent is not None:
            parent.addObject(group)
        settings_obj = doc.addObject("Part::Feature", unique_internal_name(doc, "RailwayCrossoverHostIntegrationSettings_{}".format(identifier.replace("-", "_"))))
        settings_obj.Label = "{} Host Integration Settings".format(identifier)
        tag_generated_object(settings_obj, CROSSOVER_INTEGRATION_SETTINGS_ROLE, set_id)
        group.addObject(settings_obj)
        section_number = int(prepared["section_number"] or 0)
        display_obj = _crossover_add_integrated_feature(doc, group, config, CROSSOVER_INTEGRATED_DISPLAY_ROLE, "{} Integrated Host Display".format(identifier), "RailwayCrossoverIntegratedDisplay", prepared["display_shape"], CROSSOVER_INTEGRATED_SUBTYPE, EXPORT_CATEGORY_SOLID, section_number)
        production_obj = _crossover_add_integrated_feature(doc, group, config, CROSSOVER_INTEGRATED_TEMPLATE_ROLE, "{} Integrated Crossover Template".format(identifier), "RailwayCrossoverIntegratedTemplate", prepared["production_shape"], CROSSOVER_INTEGRATED_SUBTYPE, EXPORT_CATEGORY_SOLID, section_number)
        outline_obj = _crossover_add_integrated_feature(doc, group, config, CROSSOVER_INTEGRATED_OUTLINE_ROLE, "{} Integrated Cutting Profile".format(identifier), "RailwayCrossoverIntegratedOutline", prepared["cutting_shape"], CROSSOVER_INTEGRATED_SUBTYPE, EXPORT_CATEGORY_CUTTING, section_number)
        timber_obj = _crossover_add_integrated_feature(doc, group, config, CROSSOVER_INTEGRATED_TIMBER_ROLE, "{} Final Resolved Timbering".format(identifier), "RailwayCrossoverIntegratedTimbering", prepared["timber_shape"], CROSSOVER_INTEGRATED_TIMBER_SUBTYPE, EXPORT_CATEGORY_ENGRAVING, section_number)
        created = [group, settings_obj, display_obj, production_obj, outline_obj, timber_obj]
        new_records = [
            _crossover_integration_record(production_obj, config, CROSSOVER_INTEGRATED_TEMPLATE_ROLE, CROSSOVER_INTEGRATED_SUBTYPE, EXPORT_CATEGORY_SOLID, TURNOUT_SELECTION_TEMPLATE_3D, prepared["production_shape"], section_number),
            _crossover_integration_record(outline_obj, config, CROSSOVER_INTEGRATED_OUTLINE_ROLE, CROSSOVER_INTEGRATED_SUBTYPE, EXPORT_CATEGORY_CUTTING, TURNOUT_SELECTION_TEMPLATE_2D, prepared["cutting_shape"], section_number),
            _crossover_integration_record(timber_obj, config, CROSSOVER_INTEGRATED_TIMBER_ROLE, CROSSOVER_INTEGRATED_TIMBER_SUBTYPE, EXPORT_CATEGORY_ENGRAVING, TURNOUT_SELECTION_ENGRAVING, prepared["timber_shape"], section_number),
        ]
        removed = set(prepared["removed_record_ids"])
        combined = [record for record in prepared["current_records"] if str(record.get("record_id") or "") not in removed] + new_records
        _turnout_write_production_records(doc, set_id, combined)
        integration_config = {
            "schema_version": CROSSOVER_INTEGRATION_SCHEMA_VERSION,
            "macro_version": MACRO_VERSION_NUMBER,
            "crossover_id": identifier,
            "template_set_id": set_id,
            "status": CROSSOVER_INTEGRATION_STATUS_ACTIVE,
            "signature": signature,
            "b4_signature": str(prepared["b4_result"].get("resolution_signature") or ""),
            "sectioned": bool(prepared["sectioned"]),
            "section_number": section_number,
            "source_record_ids": list(prepared["source_record_ids"]),
            "original_host_record_metadata": list(prepared["original_host_record_metadata"]),
            "original_crossover_record_metadata": list(prepared["original_crossover_record_metadata"]),
            "integration_object_names": [str(obj.Name) for obj in created],
            "source_visibility": dict(prepared["source_visibility"]),
            "crossover_visibility": dict(prepared["crossover_visibility"]),
            "source_basis": list(CROSSOVER_INTEGRATION_SOURCE_BASIS),
        }
        config["integration_schema_version"] = CROSSOVER_INTEGRATION_SCHEMA_VERSION
        config["integration_active"] = True
        config["integration_status"] = CROSSOVER_INTEGRATION_STATUS_ACTIVE
        config["integration_signature"] = signature
        config["integration_summary"] = {
            "section_number": section_number,
            "replaced_record_count": len(prepared["removed_record_ids"]),
            "integration_object_count": len(created),
            "resolved_timber_count": len(prepared["resolved_records"]),
        }
        config["integration_result"] = dict(integration_config)
        config["host_integration_allowed"] = True
        config["host_integration_reason"] = "Host integration active; chair validation remains outstanding"
        config["template_joint_check"] = "Passed: affected host records replaced reversibly without changing section numbering"
        config["section_boundary_check"] = "Passed: both host intervals are contained within the same universal section" if prepared["sectioned"] else "Passed: unsectioned host templates integrated reversibly"
        config["production_ready"] = False
        for obj in _crossover_objects(doc, identifier):
            _crossover_add_identity_properties(obj, identifier, config)
        for obj in created:
            _crossover_add_integration_identity(obj, identifier, integration_config, config)
        for source_name in prepared["source_visibility"]:
            _turnout_set_visibility(doc.getObject(source_name), False)
        for source_name in prepared["crossover_visibility"]:
            _turnout_set_visibility(doc.getObject(source_name), False)
        if Gui is not None:
            try:
                display_obj.ViewObject.ShapeColor = (0.72, 0.80, 0.86)
                display_obj.ViewObject.Transparency = 20
                production_obj.ViewObject.Visibility = False
                outline_obj.ViewObject.Visibility = False
                timber_obj.ViewObject.LineColor = (0.15, 0.45, 0.85)
                timber_obj.ViewObject.LineWidth = 1.5
                timber_obj.ViewObject.Visibility = True
            except Exception:
                pass
        _crossover_store_catalogue(doc, set_id)
        _document_recompute(doc)
        doc.commitTransaction()
        transaction_open = False
    except Exception:
        if transaction_open:
            try:
                doc.abortTransaction()
            except Exception:
                pass
        raise
    return config


def _crossover_integration_restored_records(doc, integration, restore_crossover_records=True):
    set_id = str((integration or {}).get("template_set_id") or "")
    settings = settings_for_template_set(doc, set_id)
    if settings is None:
        raise ValueError("The integrated template set has no persistent production catalogue.")
    payload = read_production_record_index(settings)
    current = hydrate_production_index_records(doc, payload) if payload else []
    integration_names = set(str(value) for value in (integration or {}).get("integration_object_names", []))
    retained = [record for record in current if str(record.get("source_name") or "") not in integration_names]
    metadata = list((integration or {}).get("original_host_record_metadata") or [])
    if restore_crossover_records:
        metadata.extend(list((integration or {}).get("original_crossover_record_metadata") or []))
    restored = hydrate_production_index_records(doc, {"records": metadata}) if metadata else []
    missing = [record for record in restored if record.get("shape") is None]
    if missing:
        raise ValueError("Original production geometry cannot be restored because {} source record(s) are missing.".format(len(missing)))
    return retained + restored


def remove_crossover_host_integration(doc, crossover_id):
    identifier = str(crossover_id or "").strip()
    clear_chair_analysis_display(doc, "crossover", identifier)
    integration = crossover_host_integration_by_id(doc, identifier)
    if integration is None:
        raise ValueError("{} has no host integration to remove.".format(identifier or "The selected crossover"))
    config = crossover_config_by_id(doc, identifier)
    if config is None:
        raise ValueError("Crossover {} no longer exists.".format(identifier))
    effective_before_removal = crossover_host_integration_effective_status(doc, config)
    restored_records = _crossover_integration_restored_records(doc, integration, restore_crossover_records=True)
    names = set(str(value) for value in integration.get("integration_object_names", []))
    transaction_open = False
    try:
        doc.openTransaction("Remove Version {} crossover host integration {}".format(MACRO_VERSION_NUMBER, identifier))
        transaction_open = True
        _turnout_write_production_records(doc, str(config.get("template_set_id") or ""), restored_records)
        for source_name, visible in dict(integration.get("source_visibility") or {}).items():
            _turnout_set_visibility(doc.getObject(source_name), visible)
        for source_name, visible in dict(integration.get("crossover_visibility") or {}).items():
            _turnout_set_visibility(doc.getObject(source_name), visible)
        group_names = []
        part_names = []
        for name in names:
            obj = doc.getObject(name)
            if obj is None:
                continue
            if object_string_property(obj, "GeneratedRole", "") == CROSSOVER_INTEGRATION_GROUP_ROLE:
                group_names.append(name)
            else:
                part_names.append(name)
        for name in part_names:
            if doc.getObject(name) is not None:
                doc.removeObject(name)
        for name in group_names:
            if doc.getObject(name) is not None:
                doc.removeObject(name)
        integration_remains_current = effective_before_removal == CROSSOVER_INTEGRATION_STATUS_ACTIVE
        config["integration_active"] = False
        config["integration_status"] = (
            CROSSOVER_INTEGRATION_STATUS_READY
            if integration_remains_current
            else CROSSOVER_INTEGRATION_STATUS_NOT_INTEGRATED
        )
        config["integration_signature"] = ""
        config["integration_summary"] = {}
        config["integration_result"] = {}
        config["host_integration_allowed"] = bool(integration_remains_current)
        config["host_integration_reason"] = (
            "Automatic timbering remains resolved and ready for host integration"
            if integration_remains_current
            else "The previous host integration was stale; review the host geometry and rerun automatic timbering before integrating again"
        )
        config["production_ready"] = False
        for obj in _crossover_objects(doc, identifier):
            _crossover_add_identity_properties(obj, identifier, config)
        _crossover_store_catalogue(doc, str(config.get("template_set_id") or ""))
        _document_recompute(doc)
        doc.commitTransaction()
        transaction_open = False
    except Exception:
        if transaction_open:
            try:
                doc.abortTransaction()
            except Exception:
                pass
        raise
    return config


def crossover_host_integration_effective_status(doc, config):
    data = dict(config or {})
    if not data.get("integration_active"):
        return (
            CROSSOVER_INTEGRATION_STATUS_READY
            if data.get("host_integration_allowed")
            else CROSSOVER_INTEGRATION_STATUS_NOT_INTEGRATED
        )
    if not data.get("host_integration_allowed"):
        return CROSSOVER_INTEGRATION_STATUS_STALE
    integration = crossover_host_integration_by_id(doc, data.get("crossover_id"))
    if integration is None:
        return CROSSOVER_INTEGRATION_STATUS_STALE
    try:
        expected = _crossover_integration_signature(
            doc, data, data.get("b4_result") or {}, integration.get("source_record_ids") or [], integration.get("section_number") or 0
        )
    except Exception:
        return CROSSOVER_INTEGRATION_STATUS_STALE
    if str(integration.get("signature") or "") != expected or str(data.get("integration_signature") or "") != expected:
        return CROSSOVER_INTEGRATION_STATUS_STALE
    for name in integration.get("integration_object_names") or []:
        if doc.getObject(str(name)) is None:
            return CROSSOVER_INTEGRATION_STATUS_STALE
    for name in list((integration.get("source_visibility") or {}).keys()) + list((integration.get("crossover_visibility") or {}).keys()):
        if doc.getObject(str(name)) is None:
            return CROSSOVER_INTEGRATION_STATUS_STALE
    return CROSSOVER_INTEGRATION_STATUS_ACTIVE


def crossover_host_integration_summary(doc, config):
    data = dict(config or {})
    integration = crossover_host_integration_by_id(doc, data.get("crossover_id")) or dict(data.get("integration_result") or {})
    summary = dict(data.get("integration_summary") or {})
    lines = [
        "Version {} — Crossover host integration".format(CROSSOVER_OPERATOR_VERSION_NUMBER),
        "Crossover: {}".format(data.get("crossover_id") or "Unknown"),
        "Status: {}".format(crossover_host_integration_effective_status(doc, data)),
        "Host A: {}".format(data.get("host_a_track_name") or data.get("host_a_label") or ""),
        "Host B: {}".format(data.get("host_b_track_name") or data.get("host_b_label") or ""),
        "Sectioning: {}".format("Universal section {}".format(integration.get("section_number")) if integration.get("sectioned") else "Unsectioned host templates"),
        "Production records replaced: {}".format(summary.get("replaced_record_count", 0)),
        "Integration objects: {}".format(summary.get("integration_object_count", 0)),
        "Resolved timbers integrated: {}".format(summary.get("resolved_timber_count", 0)),
        "Template-joint check: {}".format(data.get("template_joint_check") or "Not asserted"),
        "Section-boundary check: {}".format(data.get("section_boundary_check") or "Not asserted"),
        "Production ready: No (chair validation remains outstanding)",
    ]
    return "\n".join(lines)


def _crossover_timber_analysis_objects(doc, crossover_id):
    identifier = str(crossover_id or "").strip()
    roles = {
        CROSSOVER_TIMBER_ANALYSIS_GROUP_ROLE,
        CROSSOVER_TIMBER_CONFLICT_MARKER_ROLE,
        CROSSOVER_TIMBER_SUPPORT_MARKER_ROLE,
    }
    return [
        obj for obj in list(doc.Objects)
        if object_string_property(obj, CROSSOVER_ID_PROPERTY, "") == identifier
        and object_string_property(obj, "GeneratedRole", "") in roles
    ]


def _remove_crossover_timber_analysis_objects(doc, crossover_id):
    objects = _crossover_timber_analysis_objects(doc, crossover_id)
    group_names = [
        str(obj.Name) for obj in objects
        if object_string_property(obj, "GeneratedRole", "") == CROSSOVER_TIMBER_ANALYSIS_GROUP_ROLE
    ]
    part_names = [str(obj.Name) for obj in objects if str(obj.Name) not in group_names]
    for name in part_names + group_names:
        if doc.getObject(name) is not None:
            doc.removeObject(name)
    return len(objects)


def clear_crossover_timber_analysis_display(doc, crossover_id):
    identifier = str(crossover_id or "").strip()
    transaction_open = False
    try:
        doc.openTransaction("Clear Version {} timber analysis display {}".format(MACRO_VERSION_NUMBER, identifier))
        transaction_open = True
        removed = _remove_crossover_timber_analysis_objects(doc, identifier)
        _document_recompute(doc)
        doc.commitTransaction()
        transaction_open = False
        return removed
    except Exception:
        if transaction_open:
            try:
                doc.abortTransaction()
            except Exception:
                pass
        raise


def _timber_marker_cross(point, size, z_value):
    """Return two plain edges so the caller can build one flat compound."""
    x, y = float(point[0]), float(point[1])
    half = 0.5 * float(size)
    return (
        Part.makeLine(App.Vector(x - half, y - half, z_value), App.Vector(x + half, y + half, z_value)),
        Part.makeLine(App.Vector(x - half, y + half, z_value), App.Vector(x + half, y - half, z_value)),
    )



def _timber_marker_outline(record, z_value):
    points = [App.Vector(float(point[0]), float(point[1]), z_value) for point in record.get("collision_polygon") or []]
    if len(points) < 3:
        return None
    points.append(points[0])
    return Part.makePolygon(points)


def _create_crossover_timber_analysis_display(doc, config, result):
    identifier = str(config.get("crossover_id") or "")
    set_id = str(config.get("template_set_id") or "")
    settings = normalise_crossover_timber_analysis_settings(result.get("settings"))
    thickness = float(config.get("template_thickness") or TEMPLATE_THICKNESS)
    z_value = thickness + CENTRELINE_LIFT + 0.12
    group = doc.addObject(
        "App::DocumentObjectGroup",
        unique_internal_name(doc, "RailwayCrossoverTimberAnalysis_{}".format(identifier.replace("-", "_"))),
    )
    group.Label = "{} Temporary Timber Analysis".format(identifier)
    tag_generated_object(group, CROSSOVER_TIMBER_ANALYSIS_GROUP_ROLE, set_id)
    _crossover_add_identity_properties(group, identifier, config)
    parent = _turnout_group_parent(doc, set_id)
    if parent is not None:
        parent.addObject(group)

    by_identity = {item["stable_identity"]: item for item in result.get("timbers") or []}
    if settings.get("show_support_markers"):
        support_shapes = []
        for record in result.get("timbers") or []:
            outline = _timber_marker_outline(record, z_value)
            if outline is not None:
                support_shapes.append(outline)
        if support_shapes:
            support_obj = doc.addObject(
                "Part::Feature",
                unique_internal_name(doc, "RailwayCrossoverProtectedSupports_{}".format(identifier.replace("-", "_"))),
            )
            support_obj.Label = "{} Protected Timber Support Zones".format(identifier)
            support_obj.Shape = Part.makeCompound(support_shapes)
            tag_generated_object(support_obj, CROSSOVER_TIMBER_SUPPORT_MARKER_ROLE, set_id)
            _crossover_add_identity_properties(support_obj, identifier, config)
            prop = ensure_property(support_obj, "App::PropertyString", "ProtectedSupportZonesJSON", "Timber analysis", "Protected support-zone identities and features")
            support_obj.ProtectedSupportZonesJSON = json.dumps([
                {"timber": item["stable_identity"], "features": item.get("protected_features") or []}
                for item in result.get("timbers") or []
            ], sort_keys=True)
            set_read_only(support_obj, [prop])
            group.addObject(support_obj)
            try:
                support_obj.ViewObject.LineColor = (0.20, 0.55, 0.95)
                support_obj.ViewObject.LineWidth = 1.5
            except Exception:
                pass

    if settings.get("show_conflict_markers"):
        grouped = {}
        for finding in result.get("findings") or []:
            severity = str(finding.get("severity") or "")
            if severity == CROSSOVER_TIMBER_SEVERITY_INFORMATION:
                continue
            grouped.setdefault(severity, []).append(finding)
        severity_order = (
            CROSSOVER_TIMBER_SEVERITY_PRODUCTION_CRITICAL,
            CROSSOVER_TIMBER_SEVERITY_PRODUCTION_CONFLICT,
            CROSSOVER_TIMBER_SEVERITY_ADVISORY,
        )
        for severity in severity_order:
            findings = grouped.get(severity) or []
            if not findings:
                continue
            shapes = []
            for finding in findings:
                point = finding.get("marker_point") or (0.0, 0.0)
                shapes.extend(_timber_marker_cross(point, 3.0, z_value + 0.02))
                first = by_identity.get(finding.get("timber_a"))
                second = by_identity.get(finding.get("timber_b"))
                if first is not None and second is not None:
                    shapes.append(Part.makeLine(
                        App.Vector(float(first["centre"][0]), float(first["centre"][1]), z_value + 0.02),
                        App.Vector(float(second["centre"][0]), float(second["centre"][1]), z_value + 0.02),
                    ))
            marker = doc.addObject(
                "Part::Feature",
                unique_internal_name(doc, "RailwayCrossoverTimberFindings_{}_{}".format(
                    _chair_slug(severity), identifier.replace("-", "_")
                )),
            )
            marker.Label = "{} {} timber findings ({})".format(identifier, severity, len(findings))
            marker.Shape = Part.makeCompound(shapes)
            tag_generated_object(marker, CROSSOVER_TIMBER_CONFLICT_MARKER_ROLE, set_id)
            _crossover_add_identity_properties(marker, identifier, config)
            props = [
                ensure_property(marker, "App::PropertyString", "TimberConflictSeverity", "Timber analysis", "Batched conflict severity"),
                ensure_property(marker, "App::PropertyInteger", "TimberConflictCount", "Timber analysis", "Number of findings in this display batch"),
                ensure_property(marker, "App::PropertyString", "TimberAnalysisFindingsJSON", "Timber analysis", "Complete batched finding records"),
            ]
            marker.TimberConflictSeverity = severity
            marker.TimberConflictCount = len(findings)
            marker.TimberAnalysisFindingsJSON = json.dumps(findings, sort_keys=True)
            set_read_only(marker, props)
            group.addObject(marker)
            try:
                if severity == CROSSOVER_TIMBER_SEVERITY_PRODUCTION_CRITICAL:
                    marker.ViewObject.LineColor = (1.0, 0.0, 0.0)
                    marker.ViewObject.LineWidth = 4.0
                elif severity == CROSSOVER_TIMBER_SEVERITY_PRODUCTION_CONFLICT:
                    marker.ViewObject.LineColor = (0.95, 0.25, 0.10)
                    marker.ViewObject.LineWidth = 3.0
                else:
                    marker.ViewObject.LineColor = (0.95, 0.65, 0.10)
                    marker.ViewObject.LineWidth = 2.0
            except Exception:
                pass
    return group


def _crossover_config_with_timber_analysis_metadata(config, result):
    """Build the exact persistent timber-analysis state without document writes."""
    updated = dict(config or {})
    status = str(result.get("analysis_status") or CROSSOVER_TIMBER_ANALYSIS_STATUS_NOT_ANALYSED)
    updated["timber_analysis_schema_version"] = CROSSOVER_TIMBER_ANALYSIS_SCHEMA_VERSION
    updated["timber_analysis_status"] = status
    updated["timber_analysis_signature"] = str(result.get("geometry_signature") or "")
    updated["timber_analysis_settings"] = normalise_crossover_timber_analysis_settings(result.get("settings"))
    updated["timber_analysis_summary"] = dict(result.get("statistics") or {})
    updated["timber_analysis_result_cached"] = True
    updated["production_ready"] = False
    statistics = dict(result.get("statistics") or {})
    b4_result = dict(updated.get("b4_result") or {})
    b4_complete = (
        str(updated.get("b4_status") or "") == CROSSOVER_B4_STATUS_CLEAR
        and bool(b4_result.get("timber_resolution_complete"))
        and int(b4_result.get("remaining_production_conflicts") or 0) == 0
        and int(b4_result.get("remaining_production_critical_conflicts") or 0) == 0
    )
    analysis_clear = (
        int(statistics.get("production_conflicts") or 0) == 0
        and int(statistics.get("production_critical_conflicts") or 0) == 0
    )
    integration_allowed = bool(updated.get("host_integration_allowed")) and b4_complete and analysis_clear
    updated["host_integration_allowed"] = integration_allowed
    if not updated.get("integration_active"):
        updated["integration_status"] = (
            CROSSOVER_INTEGRATION_STATUS_READY
            if integration_allowed
            else CROSSOVER_INTEGRATION_STATUS_NOT_INTEGRATED
        )
    updated["host_integration_reason"] = (
        "Automatic timbering is resolved and the current analysis is clear; reversible host integration is available"
        if integration_allowed
        else str(
            result.get("host_integration_reason")
            or updated.get("host_integration_reason")
            or "Complete automatic timber resolution and clear all production conflicts before host integration"
        )
    )
    return updated


def _write_crossover_timber_analysis_metadata(doc, config, result):
    updated = _crossover_config_with_timber_analysis_metadata(config, result)
    status = str(updated.get("timber_analysis_status") or CROSSOVER_TIMBER_ANALYSIS_STATUS_NOT_ANALYSED)
    identifier = str(updated.get("crossover_id") or "")
    settings_object = None
    configuration_json = json.dumps(updated, sort_keys=True)
    write_statistics = {}
    for obj in _crossover_objects(doc, identifier):
        role = object_string_property(obj, "GeneratedRole", "")
        if role == CROSSOVER_SETTINGS_ROLE:
            settings_object = obj
        _crossover_add_identity_properties(
            obj, identifier, updated,
            configuration_json=configuration_json,
            write_statistics=write_statistics,
        )
    if settings_object is None:
        raise ValueError("The crossover settings object is missing.")
    properties = [
        ensure_property(settings_object, "App::PropertyString", CROSSOVER_TIMBER_ANALYSIS_STATUS_PROPERTY, "Crossover timber analysis", "Read-only timber-analysis status"),
        ensure_property(settings_object, "App::PropertyString", CROSSOVER_TIMBER_ANALYSIS_SIGNATURE_PROPERTY, "Crossover timber analysis", "Stable geometry and tolerance signature"),
        ensure_property(settings_object, "App::PropertyString", CROSSOVER_TIMBER_ANALYSIS_SETTINGS_PROPERTY, "Crossover timber analysis", "Validated analyser tolerances and display settings"),
        ensure_property(settings_object, "App::PropertyString", CROSSOVER_TIMBER_ANALYSIS_RESULT_PROPERTY, "Crossover timber analysis", "Cached read-only timber analysis result"),
    ]
    _set_persistent_property_if_changed(settings_object, CROSSOVER_TIMBER_ANALYSIS_STATUS_PROPERTY, status, write_statistics)
    _set_persistent_property_if_changed(settings_object, CROSSOVER_TIMBER_ANALYSIS_SIGNATURE_PROPERTY, str(result.get("geometry_signature") or ""), write_statistics)
    _set_persistent_property_if_changed(settings_object, CROSSOVER_TIMBER_ANALYSIS_SETTINGS_PROPERTY, json.dumps(updated["timber_analysis_settings"], sort_keys=True), write_statistics)
    _set_persistent_property_if_changed(settings_object, CROSSOVER_TIMBER_ANALYSIS_RESULT_PROPERTY, json.dumps(result, sort_keys=True), write_statistics)
    set_read_only(settings_object, properties)
    _crossover_store_catalogue(doc, str(updated.get("template_set_id") or ""), write_statistics)
    return updated



def _write_crossover_b4_and_timber_analysis_metadata(doc, config, b4_result, analysis_result):
    """Persist final automatic timbering and analysis through one object pass.

    The builders above retain the exact B10 state transitions.  Only the
    redundant intermediate document writes, repeated full-config serialisation
    and duplicate catalogue update are removed.
    """
    timings = {}
    write_statistics = {
        "object_passes": 1,
        "configuration_serialisations": 1,
        "catalogue_updates": 1,
    }
    stage_start = time.perf_counter()
    updated = _crossover_config_with_b4_metadata(config, b4_result)
    updated = _crossover_config_with_timber_analysis_metadata(updated, analysis_result)
    timings["metadata_state_assembly"] = (time.perf_counter() - stage_start) * 1000.0

    stage_start = time.perf_counter()
    configuration_json = json.dumps(updated, sort_keys=True)
    b4_settings_json = json.dumps(updated["b4_settings"], sort_keys=True)
    b4_result_json = json.dumps(b4_result, sort_keys=True)
    analysis_settings_json = json.dumps(updated["timber_analysis_settings"], sort_keys=True)
    analysis_result_json = json.dumps(analysis_result, sort_keys=True)
    timings["metadata_payload_serialisation"] = (time.perf_counter() - stage_start) * 1000.0
    write_statistics["persistent_payload_serialisations"] = 5

    stage_start = time.perf_counter()
    identifier = str(updated.get("crossover_id") or "")
    settings_object = None
    crossover_objects = _crossover_objects(doc, identifier)
    write_statistics["crossover_objects_updated"] = len(crossover_objects)
    for obj in crossover_objects:
        if object_string_property(obj, "GeneratedRole", "") == CROSSOVER_SETTINGS_ROLE:
            settings_object = obj
        _crossover_add_identity_properties(
            obj, identifier, updated,
            configuration_json=configuration_json,
            write_statistics=write_statistics,
        )
    timings["metadata_identity_propagation"] = (time.perf_counter() - stage_start) * 1000.0
    if settings_object is None:
        raise ValueError("The crossover settings object is missing.")

    stage_start = time.perf_counter()
    properties = [
        ensure_property(settings_object, "App::PropertyString", CROSSOVER_B4_SETTINGS_PROPERTY, "Crossover automatic timbering", "Validated automatic timber-resolution settings"),
        ensure_property(settings_object, "App::PropertyString", CROSSOVER_B4_RESULT_PROPERTY, "Crossover automatic timbering", "Complete automatic timber-resolution result"),
        ensure_property(settings_object, "App::PropertyString", CROSSOVER_TIMBER_ANALYSIS_STATUS_PROPERTY, "Crossover timber analysis", "Read-only timber-analysis status"),
        ensure_property(settings_object, "App::PropertyString", CROSSOVER_TIMBER_ANALYSIS_SIGNATURE_PROPERTY, "Crossover timber analysis", "Stable geometry and tolerance signature"),
        ensure_property(settings_object, "App::PropertyString", CROSSOVER_TIMBER_ANALYSIS_SETTINGS_PROPERTY, "Crossover timber analysis", "Validated analyser tolerances and display settings"),
        ensure_property(settings_object, "App::PropertyString", CROSSOVER_TIMBER_ANALYSIS_RESULT_PROPERTY, "Crossover timber analysis", "Cached read-only timber analysis result"),
    ]
    _set_persistent_property_if_changed(settings_object, CROSSOVER_B4_SETTINGS_PROPERTY, b4_settings_json, write_statistics)
    _set_persistent_property_if_changed(settings_object, CROSSOVER_B4_RESULT_PROPERTY, b4_result_json, write_statistics)
    _set_persistent_property_if_changed(settings_object, CROSSOVER_TIMBER_ANALYSIS_STATUS_PROPERTY, str(updated.get("timber_analysis_status") or CROSSOVER_TIMBER_ANALYSIS_STATUS_NOT_ANALYSED), write_statistics)
    _set_persistent_property_if_changed(settings_object, CROSSOVER_TIMBER_ANALYSIS_SIGNATURE_PROPERTY, str(analysis_result.get("geometry_signature") or ""), write_statistics)
    _set_persistent_property_if_changed(settings_object, CROSSOVER_TIMBER_ANALYSIS_SETTINGS_PROPERTY, analysis_settings_json, write_statistics)
    _set_persistent_property_if_changed(settings_object, CROSSOVER_TIMBER_ANALYSIS_RESULT_PROPERTY, analysis_result_json, write_statistics)
    set_read_only(settings_object, properties)
    timings["metadata_settings_payload_update"] = (time.perf_counter() - stage_start) * 1000.0

    stage_start = time.perf_counter()
    _crossover_store_catalogue(
        doc, str(updated.get("template_set_id") or ""), write_statistics
    )
    timings["metadata_catalogue_update"] = (time.perf_counter() - stage_start) * 1000.0
    timings["metadata_combined_total"] = sum(timings.values())
    return updated, timings, write_statistics

def _cached_crossover_timber_analysis(doc, crossover_id):
    identifier = str(crossover_id or "").strip()
    for obj in _crossover_objects(doc, identifier):
        if object_string_property(obj, "GeneratedRole", "") != CROSSOVER_SETTINGS_ROLE:
            continue
        stored = object_string_property(obj, CROSSOVER_TIMBER_ANALYSIS_RESULT_PROPERTY, "")
        try:
            result = json.loads(stored)
        except Exception:
            result = None
        if isinstance(result, dict) and result.get("crossover_id") == identifier:
            return result
    return None


def crossover_timber_analysis_effective_status(doc, crossover_config):
    """Return the stored status, or Analysis stale when geometry/settings no longer match.

    This performs no document writes and creates no diagnostic geometry.
    """
    config = dict(crossover_config or {})
    stored_status = str(
        config.get("timber_analysis_status")
        or CROSSOVER_TIMBER_ANALYSIS_STATUS_NOT_ANALYSED
    )
    stored_signature = str(config.get("timber_analysis_signature") or "")
    if not stored_signature:
        return stored_status
    try:
        settings = normalise_crossover_timber_analysis_settings(
            config.get("timber_analysis_settings")
        )
        records = crossover_timber_records(doc, config)
        current_signature = _timber_geometry_signature(config, settings, records)
    except Exception:
        # A previously analysed crossover whose required hosts or timber metadata
        # can no longer be resolved must not continue to display a current status.
        return CROSSOVER_TIMBER_ANALYSIS_STATUS_STALE
    if current_signature != stored_signature:
        return CROSSOVER_TIMBER_ANALYSIS_STATUS_STALE
    return stored_status


def analyse_rea_c10_crossover_timbering(doc, crossover_id, settings=None):
    overall_start = time.perf_counter()
    timings = {}
    identifier = str(crossover_id or "").strip()
    config = crossover_config_by_id(doc, identifier)
    if config is None:
        raise ValueError("Crossover {} was not found.".format(identifier or "selection"))

    stage_start = time.perf_counter()
    settings = normalise_crossover_timber_analysis_settings(
        settings if settings is not None else config.get("timber_analysis_settings")
    )
    records = crossover_timber_records(doc, config)
    timings["record_extraction_and_settings"] = (time.perf_counter() - stage_start) * 1000.0

    stage_start = time.perf_counter()
    signature = _timber_geometry_signature(config, settings, records)
    cached = _cached_crossover_timber_analysis(doc, identifier) if settings.get("cache_enabled") else None
    timings["signature_and_cache_lookup"] = (time.perf_counter() - stage_start) * 1000.0

    stage_start = time.perf_counter()
    if cached is not None and str(cached.get("geometry_signature") or "") == signature:
        result = dict(cached)
        result["cache_reused"] = True
        result["settings"] = settings
    else:
        result = analyse_crossover_timber_records(config, records, settings)
        result["geometry_signature"] = signature
        result["cache_reused"] = False
    timings["timber_conflict_calculation"] = (time.perf_counter() - stage_start) * 1000.0
    if not result.get("cache_reused"):
        for key, value in (result.get("performance_timings_ms") or {}).items():
            timings["core_" + str(key)] = float(value)

    objects = _crossover_timber_analysis_objects(doc, identifier)
    present_roles = {object_string_property(obj, "GeneratedRole", "") for obj in objects}
    displayable_findings = [
        finding for finding in result.get("findings") or []
        if str(finding.get("severity") or "") != CROSSOVER_TIMBER_SEVERITY_INFORMATION
    ]
    expected_roles = set()
    if settings.get("show_conflict_markers") and displayable_findings:
        expected_roles.add(CROSSOVER_TIMBER_CONFLICT_MARKER_ROLE)
    if settings.get("show_support_markers") and result.get("timbers"):
        expected_roles.add(CROSSOVER_TIMBER_SUPPORT_MARKER_ROLE)
    display_current = expected_roles.issubset(present_roles)
    if expected_roles:
        display_current = display_current and CROSSOVER_TIMBER_ANALYSIS_GROUP_ROLE in present_roles
    if result.get("cache_reused") and display_current:
        stage_start = time.perf_counter()
        for obj in objects:
            role = object_string_property(obj, "GeneratedRole", "")
            try:
                if role == CROSSOVER_TIMBER_CONFLICT_MARKER_ROLE:
                    obj.ViewObject.Visibility = bool(settings.get("show_conflict_markers"))
                elif role == CROSSOVER_TIMBER_SUPPORT_MARKER_ROLE:
                    obj.ViewObject.Visibility = bool(settings.get("show_support_markers"))
            except Exception:
                pass
        timings["visibility_updates"] = (time.perf_counter() - stage_start) * 1000.0
        timings["metadata_updates"] = 0.0
        timings["diagnostic_display_construction"] = 0.0
        timings["document_recompute"] = 0.0
        timings["total"] = (time.perf_counter() - overall_start) * 1000.0
        result["display_cache_reused"] = True
        result["performance_timings_ms"] = timings
        return result

    transaction_open = False
    try:
        doc.openTransaction("Analyse Version {} crossover timbering {}".format(MACRO_VERSION_NUMBER, identifier))
        transaction_open = True

        stage_start = time.perf_counter()
        _remove_crossover_timber_analysis_objects(doc, identifier)
        updated_config = _write_crossover_timber_analysis_metadata(doc, config, result)
        timings["metadata_updates"] = (time.perf_counter() - stage_start) * 1000.0

        stage_start = time.perf_counter()
        _create_crossover_timber_analysis_display(doc, updated_config, result)
        timings["diagnostic_display_construction"] = (time.perf_counter() - stage_start) * 1000.0

        stage_start = time.perf_counter()
        _document_recompute(doc)
        timings["document_recompute"] = (time.perf_counter() - stage_start) * 1000.0

        stage_start = time.perf_counter()
        doc.commitTransaction()
        transaction_open = False
        timings["transaction_commit"] = (time.perf_counter() - stage_start) * 1000.0
    except Exception:
        if transaction_open:
            try:
                doc.abortTransaction()
            except Exception:
                pass
        raise
    timings["total"] = (time.perf_counter() - overall_start) * 1000.0
    result["display_cache_reused"] = False
    result["performance_timings_ms"] = timings
    return result



def set_crossover_timber_analysis_visibility(doc, crossover_id, conflicts=None, supports=None):
    identifier = str(crossover_id or "").strip()
    changed = 0
    for obj in _crossover_timber_analysis_objects(doc, identifier):
        role = object_string_property(obj, "GeneratedRole", "")
        visible = None
        if role == CROSSOVER_TIMBER_CONFLICT_MARKER_ROLE and conflicts is not None:
            visible = bool(conflicts)
        elif role == CROSSOVER_TIMBER_SUPPORT_MARKER_ROLE and supports is not None:
            visible = bool(supports)
        if visible is not None:
            try:
                obj.ViewObject.Visibility = visible
                changed += 1
            except Exception:
                pass
    return changed



# ---------------------------------------------------------------------------
# A8A7A/A8A7A1 chair-position and assignment framework.
#
# This stage is analytical and read-only regarding production geometry. It
# derives stable support records from the existing rail curves and final timber
# records, then creates only lightweight temporary diagnostic geometry.
# Detailed chair solids remain deliberately deferred to A8A7D.
# ---------------------------------------------------------------------------
CHAIR_ANALYSIS_SCHEMA_VERSION = 2
CHAIR_ANALYSIS_SETTINGS_PROPERTY = "ChairAnalysisSettingsJSON"
CHAIR_ANALYSIS_RESULT_PROPERTY = "ChairAnalysisResultJSON"
CHAIR_ANALYSIS_STATUS_PROPERTY = "ChairAnalysisStatus"
CHAIR_ANALYSIS_SIGNATURE_PROPERTY = "ChairAnalysisSignature"
CHAIR_ANALYSIS_GROUP_ROLE = "ChairAnalysisDisplay"
CHAIR_POSITION_MARKER_ROLE = "ChairPositionMarkers"
CHAIR_PROTECTED_MARKER_ROLE = "ChairProtectedPositionMarkers"
CHAIR_FOOTPRINT_MARKER_ROLE = "ChairFootprintMarkers"
CHAIR_STATUS_NOT_ANALYSED = "Not analysed"
CHAIR_STATUS_STALE = "Analysis stale"
CHAIR_STATUS_GENERATED = "Chair positions generated"
CHAIR_STATUS_INCOMPLETE = "Assignments incomplete"
CHAIR_STATUS_CONFLICTS = "Conflicts present"
CHAIR_STATUS_CRITICAL = "Production-critical conflicts"
CHAIR_STATUS_VALIDATED = "Chair positions validated"
CHAIR_SEVERITY_INFORMATION = "Informational"
CHAIR_SEVERITY_ADVISORY = "Advisory"
CHAIR_SEVERITY_CONFLICT = "Production conflict"
CHAIR_SEVERITY_CRITICAL = "Production-critical conflict"
CHAIR_FAMILY_ORDINARY = "ordinary running-rail chair"
CHAIR_FAMILY_SLIDE = "slide chair"
CHAIR_FAMILY_SWITCH = "switch-support chair"
CHAIR_FAMILY_SWITCH_HEEL = "switch-heel chair"
CHAIR_FAMILY_CLOSURE = "special closure-rail chair"
CHAIR_FAMILY_BRIDGE = "bridge chair"
CHAIR_FAMILY_CHECK = "check-rail chair"
CHAIR_FAMILY_WING = "wing-rail chair"
CHAIR_FAMILY_CROSSING = "common-crossing chair"
CHAIR_FAMILY_VEE = "vee support"
CHAIR_FAMILY_SPLICE = "splice-rail support"
CHAIR_FAMILY_KNUCKLE = "knuckle-region support"
CHAIR_FAMILY_NOSE = "crossing-nose support"
CHAIR_FAMILY_JOINT = "rail-joint support"
CHAIR_FAMILY_UNRESOLVED = "unresolved special chair"
CHAIR_FAMILY_OMITTED = "deliberately omitted chair position"
CHAIR_CLASS_SOURCE = "source-derived prototype requirement"
CHAIR_CLASS_INFERENCE = "documented railway-practice inference"
CHAIR_CLASS_ASSUMPTION = "configurable engineering assumption"
CHAIR_CLASS_APPROXIMATION = "temporary visual approximation"
CHAIR_CLASS_CONFIRM = "dimension requiring later confirmation"
CHAIR_ANALYSIS_SOURCE_BASIS = (
    "Templot5 revision 556b chairs_unit.pas T_2d_data and init_2d_rea chair code and base-dimension tables",
    "Templot5 revision 556b chairs_unit_x.pas draw_chairs_on_timber and REA chairing initialisation",
    "Templot5 revision 556b math_unit.pas drawtimber switch, bridge, check-rail and crossing-chair assignment",
    "Templot5 revision 556b switch_select.pas init_switch_data REA C-switch support counts and timber centres",
    "Templot5 revision 556b shove_timber.pas shoved, omitted and lengthened timber handling",
)


def default_chair_analysis_settings():
    """Return explicit model-scale assumptions used only by chair analysis."""
    return {
        "schema_version": CHAIR_ANALYSIS_SCHEMA_VERSION,
        "position_tolerance": 0.20,
        "footprint_clearance": 0.15,
        "timber_end_clearance": 0.50,
        "maximum_advisory_skew_degrees": 5.0,
        "maximum_unsupported_span": 15.0,
        "markers_visible": True,
        "protected_markers_visible": False,
        "footprints_visible": False,
        "cache_enabled": True,
        # Reserved for later solid stages. They are stored but not applied here.
        "future_chair_embed_depth": 0.20,
        "future_boolean_overlap_allowance": 0.05,
        "future_boolean_fuzzy_tolerance": 0.01,
    }


def normalise_chair_analysis_settings(settings=None):
    defaults = default_chair_analysis_settings()
    supplied = settings if isinstance(settings, dict) else {}
    result = dict(defaults)
    for key in (
        "position_tolerance", "footprint_clearance", "timber_end_clearance",
        "maximum_advisory_skew_degrees", "maximum_unsupported_span",
        "future_chair_embed_depth", "future_boolean_overlap_allowance",
        "future_boolean_fuzzy_tolerance",
    ):
        if key in supplied:
            try:
                result[key] = float(supplied[key])
            except Exception:
                raise ValueError("Chair setting {} must be numeric.".format(key.replace("_", " ")))
    limits = {
        "position_tolerance": (0.0, 5.0),
        "footprint_clearance": (0.0, 5.0),
        "timber_end_clearance": (0.0, 10.0),
        "maximum_advisory_skew_degrees": (0.0, 30.0),
        "maximum_unsupported_span": (1.0, 100.0),
        "future_chair_embed_depth": (0.0, 5.0),
        "future_boolean_overlap_allowance": (0.0, 2.0),
        "future_boolean_fuzzy_tolerance": (0.0, 1.0),
    }
    for key, bounds in limits.items():
        value = float(result[key])
        if not math.isfinite(value) or value < bounds[0] or value > bounds[1]:
            raise ValueError(
                "Chair setting {} must be between {:.3f} and {:.3f}.".format(
                    key.replace("_", " "), bounds[0], bounds[1]
                )
            )
    for key in ("markers_visible", "protected_markers_visible", "footprints_visible", "cache_enabled"):
        result[key] = bool(supplied.get(key, defaults[key]))
    result["schema_version"] = CHAIR_ANALYSIS_SCHEMA_VERSION
    return result


def _chair_slug(value):
    text = re.sub(r"[^a-z0-9]+", "-", str(value or "").lower()).strip("-")
    return text or "unnamed"


def _chair_xy(point):
    if hasattr(point, "x"):
        return float(point.x), float(point.y)
    return float(point[0]), float(point[1])


def _chair_vector(point):
    x, y = _chair_xy(point)
    return vector_xy(x, y)


def _chair_distance(a, b):
    ax, ay = _chair_xy(a)
    bx, by = _chair_xy(b)
    return math.hypot(bx - ax, by - ay)


def _chair_polyline_stations(points):
    stations = [0.0]
    for first, second in zip(points[:-1], points[1:]):
        stations.append(stations[-1] + _chair_distance(first, second))
    return stations


def _chair_interpolate_polyline(points, stations, target):
    if not points:
        raise ValueError("Cannot interpolate an empty chair rail path.")
    if len(points) == 1 or not stations or stations[-1] <= 1.0e-12:
        return _chair_xy(points[0])
    value = min(max(float(target), 0.0), float(stations[-1]))
    index = max(0, min(len(points) - 2, bisect.bisect_right(stations, value) - 1))
    span = stations[index + 1] - stations[index]
    fraction = 0.0 if span <= 1.0e-12 else (value - stations[index]) / span
    ax, ay = _chair_xy(points[index])
    bx, by = _chair_xy(points[index + 1])
    return ax + fraction * (bx - ax), ay + fraction * (by - ay)


def _chair_resample_midline(first_points, second_points):
    """Create a deterministic centre path between two logical rail faces."""
    if len(first_points) < 2 or len(second_points) < 2:
        raise ValueError("A rail face pair contains too few points for chair analysis.")
    first_stations = _chair_polyline_stations(first_points)
    second_stations = _chair_polyline_stations(second_points)
    count = max(2, len(first_points), len(second_points))
    result = []
    for index in range(count):
        fraction = index / float(count - 1)
        a = _chair_interpolate_polyline(first_points, first_stations, fraction * first_stations[-1])
        b = _chair_interpolate_polyline(second_points, second_stations, fraction * second_stations[-1])
        point = (0.5 * (a[0] + b[0]), 0.5 * (a[1] + b[1]))
        if not result or _chair_distance(result[-1], point) > 1.0e-8:
            result.append(point)
    return result


def _chair_rail_role(name):
    text = str(name or "").lower()
    if "check rail" in text:
        return "check rail"
    if "vee point" in text:
        return "vee point rail"
    if "vee splice" in text:
        return "vee splice rail"
    if "wing" in text and "knuckle" in text:
        return "wing rail knuckle"
    if "wing" in text:
        return "wing rail"
    if "straight switch" in text:
        return "straight switch and closure rail"
    if "curved switch" in text:
        return "curved switch and closure rail"
    if "stock rail" in text:
        return "stock rail"
    if "connector" in text:
        return "crossover connecting rail"
    return str(name or "running rail")


def _chair_supported_feature(name):
    text = str(name or "").lower()
    if "check rail" in text:
        return "check-rail support"
    if "vee point" in text:
        return "vee nose and point-rail support"
    if "vee splice" in text:
        return "vee splice-rail support"
    if "knuckle" in text:
        return "knuckle-region support"
    if "wing" in text:
        return "wing-rail support"
    if "switch and closure" in text:
        return "switch blade and closure-rail support"
    if "stock rail" in text:
        return "stock-rail support"
    if "connector" in text:
        return "plain crossover connecting-road support"
    return "running-rail support"


def _chair_turnout_rail_records(config, host_data=None, parent_crossover_id=None, side=""):
    cfg = dict(config or {})
    turnout_id = str(cfg.get("turnout_id") or "")
    if not turnout_id:
        raise ValueError("A chair rail source has no stable turnout identity.")
    if host_data is None:
        raise ValueError("A chair rail source has no host alignment data.")
    dimensions = rea_c10_dimensions(
        float(cfg.get("track_gauge", TURNOUT_DEFAULT_GAUGE)),
        float(cfg.get("flangeway", TURNOUT_DEFAULT_FLANGEWAY)),
    )
    named = dict(rea_c10_complete_rail_polylines(dimensions))
    records = []
    for gauge_name in sorted(name for name in named if name.endswith(" gauge face")):
        outer_name = gauge_name[:-len(" gauge face")] + " outer face"
        if outer_name not in named:
            continue
        base_name = gauge_name[:-len(" gauge face")]
        local_midline = _chair_resample_midline(named[gauge_name], named[outer_name])
        world_points = _turnout_map_polyline(
            host_data,
            float(cfg.get("toe_chainage") or 0.0),
            str(cfg.get("orientation") or TURNOUT_ORIENTATION_FACING),
            str(cfg.get("handing") or TURNOUT_HAND_LEFT),
            local_midline,
        )
        if len(world_points) < 2:
            continue
        rail_id = "{}:rail:{}".format(turnout_id, _chair_slug(base_name))
        records.append({
            "stable_identity": rail_id,
            "parent_turnout_identity": turnout_id,
            "parent_crossover_identity": str(parent_crossover_id or ""),
            "turnout_side": str(side or ""),
            "name": base_name,
            "rail_role": _chair_rail_role(base_name),
            "supported_feature": _chair_supported_feature(base_name),
            "points": [[float(point.x), float(point.y)] for point in world_points],
            "source_configuration": {
                "gauge_face": gauge_name,
                "outer_face": outer_name,
                "rail_geometry_revision": int(cfg.get("rail_geometry_revision") or TURNOUT_RAIL_GEOMETRY_REVISION),
            },
        })
    if not records:
        raise ValueError("No complete logical rail-face pairs were available for chair analysis.")
    return records


def _chair_connector_rail_records(doc, crossover_config):
    config = dict(crossover_config or {})
    identifier = str(config.get("crossover_id") or "")
    host_a = doc.getObject(str(config.get("host_a_object") or ""))
    host_b = doc.getObject(str(config.get("host_b_object") or ""))
    if host_a is None or host_b is None:
        return []
    solved = solve_rea_c10_crossover_geometry(
        doc,
        host_a,
        host_b,
        float(config.get("toe_chainage_a") or 0.0),
        arrangement=str(config.get("arrangement") or CROSSOVER_ARRANGEMENT_FACING),
        handing=str(config.get("handing") or CROSSOVER_HAND_AUTO),
        track_gauge=float(config.get("track_gauge", TURNOUT_DEFAULT_GAUGE)),
        flangeway=float(config.get("flangeway", TURNOUT_DEFAULT_FLANGEWAY)),
        minimum_radius=float(config.get("minimum_requested_radius") or CROSSOVER_DEFAULT_MINIMUM_RADIUS),
        ignored_crossover_id=identifier,
    )
    points = list(solved.get("connector", {}).get("points") or [])
    if len(points) < 2:
        return []
    gauge = float(config.get("track_gauge", TURNOUT_DEFAULT_GAUGE))
    records = []
    for label, offset in (("left connecting rail", 0.5 * gauge), ("right connecting rail", -0.5 * gauge)):
        offset_points = _crossover_offset_polyline(points, offset)
        records.append({
            "stable_identity": "{}:rail:{}".format(identifier, _chair_slug(label)),
            "parent_turnout_identity": "",
            "parent_crossover_identity": identifier,
            "turnout_side": "connector",
            "name": label,
            "rail_role": "crossover connecting rail",
            "supported_feature": "plain crossover connecting-road support",
            "points": [[float(point.x), float(point.y)] for point in offset_points],
            "source_configuration": {
                "source": "stored crossover geometry resolved analytically without rebuilding production shapes",
                "connector_geometry_signature": str(config.get("connector_geometry_signature") or ""),
            },
        })
    return records


def chair_rail_records_for_entity(doc, entity_kind, config):
    kind = str(entity_kind or "").lower()
    cfg = dict(config or {})
    if kind == "turnout":
        host = doc.getObject(str(cfg.get("host_object") or ""))
        if host is None:
            raise ValueError("The turnout host centreline is no longer available.")
        return _chair_turnout_rail_records(cfg, turnout_host_alignment(host))
    if kind == "crossover":
        identifier = str(cfg.get("crossover_id") or "")
        host_a = doc.getObject(str(cfg.get("host_a_object") or ""))
        host_b = doc.getObject(str(cfg.get("host_b_object") or ""))
        if host_a is None or host_b is None:
            raise ValueError("Both crossover host centrelines must remain available.")
        result = []
        for side, turnout_cfg, host in (
            ("A", dict(cfg.get("turnout_a_config") or {}), host_a),
            ("B", dict(cfg.get("turnout_b_config") or {}), host_b),
        ):
            result.extend(_chair_turnout_rail_records(
                turnout_cfg, turnout_host_alignment(host), parent_crossover_id=identifier, side=side
            ))
        result.extend(_chair_connector_rail_records(doc, cfg))
        return result
    raise ValueError("Chair analysis supports turnout or crossover entities.")


def _chair_turnout_timber_records(doc, config):
    cfg = dict(config or {})
    identifier = str(cfg.get("turnout_id") or "")
    host = doc.getObject(str(cfg.get("host_object") or ""))
    if host is None:
        raise ValueError("The turnout host centreline is no longer available.")
    host_data = turnout_host_alignment(host)
    dimensions = rea_c10_dimensions(
        float(cfg.get("track_gauge", TURNOUT_DEFAULT_GAUGE)),
        float(cfg.get("flangeway", TURNOUT_DEFAULT_FLANGEWAY)),
    )
    point, heading = interpolate_alignment_station(host_data, float(cfg.get("toe_chainage") or 0.0))
    if _turnout_orientation_sign(str(cfg.get("orientation") or TURNOUT_ORIENTATION_FACING)) < 0.0:
        heading += math.pi
    reference_axis = (math.cos(heading), math.sin(heading))
    origin = (float(point.x), float(point.y))
    layout = rea_c10_timber_layout(dimensions, float(cfg.get("template_width") or DEFAULT_MAIN_TEMPLATE_WIDTH))
    records = []
    for timber in layout:
        record = _timber_record_from_layout(
            identifier,
            "T",
            cfg,
            host_data,
            origin,
            reference_axis,
            timber,
        )
        record["stable_identity"] = "{}:timber:{}".format(identifier, timber["identifier"])
        record["parent_turnout_identity"] = identifier
        record["crossover_identity"] = ""
        record["turnout_side"] = ""
        records.append(record)
    records.sort(key=lambda item: (float(item.get("longitudinal_station") or 0.0), item["stable_identity"]))
    return records


def chair_timber_records_for_entity(doc, entity_kind, config):
    if str(entity_kind or "").lower() == "turnout":
        return _chair_turnout_timber_records(doc, config)
    if str(entity_kind or "").lower() == "crossover":
        return crossover_timber_records(doc, config)
    raise ValueError("Chair analysis supports turnout or crossover entities.")


def _chair_bbox_for_points(points, padding=0.0):
    xs = [float(point[0]) for point in points]
    ys = [float(point[1]) for point in points]
    return min(xs) - padding, min(ys) - padding, max(xs) + padding, max(ys) + padding


def _chair_bbox_overlap(first, second):
    return not (
        float(first[2]) < float(second[0]) or float(second[2]) < float(first[0])
        or float(first[3]) < float(second[1]) or float(second[3]) < float(first[1])
    )


def _chair_project_to_polyline(point, points):
    px, py = _chair_xy(point)
    best = None
    accumulated = 0.0
    for index, (first, second) in enumerate(zip(points[:-1], points[1:])):
        ax, ay = _chair_xy(first)
        bx, by = _chair_xy(second)
        dx, dy = bx - ax, by - ay
        length_sq = dx * dx + dy * dy
        if length_sq <= 1.0e-16:
            accumulated += math.sqrt(length_sq)
            continue
        fraction = min(1.0, max(0.0, ((px - ax) * dx + (py - ay) * dy) / length_sq))
        qx, qy = ax + fraction * dx, ay + fraction * dy
        distance = math.hypot(px - qx, py - qy)
        length = math.sqrt(length_sq)
        tangent = (dx / length, dy / length)
        candidate = (distance, accumulated + fraction * length, (qx, qy), tangent, index)
        if best is None or candidate[:2] < best[:2]:
            best = candidate
        accumulated += length
    return best

def _chair_prepare_polyline_projection(points):
    """Pre-index one rail polyline for exact repeated projections."""
    raw_points = list(points or [])
    segments = []
    segment_lengths = []
    accumulated = 0.0
    for index, (first, second) in enumerate(zip(raw_points[:-1], raw_points[1:])):
        ax, ay = _chair_xy(first)
        bx, by = _chair_xy(second)
        dx, dy = bx - ax, by - ay
        length_sq = dx * dx + dy * dy
        length = math.sqrt(length_sq)
        if length_sq <= 1.0e-16:
            accumulated += length
            continue
        segments.append({
            "index": index,
            "ax": ax,
            "ay": ay,
            "dx": dx,
            "dy": dy,
            "length_sq": length_sq,
            "length": length,
            "station_start": accumulated,
            "bbox": (min(ax, bx), min(ay, by), max(ax, bx), max(ay, by)),
        })
        segment_lengths.append(length)
        accumulated += length
    if not segments:
        return {
            "points": raw_points,
            "segments": [],
            "bins": {},
            "cell_size": 20.0,
            "total_length": accumulated,
            "bounding_box": _chair_bbox_for_points(raw_points, 0.0) if raw_points else (0.0, 0.0, 0.0, 0.0),
            "projection_blocks": [],
        }
    sorted_lengths = sorted(segment_lengths)
    median_length = sorted_lengths[len(sorted_lengths) // 2]
    cell_size = max(8.0, min(30.0, median_length * 16.0))
    bins = {}
    for segment_index, segment in enumerate(segments):
        bbox = segment["bbox"]
        x0 = int(math.floor(bbox[0] / cell_size))
        x1 = int(math.floor(bbox[2] / cell_size))
        y0 = int(math.floor(bbox[1] / cell_size))
        y1 = int(math.floor(bbox[3] / cell_size))
        for cell_x in range(x0, x1 + 1):
            for cell_y in range(y0, y1 + 1):
                bins.setdefault((cell_x, cell_y), []).append(segment_index)
    block_size = 16
    blocks = []
    for start in range(0, len(segments), block_size):
        finish = min(len(segments), start + block_size)
        chunk = segments[start:finish]
        blocks.append({
            "start": start,
            "finish": finish,
            "bbox": (
                min(item["bbox"][0] for item in chunk),
                min(item["bbox"][1] for item in chunk),
                max(item["bbox"][2] for item in chunk),
                max(item["bbox"][3] for item in chunk),
            ),
        })
    return {
        "points": raw_points,
        "segments": segments,
        "bins": bins,
        "cell_size": cell_size,
        "total_length": accumulated,
        "bounding_box": _chair_bbox_for_points(raw_points, 0.0),
        "projection_blocks": blocks,
    }



def _chair_projection_candidate_indices(prepared, query_bbox):
    segments = list((prepared or {}).get("segments") or [])
    if not segments:
        return []
    if query_bbox is None:
        return list(range(len(segments)))
    cell_size = max(1.0e-9, float((prepared or {}).get("cell_size") or 20.0))
    x0 = int(math.floor(float(query_bbox[0]) / cell_size))
    x1 = int(math.floor(float(query_bbox[2]) / cell_size))
    y0 = int(math.floor(float(query_bbox[1]) / cell_size))
    y1 = int(math.floor(float(query_bbox[3]) / cell_size))
    values = set()
    bins = dict((prepared or {}).get("bins") or {})
    for cell_x in range(x0, x1 + 1):
        for cell_y in range(y0, y1 + 1):
            values.update(bins.get((cell_x, cell_y), []))
    return sorted(values) if values else list(range(len(segments)))


def _chair_project_to_prepared_polyline(point, prepared, query_bbox=None):
    """Project exactly, using either the existing local bins or exact blocks."""
    px, py = _chair_xy(point)
    segments = list((prepared or {}).get("segments") or [])
    if not segments:
        return None

    if query_bbox is not None:
        groups = [(0.0, _chair_projection_candidate_indices(prepared, query_bbox))]
    else:
        groups = []
        for block_index, block in enumerate((prepared or {}).get("projection_blocks") or []):
            bbox = block["bbox"]
            dx = 0.0 if bbox[0] <= px <= bbox[2] else (bbox[0] - px if px < bbox[0] else px - bbox[2])
            dy = 0.0 if bbox[1] <= py <= bbox[3] else (bbox[1] - py if py < bbox[1] else py - bbox[3])
            groups.append((dx * dx + dy * dy, block_index, list(range(int(block["start"]), int(block["finish"])))))
        if groups:
            groups.sort(key=lambda item: (item[0], item[1]))
            groups = [(item[0], item[2]) for item in groups]
        else:
            groups = [(0.0, list(range(len(segments))))]

    best = None
    best_segment_index = None
    for lower_bound_sq, prepared_indices in groups:
        if best is not None and query_bbox is None:
            best_sq = float(best[0]) * float(best[0])
            if lower_bound_sq > best_sq + max(1.0e-18, best_sq * 1.0e-15):
                break
        for prepared_index in prepared_indices:
            segment = segments[prepared_index]
            dx = float(segment["dx"])
            dy = float(segment["dy"])
            length_sq = float(segment["length_sq"])
            fraction = min(1.0, max(0.0, (
                (px - float(segment["ax"])) * dx + (py - float(segment["ay"])) * dy
            ) / length_sq))
            qx = float(segment["ax"]) + fraction * dx
            qy = float(segment["ay"]) + fraction * dy
            distance = math.hypot(px - qx, py - qy)
            length = float(segment["length"])
            segment_index = int(segment["index"])
            candidate = (
                distance,
                float(segment["station_start"]) + fraction * length,
                (qx, qy),
                (dx / length, dy / length),
                segment_index,
            )
            if (
                best is None
                or (candidate[0], candidate[1], segment_index)
                < (best[0], best[1], best_segment_index)
            ):
                best = candidate
                best_segment_index = segment_index
    return best




def _chair_point_near_polygon(point, polygon, tolerance):
    if _timber_point_in_convex_polygon(point, polygon, tolerance=max(1.0e-9, float(tolerance))):
        return True
    px, py = _chair_xy(point)
    for first, second in zip(polygon, polygon[1:] + polygon[:1]):
        projected = _chair_project_to_polyline((px, py), [first, second])
        if projected is not None and projected[0] <= float(tolerance) + 1.0e-9:
            return True
    return False


def _chair_base_dimensions(family, subtype=""):
    """Return model footprint dimensions and their provenance.

    Templot dimensions are prototype inches converted with the macro's fixed
    OO scale. Crossing/block-chair dimensions not fully established by the
    inspected source remain explicit temporary envelopes.
    """
    inch = (25.4 / TURNOUT_DEFAULT_SCALE)
    if family == CHAIR_FAMILY_ORDINARY:
        return 14.5 * inch, 8.0 * inch, CHAIR_CLASS_SOURCE, "REA S1"
    if family == CHAIR_FAMILY_JOINT:
        return 14.5 * inch, 10.0 * inch, CHAIR_CLASS_SOURCE, "REA S1J"
    if family == CHAIR_FAMILY_BRIDGE:
        return 10.5 * inch, 11.0 * inch, CHAIR_CLASS_SOURCE, "REA L1"
    if family in (CHAIR_FAMILY_SLIDE, CHAIR_FAMILY_SWITCH):
        return 18.0 * inch, 8.0 * inch, CHAIR_CLASS_SOURCE, "REA P/PLR support envelope"
    if family == CHAIR_FAMILY_CHECK:
        return 19.75 * inch, 8.0 * inch, CHAIR_CLASS_SOURCE, "REA check-rail chair base"
    if family == CHAIR_FAMILY_OMITTED:
        return 0.0, 0.0, CHAIR_CLASS_SOURCE, "support shared with adjacent slide/block chair"
    if family in (
        CHAIR_FAMILY_SWITCH_HEEL, CHAIR_FAMILY_CLOSURE, CHAIR_FAMILY_WING,
        CHAIR_FAMILY_CROSSING, CHAIR_FAMILY_VEE, CHAIR_FAMILY_SPLICE,
        CHAIR_FAMILY_KNUCKLE, CHAIR_FAMILY_NOSE, CHAIR_FAMILY_UNRESOLVED,
    ):
        return 14.5 * inch, 10.5 * inch, CHAIR_CLASS_APPROXIMATION, "analytical conflict envelope only; final base dimension requires confirmation"
    return 14.5 * inch, 8.0 * inch, CHAIR_CLASS_ASSUMPTION, "ordinary analytical envelope"



def _chair_requirement_route_matches(requirement, rail, support=None):
    """Return True when a resolved-timber requirement belongs to this rail route.

    Shared and extended crossover timbers retain per-route support requirements.
    Those requirements must not be applied indiscriminately to every rail which
    crosses the final long timber.
    """
    requirement = dict(requirement or {})
    rail_side = str((rail or {}).get("turnout_side") or "").strip().lower()
    route_kind = str(requirement.get("route_kind") or "").strip().lower()
    route_identity = str(
        requirement.get("route_identity")
        or requirement.get("source_timber_identity")
        or ""
    ).strip().lower()

    if rail_side in ("a", "b"):
        if route_kind in ("a", "b", "connector") and route_kind != rail_side:
            return False
        if not route_kind and route_identity:
            other = "b" if rail_side == "a" else "a"
            if ":{}:".format(other) in route_identity and ":{}:".format(rail_side) not in route_identity:
                return False
    elif rail_side == "connector":
        if route_kind in ("a", "b"):
            return False
    elif route_kind == "connector":
        return False

    zone = list(requirement.get("zone_polygon") or [])
    if support is not None and len(zone) >= 3:
        # Requirement zones are inherited source-support areas. A modest
        # analytical tolerance avoids rejecting a route solely at a shared edge.
        if not _chair_point_near_polygon(support, zone, 0.50):
            return False
    return True


def _chair_feature_applies_to_rail(feature, rail_role):
    text = str(feature or "").strip().lower()
    role = str(rail_role or "").strip().lower()
    if not text:
        return False
    if "future " in text or text in ("shared crossover timber envelope",):
        return False
    if text in ("turnout rail support", "rail support"):
        return True
    if role == "check rail":
        return "check" in text or "common-crossing" in text or "common crossing" in text
    if role in ("wing rail", "wing rail knuckle"):
        return any(token in text for token in ("wing", "knuckle", "common-crossing", "common crossing"))
    if role == "vee point rail":
        return any(token in text for token in ("vee", "crossing nose", "common-crossing", "common crossing", "joint"))
    if role == "vee splice rail":
        return any(token in text for token in ("splice", "vee", "crossing nose", "common-crossing", "common crossing", "joint"))
    if role == "stock rail":
        return any(token in text for token in (
            "stock-rail", "stock rail", "slide", "switch blade", "switch toe",
            "switch heel", "rail joint", "rail-joint", "common-crossing", "common crossing",
        ))
    if "switch and closure" in role:
        return any(token in text for token in (
            "switch", "closure", "rail joint", "rail-joint", "common-crossing", "common crossing",
        ))
    if role == "crossover connecting rail":
        return "connector" in text or "plain-track" in text or "plain track" in text
    return any(token in text for token in ("running", "rail joint", "rail-joint", "plain"))


def _chair_applicable_timber_features(timber, rail, support=None):
    """Return only protected features applicable to the current route and rail."""
    requirements = [dict(item) for item in (timber.get("support_requirements") or []) if isinstance(item, dict)]
    raw = []
    if requirements:
        matched = [item for item in requirements if _chair_requirement_route_matches(item, rail, support)]
        for requirement in matched:
            raw.extend(str(value) for value in requirement.get("features") or [])
        # A final connector sleeper may omit route_kind in its single stored
        # requirement. Its timber identity still provides an unambiguous route.
        if not raw and str((rail or {}).get("turnout_side") or "").lower() == "connector" and str(timber.get("turnout_side") or "").lower() == "connector":
            raw.extend(str(value) for value in timber.get("protected_features") or [])
    else:
        raw.extend(str(value) for value in timber.get("protected_features") or [])

    role = str((rail or {}).get("rail_role") or "")
    return sorted(set(feature for feature in raw if _chair_feature_applies_to_rail(feature, role)))


def _chair_assignment(timber, rail, support=None):
    identifier = str(timber.get("identifier") or timber.get("prototype_reference") or "")
    section = str(timber.get("section") or "").lower()
    role = str(rail.get("rail_role") or "").lower()
    digits = re.search(r"([0-9]+)", identifier)
    number = int(digits.group(1)) if digits else 0
    family = CHAIR_FAMILY_ORDINARY
    subtype = "REA S1"
    classification = CHAIR_CLASS_SOURCE
    protected = []
    mandatory = False
    deliberate_omission = False

    if identifier in ("J1", "J2", "R1"):
        family, subtype, mandatory = CHAIR_FAMILY_JOINT, "REA S1J rail-joint support", True
        protected.append("rail joint")
    if role == "check rail":
        family, subtype, mandatory = CHAIR_FAMILY_CHECK, "REA check-rail support", True
        protected.append("check rail")
    elif role == "wing rail knuckle":
        family, subtype, mandatory = CHAIR_FAMILY_KNUCKLE, "REA knuckle-region special support", True
        protected.extend(["wing rail", "knuckle region"])
    elif role == "wing rail":
        family, subtype, mandatory = CHAIR_FAMILY_WING, "REA wing-rail special support", True
        protected.append("wing rail")
    elif role == "vee point rail":
        family, subtype, mandatory = CHAIR_FAMILY_VEE, "REA vee point-rail support", True
        protected.extend(["vee nose", "crossing nose"])
    elif role == "vee splice rail":
        family, subtype, mandatory = CHAIR_FAMILY_SPLICE, "REA vee splice-rail support", True
        protected.append("splice rail")
    elif identifier.startswith("X"):
        suffix = str(timber.get("source_configuration", {}).get("crossing_suffix") or "")
        family = CHAIR_FAMILY_CROSSING
        subtype_map = {
            "Z": "REA ZY crossing chair region",
            "Y": "REA XN crossing chair region",
            "X": "REA XA crossing chair region",
            "A": "REA AA crossing-nose chair region",
            "B": "REA AB/BB vee and splice support region",
            "C": "REA BB/BC vee support region",
            "D": "REA CD vee support region",
            "E": "REA EF vee support region",
            "F": "REA EF exit support region",
        }
        subtype = subtype_map.get(suffix, "REA crossing special chair requiring final subtype resolution")
        mandatory = True
        protected.append("common crossing {} timber".format(suffix or identifier))
        if suffix == "A":
            family = CHAIR_FAMILY_NOSE
            protected.append("crossing nose")
        elif suffix in ("B", "C", "D", "E", "F") and role in ("vee point rail", "vee splice rail"):
            family = CHAIR_FAMILY_VEE if role == "vee point rail" else CHAIR_FAMILY_SPLICE
    elif identifier.startswith("S") and number:
        if 1 <= number <= 7:
            if role == "stock rail":
                family, subtype, mandatory = CHAIR_FAMILY_SLIDE, "REA P slide chair", True
                protected.extend(["slide-chair position", "switch blade support"])
                if number == 1:
                    protected.append("switch toe")
            elif "switch and closure" in role:
                family, subtype = CHAIR_FAMILY_OMITTED, "switch blade supported by adjacent slide-chair table"
                deliberate_omission = True
                protected.append("switch blade support shared with stock-rail slide chair")
        elif 8 <= number <= 9:
            if role == "stock rail":
                family, subtype, mandatory = CHAIR_FAMILY_SWITCH, "REA PLR block-slide support", True
                protected.append("switch blade support")
            elif "switch and closure" in role:
                family, subtype = CHAIR_FAMILY_OMITTED, "switch blade supported by block-slide chair"
                deliberate_omission = True
        elif 10 <= number <= 12:
            family, subtype, mandatory = CHAIR_FAMILY_SWITCH_HEEL, "REA PLR block-heel support", True
            protected.append("switch heel")
        elif number >= 13 and "switch and closure" in role:
            family, subtype, mandatory = CHAIR_FAMILY_CLOSURE, "closure-rail special support", True
            protected.append("closure rail")
    elif identifier.startswith("T") and "switch and closure" in role:
        family = CHAIR_FAMILY_CLOSURE
        subtype = "closure-rail support"
        mandatory = True
        protected.append("closure rail")
    elif section == "closure" and role == "stock rail":
        family = CHAIR_FAMILY_BRIDGE
        subtype = "REA L1 bridge chair where ordinary bases cannot fit"
        classification = CHAIR_CLASS_INFERENCE
    elif role == "crossover connecting rail":
        family, subtype, classification = CHAIR_FAMILY_ORDINARY, "plain connecting-road S1", CHAIR_CLASS_INFERENCE

    inherited_features = _chair_applicable_timber_features(timber, rail, support)
    if inherited_features:
        for feature in inherited_features:
            if feature not in protected:
                protected.append(feature)
        feature_text = " ".join(inherited_features).lower()
        mandatory = mandatory or any(
            token in feature_text
            for token in ("switch", "crossing", "wing", "check", "vee", "joint", "splice", "knuckle")
        )
        # Resolved crossover timbers have new stable identities. Recover only
        # the applicable functional assignment for this rail and route.
        if family == CHAIR_FAMILY_ORDINARY and role == "stock rail" and any(token in feature_text for token in ("slide", "switch blade", "switch toe")):
            family, subtype, classification = CHAIR_FAMILY_SLIDE, "REA P/PLR slide support inherited through resolved timbering", CHAIR_CLASS_INFERENCE
        elif family == CHAIR_FAMILY_ORDINARY and "switch heel" in feature_text:
            family, subtype, classification = CHAIR_FAMILY_SWITCH_HEEL, "REA block-heel support inherited through resolved timbering", CHAIR_CLASS_INFERENCE
        elif family == CHAIR_FAMILY_ORDINARY and ("rail joint" in feature_text or "rail-joint" in feature_text):
            family, subtype, classification = CHAIR_FAMILY_JOINT, "REA joint support inherited through resolved timbering", CHAIR_CLASS_INFERENCE
        elif family == CHAIR_FAMILY_ORDINARY and ("common crossing" in feature_text or "common-crossing" in feature_text):
            family, subtype, classification = CHAIR_FAMILY_CROSSING, "common-crossing support inherited through resolved timbering", CHAIR_CLASS_INFERENCE
        elif family == CHAIR_FAMILY_ORDINARY and "closure" in feature_text and "switch and closure" in role:
            family, subtype, classification = CHAIR_FAMILY_CLOSURE, "closure support inherited through resolved timbering", CHAIR_CLASS_INFERENCE

    crossing_suffix = str(timber.get("source_configuration", {}).get("crossing_suffix") or "")
    if crossing_suffix == "A" and role in ("vee point rail", "vee splice rail", "stock rail", "straight switch and closure rail", "curved switch and closure rail"):
        family, subtype, mandatory = CHAIR_FAMILY_NOSE, "REA AA crossing-nose support region", True
        if "crossing nose" not in protected:
            protected.append("crossing nose")
    if family in (
        CHAIR_FAMILY_SWITCH_HEEL, CHAIR_FAMILY_CLOSURE, CHAIR_FAMILY_WING,
        CHAIR_FAMILY_CROSSING, CHAIR_FAMILY_VEE, CHAIR_FAMILY_SPLICE,
        CHAIR_FAMILY_KNUCKLE, CHAIR_FAMILY_NOSE,
    ) and "final subtype" in subtype:
        family = CHAIR_FAMILY_UNRESOLVED

    length, width, dimension_class, dimension_note = _chair_base_dimensions(family, subtype)
    if classification == CHAIR_CLASS_SOURCE and dimension_class != CHAIR_CLASS_SOURCE:
        classification = dimension_class
    return {
        "chair_family": family,
        "chair_subtype": subtype,
        "classification": classification,
        "mandatory": mandatory,
        "deliberate_omission": deliberate_omission,
        "protected_features": protected,
        "footprint_length": length,
        "footprint_width": width,
        "footprint_dimension_classification": dimension_class,
        "footprint_dimension_note": dimension_note,
    }


def _chair_orientation_metadata(config, rail, assignment):
    family = str(assignment.get("chair_family") or "")
    if family in (CHAIR_FAMILY_ORDINARY, CHAIR_FAMILY_JOINT, CHAIR_FAMILY_BRIDGE, CHAIR_FAMILY_OMITTED):
        handedness = "not applicable"
    else:
        handedness = str((config or {}).get("handing") or "not applicable")
    if family == CHAIR_FAMILY_OMITTED:
        key_orientation = "not applicable"
        key_classification = CHAIR_CLASS_SOURCE
    else:
        # Templot resolves key direction from template-side and joint context.
        # A8A7A records that dependency without inventing the final solid hand.
        key_orientation = "requires confirmation from rail side, joint context and final chair subtype"
        key_classification = CHAIR_CLASS_CONFIRM
    rail_source = dict((rail or {}).get("source_configuration") or {})
    gauge_face = str(rail_source.get("gauge_face") or "")
    outer_face = str(rail_source.get("outer_face") or "")
    rail_foot_orientation = (
        "seat orientation derived from named gauge face '{}' and outer face '{}'".format(gauge_face, outer_face)
        if gauge_face and outer_face
        else "derived from stable logical rail tangent; detailed foot seat requires later solid confirmation"
    )
    return {
        "handedness": handedness,
        "handedness_classification": CHAIR_CLASS_SOURCE if handedness != "not applicable" else CHAIR_CLASS_INFERENCE,
        "key_orientation": key_orientation,
        "key_orientation_classification": key_classification,
        "rail_foot_orientation": rail_foot_orientation,
        "rail_foot_orientation_classification": CHAIR_CLASS_SOURCE if gauge_face and outer_face else CHAIR_CLASS_CONFIRM,
    }


def _chair_support_zone(timber, support, tangent, rail_station, settings, protected):
    polygon = list(timber.get("outline_polygon") or timber.get("collision_polygon") or [])
    if not protected or len(polygon) < 3:
        return None
    sx, sy = _chair_xy(support)
    tx, ty = float(tangent[0]), float(tangent[1])
    offsets = [(_chair_xy(point)[0] - sx) * tx + (_chair_xy(point)[1] - sy) * ty for point in polygon]
    if not offsets:
        return None
    tolerance = float(settings.get("position_tolerance") or 0.0)
    return {
        "type": "allowable rail-station interval within the effective timber outline",
        "centre_station": float(rail_station),
        "minimum_station": float(rail_station + min(offsets) - tolerance),
        "maximum_station": float(rail_station + max(offsets) + tolerance),
        "position_tolerance": tolerance,
        "classification": CHAIR_CLASS_INFERENCE,
    }



def _chair_footprint_polygon(centre, timber, length, width):
    cx, cy = _chair_xy(centre)
    long_axis = tuple(float(value) for value in timber.get("length_axis", (0.0, 1.0)))
    width_axis = tuple(float(value) for value in timber.get("width_axis", (1.0, 0.0)))
    half_length = 0.5 * max(0.0, float(length))
    half_width = 0.5 * max(0.0, float(width))
    return [
        [cx - half_length * long_axis[0] - half_width * width_axis[0], cy - half_length * long_axis[1] - half_width * width_axis[1]],
        [cx + half_length * long_axis[0] - half_width * width_axis[0], cy + half_length * long_axis[1] - half_width * width_axis[1]],
        [cx + half_length * long_axis[0] + half_width * width_axis[0], cy + half_length * long_axis[1] + half_width * width_axis[1]],
        [cx - half_length * long_axis[0] + half_width * width_axis[0], cy - half_length * long_axis[1] + half_width * width_axis[1]],
    ]


def _chair_footprint_fit_measurements(footprint, timber):
    """Measure footprint fit separately at timber ends and timber sides."""
    polygon = list(footprint or [])
    if not polygon:
        return None
    centre = _chair_xy(timber.get("centre") or (0.0, 0.0))
    length_axis = tuple(float(value) for value in timber.get("length_axis", (0.0, 1.0)))
    width_axis = tuple(float(value) for value in timber.get("width_axis", (1.0, 0.0)))
    length_values = []
    width_values = []
    for point in polygon:
        px, py = _chair_xy(point)
        dx, dy = px - centre[0], py - centre[1]
        length_values.append(dx * length_axis[0] + dy * length_axis[1])
        width_values.append(dx * width_axis[0] + dy * width_axis[1])
    half_length = 0.5 * float(timber.get("length") or 0.0)
    half_width = 0.5 * float(timber.get("width") or 0.0)
    end_clearance = min(min(length_values) + half_length, half_length - max(length_values))
    side_clearance = min(min(width_values) + half_width, half_width - max(width_values))
    return {
        "end_clearance": float(end_clearance),
        "side_clearance": float(side_clearance),
        "end_overhang": max(0.0, -float(end_clearance)),
        "side_overhang": max(0.0, -float(side_clearance)),
    }


def _chair_position_identity(entity_id, timber_id, rail_id):
    return "{}:chair:{}:{}".format(entity_id, _chair_slug(timber_id), _chair_slug(rail_id.split(":rail:")[-1]))


def generate_chair_positions(entity_kind, config, rail_records, timber_records, settings=None):
    settings = normalise_chair_analysis_settings(settings)
    entity_id = str(config.get("turnout_id") or config.get("crossover_id") or "")
    if not entity_id:
        raise ValueError("Chair analysis requires a stable turnout or crossover identity.")
    positions = []
    rail_supports = {rail["stable_identity"]: [] for rail in rail_records}
    padding = float(settings["position_tolerance"])
    for timber in timber_records:
        polygon = list(timber.get("outline_polygon") or timber.get("collision_polygon") or [])
        if len(polygon) < 3:
            continue
        timber_bbox = _chair_bbox_for_points(polygon, padding)
        centre = timber.get("centre") or _timber_polygon_centroid(polygon)
        timber_id = str(timber.get("stable_identity") or timber.get("identifier") or "")
        for rail in rail_records:
            points = list(rail.get("points") or [])
            if len(points) < 2 or not _chair_bbox_overlap(timber_bbox, _chair_bbox_for_points(points, padding)):
                continue
            projected = _chair_project_to_polyline(centre, points)
            if projected is None:
                continue
            distance, rail_station, support, tangent, _segment_index = projected
            if not _chair_point_near_polygon(support, polygon, padding):
                continue
            assignment = _chair_assignment(timber, rail, support)
            footprint = _chair_footprint_polygon(
                support, timber, assignment["footprint_length"], assignment["footprint_width"]
            ) if not assignment["deliberate_omission"] else []
            timber_axis = tuple(float(value) for value in timber.get("width_axis", (1.0, 0.0)))
            dot = max(-1.0, min(1.0, abs(tangent[0] * timber_axis[0] + tangent[1] * timber_axis[1])))
            skew = math.degrees(math.acos(dot))
            position_id = _chair_position_identity(entity_id, timber_id, rail["stable_identity"])
            orientation_metadata = _chair_orientation_metadata(config, rail, assignment)
            support_zone = _chair_support_zone(
                timber, support, tangent, rail_station, settings,
                assignment["mandatory"] or assignment["deliberate_omission"],
            )
            record = {
                "stable_chair_position_identity": position_id,
                "parent_template_set_identity": str(config.get("template_set_id") or ""),
                "parent_turnout_identity": str(rail.get("parent_turnout_identity") or ""),
                "parent_crossover_identity": str(rail.get("parent_crossover_identity") or ""),
                "timber_identity": timber_id,
                "timber_identifier": str(timber.get("identifier") or timber.get("prototype_reference") or ""),
                "rail_identity": str(rail.get("stable_identity") or ""),
                "rail_name": str(rail.get("name") or ""),
                "rail_role": str(rail.get("rail_role") or ""),
                "supported_feature": str(rail.get("supported_feature") or ""),
                "centre_point": [float(support[0]), float(support[1])],
                "rail_station": float(rail_station),
                "local_rail_tangent": [float(tangent[0]), float(tangent[1])],
                "timber_centre": [float(centre[0]), float(centre[1])],
                "timber_angle_radians": float(timber.get("angle_radians") or 0.0),
                "timber_angle_degrees": float(timber.get("angle_degrees") or 0.0),
                "local_support_direction": [float(timber.get("length_axis", [0.0, 1.0])[0]), float(timber.get("length_axis", [0.0, 1.0])[1])],
                "chair_family": assignment["chair_family"],
                "chair_subtype": assignment["chair_subtype"],
                "handedness": orientation_metadata["handedness"],
                "handedness_classification": orientation_metadata["handedness_classification"],
                "key_orientation": orientation_metadata["key_orientation"],
                "key_orientation_classification": orientation_metadata["key_orientation_classification"],
                "rail_foot_orientation": orientation_metadata["rail_foot_orientation"],
                "rail_foot_orientation_classification": orientation_metadata["rail_foot_orientation_classification"],
                "protected_support_classification": "mandatory" if assignment["mandatory"] else ("deliberately omitted" if assignment["deliberate_omission"] else "ordinary"),
                "protected_features": list(assignment["protected_features"]),
                "protected_support_zone": support_zone,
                "source_configuration": {
                    "rail": dict(rail.get("source_configuration") or {}),
                    "timber": dict(timber.get("source_configuration") or {}),
                },
                "chair_footprint_parameters": {
                    "length": float(assignment["footprint_length"]),
                    "width": float(assignment["footprint_width"]),
                    "clearance": float(settings["footprint_clearance"]),
                    "polygon": footprint,
                    "dimension_classification": assignment["footprint_dimension_classification"],
                    "dimension_note": assignment["footprint_dimension_note"],
                },
                "future_solid_generation_parameters": {
                    "embed_depth": float(settings["future_chair_embed_depth"]),
                    "boolean_overlap_allowance": float(settings["future_boolean_overlap_allowance"]),
                    "boolean_fuzzy_tolerance": float(settings["future_boolean_fuzzy_tolerance"]),
                    "active_in_this_stage": False,
                },
                "source_or_assumed_classification": assignment["classification"],
                "validation_status": "not yet validated",
                "stale_signature_state": False,
                "mandatory": bool(assignment["mandatory"]),
                "deliberate_omission": bool(assignment["deliberate_omission"]),
                "chair_skew_degrees": float(skew),
                "distance_from_timber_centre": float(distance),
            }
            positions.append(record)
            rail_supports[rail["stable_identity"]].append(record)
    positions.sort(key=lambda item: (
        item["timber_identity"], item["rail_identity"], item["stable_chair_position_identity"]
    ))
    identities = [item["stable_chair_position_identity"] for item in positions]
    if len(identities) != len(set(identities)):
        raise ValueError("Chair-position generation produced duplicate stable identities.")
    return positions, rail_supports


def _chair_finding(code, severity, message, chair_ids=None, timber_ids=None, rail_ids=None):
    return {
        "code": str(code),
        "severity": str(severity),
        "message": str(message),
        "chair_position_identities": list(chair_ids or []),
        "timber_identities": list(timber_ids or []),
        "rail_identities": list(rail_ids or []),
    }




def _chair_rail_side_label(position):
    text = str((position or {}).get("rail_name") or "").strip().lower().replace("-", " ")
    if "main side" in text:
        return "main side"
    if "turnout side" in text:
        return "turnout side"
    return ""


def _chair_shared_functional_base(first, second):
    """Recognise rail components intentionally carried by one functional chair base."""
    if str(first.get("timber_identity") or "") != str(second.get("timber_identity") or ""):
        return False
    roles = {str(first.get("rail_role") or "").lower(), str(second.get("rail_role") or "").lower()}
    if roles == {"stock rail", "check rail"}:
        first_side = _chair_rail_side_label(first)
        second_side = _chair_rail_side_label(second)
        return bool(first_side and first_side == second_side)
    return False

def _chair_spatial_pairs(positions, padding=0.0):
    candidates = []
    indexed = []
    for index, item in enumerate(positions):
        polygon = list(item.get("chair_footprint_parameters", {}).get("polygon") or [])
        if len(polygon) < 3:
            continue
        bbox = _chair_bbox_for_points(polygon, padding)
        indexed.append((index, bbox))
    if len(indexed) < 2:
        return []
    widths = sorted(max(1.0, bbox[2] - bbox[0], bbox[3] - bbox[1]) for _index, bbox in indexed)
    cell = max(2.0, widths[len(widths) // 2])
    bins = {}
    for index, bbox in indexed:
        x0 = int(math.floor(bbox[0] / cell)); x1 = int(math.floor(bbox[2] / cell))
        y0 = int(math.floor(bbox[1] / cell)); y1 = int(math.floor(bbox[3] / cell))
        for x in range(x0, x1 + 1):
            for y in range(y0, y1 + 1):
                bins.setdefault((x, y), []).append(index)
    seen = set()
    for values in bins.values():
        for first_index, first in enumerate(values):
            for second in values[first_index + 1:]:
                pair = tuple(sorted((first, second)))
                if pair not in seen:
                    seen.add(pair); candidates.append(pair)
    return candidates


def validate_chair_positions(config, rail_records, timber_records, positions, rail_supports, settings=None):
    settings = normalise_chair_analysis_settings(settings)
    findings = []
    by_identity = {}
    for item in positions:
        identity = item["stable_chair_position_identity"]
        if identity in by_identity:
            findings.append(_chair_finding(
                "DUPLICATE_CHAIR_IDENTITY", CHAIR_SEVERITY_CRITICAL,
                "Duplicate chair-position identity {}.".format(identity), [identity]
            ))
        by_identity[identity] = item
    seen_assignment = set()
    timber_by_id = {str(item.get("stable_identity") or ""): item for item in timber_records}
    rail_by_id = {str(item.get("stable_identity") or ""): item for item in rail_records}
    prepared_rail_by_id = {
        rail_id: _chair_prepare_polyline_projection(list(rail.get("points") or []))
        for rail_id, rail in rail_by_id.items()
    }
    for item in positions:
        key = (item["timber_identity"], item["rail_identity"])
        if key in seen_assignment:
            findings.append(_chair_finding(
                "DUPLICATE_CHAIR_ASSIGNMENT", CHAIR_SEVERITY_CONFLICT,
                "More than one chair assignment supports rail {} on timber {}.".format(key[1], key[0]),
                [item["stable_chair_position_identity"]], [key[0]], [key[1]],
            ))
        seen_assignment.add(key)
        rail = rail_by_id.get(item["rail_identity"])
        if rail is None:
            findings.append(_chair_finding(
                "WRONG_OR_MISSING_RAIL", CHAIR_SEVERITY_CRITICAL,
                "Chair {} refers to a missing rail.".format(item["stable_chair_position_identity"]),
                [item["stable_chair_position_identity"]], [item["timber_identity"]], [item["rail_identity"]],
            ))
        else:
            assigned_projection = _chair_project_to_prepared_polyline(
                item.get("centre_point") or (0.0, 0.0), prepared_rail_by_id.get(item["rail_identity"]), None
            )
            if assigned_projection is None or float(assigned_projection[0]) > float(settings["position_tolerance"]) + 1.0e-9:
                findings.append(_chair_finding(
                    "CHAIR_CENTRE_NOT_ON_ASSIGNED_RAIL", CHAIR_SEVERITY_CRITICAL,
                    "Chair {} centre does not lie on its assigned stable rail within tolerance.".format(item["stable_chair_position_identity"]),
                    [item["stable_chair_position_identity"]], [item["timber_identity"]], [item["rail_identity"]],
                ))
        valid_hands = (TURNOUT_HAND_LEFT, TURNOUT_HAND_RIGHT, "not applicable", "")
        if str(item.get("handedness") or "") not in valid_hands:
            findings.append(_chair_finding(
                "INVALID_CHAIR_HANDEDNESS", CHAIR_SEVERITY_CONFLICT,
                "Chair {} has invalid handedness {}.".format(item["stable_chair_position_identity"], item.get("handedness")),
                [item["stable_chair_position_identity"]], [item["timber_identity"]], [item["rail_identity"]],
            ))
        key_orientation = str(item.get("key_orientation") or "").lower()
        if not key_orientation or key_orientation in ("invalid", "unknown"):
            findings.append(_chair_finding(
                "INVALID_KEY_ORIENTATION", CHAIR_SEVERITY_CONFLICT,
                "Chair {} has no valid key orientation.".format(item["stable_chair_position_identity"]),
                [item["stable_chair_position_identity"]], [item["timber_identity"]], [item["rail_identity"]],
            ))
        elif "requires confirmation" in key_orientation:
            findings.append(_chair_finding(
                "KEY_ORIENTATION_REQUIRES_CONFIRMATION", CHAIR_SEVERITY_ADVISORY,
                "Chair {} key orientation remains explicitly deferred to subtype and rail-side confirmation.".format(item["stable_chair_position_identity"]),
                [item["stable_chair_position_identity"]], [item["timber_identity"]], [item["rail_identity"]],
            ))
        if item.get("mandatory") and not isinstance(item.get("protected_support_zone"), dict):
            findings.append(_chair_finding(
                "PROTECTED_SUPPORT_ZONE_MISSING", CHAIR_SEVERITY_CRITICAL,
                "Mandatory support {} has no allowable support interval.".format(item["stable_chair_position_identity"]),
                [item["stable_chair_position_identity"]], [item["timber_identity"]], [item["rail_identity"]],
            ))
        timber = timber_by_id.get(item["timber_identity"])
        if timber is None:
            findings.append(_chair_finding(
                "WRONG_OR_MISSING_TIMBER", CHAIR_SEVERITY_CRITICAL,
                "Chair {} refers to a missing timber.".format(item["stable_chair_position_identity"]),
                [item["stable_chair_position_identity"]], [item["timber_identity"]], [item["rail_identity"]],
            ))
            continue
        outline = list(timber.get("outline_polygon") or timber.get("collision_polygon") or [])
        centre = item["centre_point"]
        if outline and not _chair_point_near_polygon(centre, outline, settings["position_tolerance"]):
            findings.append(_chair_finding(
                "CHAIR_CENTRE_OUTSIDE_TIMBER", CHAIR_SEVERITY_CRITICAL,
                "Chair centre {} lies outside timber {}.".format(item["stable_chair_position_identity"], item["timber_identity"]),
                [item["stable_chair_position_identity"]], [item["timber_identity"]], [item["rail_identity"]],
            ))
        footprint_parameters = dict(item.get("chair_footprint_parameters") or {})
        footprint = list(footprint_parameters.get("polygon") or [])
        if footprint and outline:
            fit = _chair_footprint_fit_measurements(footprint, timber)
            if fit is not None:
                dimension_class = str(footprint_parameters.get("dimension_classification") or "")
                end_clearance = float(fit["end_clearance"])
                if end_clearance < float(settings["timber_end_clearance"]) - 1.0e-9:
                    confirmed = dimension_class == CHAIR_CLASS_SOURCE
                    severity = (
                        CHAIR_SEVERITY_CONFLICT
                        if confirmed and item.get("mandatory") and end_clearance < -float(settings["position_tolerance"])
                        else CHAIR_SEVERITY_ADVISORY
                    )
                    findings.append(_chair_finding(
                        "TIMBER_END_CLEARANCE", severity,
                        "Chair {} has {:.3f} mm timber-end clearance; {:.3f} mm is configured. Footprint provenance: {}.".format(
                            item["stable_chair_position_identity"], end_clearance,
                            settings["timber_end_clearance"], dimension_class or "not recorded"
                        ),
                        [item["stable_chair_position_identity"]], [item["timber_identity"]], [item["rail_identity"]],
                    ))

                chair_width = float(footprint_parameters.get("width") or 0.0)
                timber_width = float(timber.get("width") or 0.0)
                inherent_half_overhang = 0.5 * max(0.0, chair_width - timber_width)
                permitted_side_overhang = (
                    inherent_half_overhang
                    + float(settings["position_tolerance"])
                    + float(settings["footprint_clearance"])
                )
                side_overhang = float(fit["side_overhang"])
                if side_overhang > permitted_side_overhang + 1.0e-9:
                    findings.append(_chair_finding(
                        "CHAIR_FOOTPRINT_SIDE_OVERHANG", CHAIR_SEVERITY_ADVISORY,
                        "Chair {} analytically overhangs a timber side by {:.3f} mm; {:.3f} mm is allowed for the recorded base width and analysis tolerances. Final solid fit remains staged for A8A7D/A8A7E.".format(
                            item["stable_chair_position_identity"], side_overhang, permitted_side_overhang
                        ),
                        [item["stable_chair_position_identity"]], [item["timber_identity"]], [item["rail_identity"]],
                    ))
        if float(item.get("chair_skew_degrees") or 0.0) > float(settings["maximum_advisory_skew_degrees"]) + 1.0e-9:
            findings.append(_chair_finding(
                "EXCESSIVE_CHAIR_SKEW", CHAIR_SEVERITY_ADVISORY,
                "Chair {} is skewed {:.3f} degrees relative to its timber.".format(
                    item["stable_chair_position_identity"], item["chair_skew_degrees"]
                ),
                [item["stable_chair_position_identity"]], [item["timber_identity"]], [item["rail_identity"]],
            ))
        if item["chair_family"] == CHAIR_FAMILY_UNRESOLVED:
            findings.append(_chair_finding(
                "UNRESOLVED_SPECIAL_CHAIR", CHAIR_SEVERITY_CONFLICT,
                "Chair {} requires a confirmed special-chair subtype.".format(item["stable_chair_position_identity"]),
                [item["stable_chair_position_identity"]], [item["timber_identity"]], [item["rail_identity"]],
            ))
        if item.get("mandatory") and item["chair_family"] in (CHAIR_FAMILY_ORDINARY, CHAIR_FAMILY_UNRESOLVED):
            findings.append(_chair_finding(
                "PROTECTED_POSITION_ASSIGNMENT_INCOMPLETE", CHAIR_SEVERITY_CRITICAL,
                "Protected support {} does not yet have a complete functional chair assignment.".format(item["stable_chair_position_identity"]),
                [item["stable_chair_position_identity"]], [item["timber_identity"]], [item["rail_identity"]],
            ))

    positions_by_timber = {}
    for item in positions:
        positions_by_timber.setdefault(item.get("timber_identity"), []).append(item)
    for timber in timber_records:
        features = [str(value) for value in timber.get("protected_features") or []]
        feature_text = " ".join(features).lower()
        requires_mandatory = any(token in feature_text for token in ("switch", "crossing", "wing", "check", "vee", "joint", "splice", "knuckle"))
        if not requires_mandatory:
            continue
        timber_id = str(timber.get("stable_identity") or timber.get("identifier") or "")
        supported = [item for item in positions_by_timber.get(timber_id, []) if item.get("mandatory") or item.get("deliberate_omission")]
        if not supported:
            findings.append(_chair_finding(
                "PROTECTED_TIMBER_WITHOUT_MANDATORY_CHAIR", CHAIR_SEVERITY_CRITICAL,
                "Protected timber {} has no mandatory or deliberately shared support assignment.".format(timber_id),
                timber_ids=[timber_id],
            ))

    for rail in rail_records:
        supports = sorted(rail_supports.get(rail["stable_identity"], []), key=lambda item: float(item["rail_station"]))
        if not supports:
            findings.append(_chair_finding(
                "RAIL_WITHOUT_TIMBER_SUPPORT", CHAIR_SEVERITY_CRITICAL,
                "Rail {} has no timber-supported chair positions.".format(rail["stable_identity"]),
                rail_ids=[rail["stable_identity"]],
            ))
            continue
        for before, after in zip(supports[:-1], supports[1:]):
            gap = float(after["rail_station"]) - float(before["rail_station"])
            if gap > float(settings["maximum_unsupported_span"]):
                findings.append(_chair_finding(
                    "EXCESSIVE_UNSUPPORTED_RAIL_SPAN", CHAIR_SEVERITY_CONFLICT,
                    "Rail {} has {:.3f} mm between adjacent supports {} and {}.".format(
                        rail["stable_identity"], gap,
                        before["stable_chair_position_identity"], after["stable_chair_position_identity"],
                    ),
                    [before["stable_chair_position_identity"], after["stable_chair_position_identity"]],
                    [before["timber_identity"], after["timber_identity"]], [rail["stable_identity"]],
                ))

    for first_index, second_index in _chair_spatial_pairs(positions, settings["footprint_clearance"]):
        first = positions[first_index]; second = positions[second_index]
        if first.get("deliberate_omission") or second.get("deliberate_omission"):
            continue
        if first["stable_chair_position_identity"] == second["stable_chair_position_identity"]:
            continue
        # Paired components of one special support can share a functional base.
        if _chair_shared_functional_base(first, second):
            continue
        if first["timber_identity"] == second["timber_identity"] and set(first.get("protected_features") or []) & set(second.get("protected_features") or []):
            continue
        polygon_a = first.get("chair_footprint_parameters", {}).get("polygon") or []
        polygon_b = second.get("chair_footprint_parameters", {}).get("polygon") or []
        if not polygon_a or not polygon_b or not _chair_bbox_overlap(_chair_bbox_for_points(polygon_a), _chair_bbox_for_points(polygon_b)):
            continue
        overlap_polygon = _timber_convex_intersection(polygon_a, polygon_b)
        overlap_area = abs(_timber_polygon_area(overlap_polygon)) if len(overlap_polygon) >= 3 else 0.0
        if overlap_area <= float(settings["position_tolerance"]) ** 2:
            continue
        first_class = str(first.get("chair_footprint_parameters", {}).get("dimension_classification") or "")
        second_class = str(second.get("chair_footprint_parameters", {}).get("dimension_classification") or "")
        confirmed_pair = first_class == CHAIR_CLASS_SOURCE and second_class == CHAIR_CLASS_SOURCE
        severity = CHAIR_SEVERITY_CONFLICT if confirmed_pair else CHAIR_SEVERITY_ADVISORY
        code = "CHAIR_INTERFERENCE_ADJACENT_RAILS" if first["rail_identity"] != second["rail_identity"] else "OVERLAPPING_CHAIR_FOOTPRINTS"
        findings.append(_chair_finding(
            code, severity,
            "Chair footprints {} and {} overlap by {:.3f} square mm. Footprint provenance: {} / {}.".format(
                first["stable_chair_position_identity"], second["stable_chair_position_identity"], overlap_area,
                first_class or "not recorded", second_class or "not recorded"
            ),
            [first["stable_chair_position_identity"], second["stable_chair_position_identity"]],
            [first["timber_identity"], second["timber_identity"]],
            [first["rail_identity"], second["rail_identity"]],
        ))

    severity_order = {
        CHAIR_SEVERITY_INFORMATION: 0,
        CHAIR_SEVERITY_ADVISORY: 1,
        CHAIR_SEVERITY_CONFLICT: 2,
        CHAIR_SEVERITY_CRITICAL: 3,
    }
    findings.sort(key=lambda item: (-severity_order.get(item["severity"], 0), item["code"], item["message"]))
    counts = {name: 0 for name in severity_order}
    for finding in findings:
        counts[finding["severity"]] = counts.get(finding["severity"], 0) + 1
    maximum_severity_by_chair = {}
    for finding in findings:
        rank = severity_order.get(finding["severity"], 0)
        for identity in finding.get("chair_position_identities", []) or []:
            current = maximum_severity_by_chair.get(identity)
            if current is None or rank > current[0]:
                maximum_severity_by_chair[identity] = (rank, finding["severity"])
    for item in positions:
        status = maximum_severity_by_chair.get(item["stable_chair_position_identity"])
        item["validation_status"] = status[1] if status is not None else "validated"
    return findings, counts


def _chair_geometry_signature(entity_kind, config, settings, rail_records, timber_records):
    """Return the stable chair-calculation signature, excluding display-only controls."""
    calculation_settings = normalise_chair_analysis_settings(settings)
    for key in (
        "markers_visible", "protected_markers_visible", "footprints_visible",
        "physical_solids_visible", "unresolved_markers_visible", "cache_enabled",
    ):
        calculation_settings.pop(key, None)
    payload = {
        "schema_version": CHAIR_ANALYSIS_SCHEMA_VERSION,
        "entity_kind": str(entity_kind),
        "entity_id": str(config.get("turnout_id") or config.get("crossover_id") or ""),
        "settings": calculation_settings,
        "rails": [{
            "id": item["stable_identity"],
            "points": [[round(float(value), 5) for value in point] for point in item.get("points", [])],
            "role": item.get("rail_role"),
        } for item in rail_records],
        "timbers": [{
            "id": item.get("stable_identity"),
            "centre": [round(float(value), 5) for value in item.get("centre", [])],
            "angle": round(float(item.get("angle_radians") or 0.0), 8),
            "width": round(float(item.get("width") or 0.0), 5),
            "length": round(float(item.get("length") or 0.0), 5),
            "outline": [[round(float(value), 5) for value in point] for point in item.get("outline_polygon", [])],
        } for item in timber_records],
    }
    return hashlib.sha256(json.dumps(payload, sort_keys=True, separators=(",", ":")).encode("utf-8")).hexdigest()


def _chair_status_from_counts(position_count, positions, counts):
    if counts.get(CHAIR_SEVERITY_CRITICAL, 0):
        return CHAIR_STATUS_CRITICAL
    if counts.get(CHAIR_SEVERITY_CONFLICT, 0):
        return CHAIR_STATUS_CONFLICTS
    if any(item.get("chair_family") == CHAIR_FAMILY_UNRESOLVED for item in positions):
        return CHAIR_STATUS_INCOMPLETE
    if position_count:
        return CHAIR_STATUS_VALIDATED
    return CHAIR_STATUS_INCOMPLETE


def analyse_chair_position_records(entity_kind, config, rail_records, timber_records, settings=None):
    settings = normalise_chair_analysis_settings(settings)
    positions, rail_supports = generate_chair_positions(entity_kind, config, rail_records, timber_records, settings)
    findings, counts = validate_chair_positions(config, rail_records, timber_records, positions, rail_supports, settings)
    status = _chair_status_from_counts(len(positions), positions, counts)
    families = {}
    for item in positions:
        families[item["chair_family"]] = families.get(item["chair_family"], 0) + 1
    return {
        "schema_version": CHAIR_ANALYSIS_SCHEMA_VERSION,
        "macro_version": MACRO_VERSION_NUMBER,
        "entity_kind": str(entity_kind),
        "entity_id": str(config.get("turnout_id") or config.get("crossover_id") or ""),
        "status": status,
        "settings": settings,
        "source_basis": list(CHAIR_ANALYSIS_SOURCE_BASIS),
        "positions": positions,
        "findings": findings,
        "summary": {
            "rail_count": len(rail_records),
            "timber_count": len(timber_records),
            "chair_position_count": len(positions),
            "family_counts": families,
            "severity_counts": counts,
            "deliberately_omitted_count": sum(1 for item in positions if item.get("deliberate_omission")),
            "mandatory_position_count": sum(1 for item in positions if item.get("mandatory")),
        },
        "cache_reused": False,
        "production_geometry_changed": False,
        "chair_solids_generated": False,
    }


def _chair_entity_objects(doc, entity_kind, entity_id):
    if str(entity_kind).lower() == "turnout":
        property_name = TURNOUT_ID_PROPERTY
    else:
        property_name = CROSSOVER_ID_PROPERTY
    return [obj for obj in list(doc.Objects) if object_string_property(obj, property_name, "") == str(entity_id)]


def _chair_settings_object(doc, entity_kind, entity_id):
    target_role = TURNOUT_SETTINGS_ROLE if str(entity_kind).lower() == "turnout" else CROSSOVER_SETTINGS_ROLE
    for obj in _chair_entity_objects(doc, entity_kind, entity_id):
        if object_string_property(obj, "GeneratedRole", "") == target_role:
            return obj
    return None


def _chair_read_cached_result(doc, entity_kind, entity_id):
    obj = _chair_settings_object(doc, entity_kind, entity_id)
    if obj is None:
        return None
    try:
        value = json.loads(object_string_property(obj, CHAIR_ANALYSIS_RESULT_PROPERTY, ""))
    except Exception:
        value = None
    return value if isinstance(value, dict) else None


def _chair_write_metadata(doc, entity_kind, config, result):
    kind = str(entity_kind).lower()
    updated = dict(config or {})
    updated["chair_analysis_status"] = str(result.get("status") or CHAIR_STATUS_NOT_ANALYSED)
    updated["chair_analysis_signature"] = str(result.get("geometry_signature") or "")
    updated["chair_analysis_settings"] = normalise_chair_analysis_settings(result.get("settings"))
    updated["chair_analysis_summary"] = dict(result.get("summary") or {})
    updated["chair_analysis_schema_version"] = CHAIR_ANALYSIS_SCHEMA_VERSION
    updated["chair_solids_complete"] = False
    updated["chair_final_validation_complete"] = False
    updated["production_ready"] = False
    entity_id = str(updated.get("turnout_id") or updated.get("crossover_id") or "")
    settings_obj = _chair_settings_object(doc, kind, entity_id)
    if settings_obj is None:
        raise ValueError("The {} settings object is missing.".format(kind))
    properties = [
        ensure_property(settings_obj, "App::PropertyString", CHAIR_ANALYSIS_STATUS_PROPERTY, "Chair analysis", "Current logical chair-position analysis status"),
        ensure_property(settings_obj, "App::PropertyString", CHAIR_ANALYSIS_SIGNATURE_PROPERTY, "Chair analysis", "Stable rail, timber and tolerance signature"),
        ensure_property(settings_obj, "App::PropertyString", CHAIR_ANALYSIS_SETTINGS_PROPERTY, "Chair analysis", "Validated analytical chair settings"),
        ensure_property(settings_obj, "App::PropertyString", CHAIR_ANALYSIS_RESULT_PROPERTY, "Chair analysis", "Cached logical chair-position and validation result"),
    ]
    setattr(settings_obj, CHAIR_ANALYSIS_STATUS_PROPERTY, updated["chair_analysis_status"])
    setattr(settings_obj, CHAIR_ANALYSIS_SIGNATURE_PROPERTY, updated["chair_analysis_signature"])
    setattr(settings_obj, CHAIR_ANALYSIS_SETTINGS_PROPERTY, json.dumps(updated["chair_analysis_settings"], sort_keys=True))
    setattr(settings_obj, CHAIR_ANALYSIS_RESULT_PROPERTY, json.dumps(result, sort_keys=True))
    set_read_only(settings_obj, properties)
    for obj in _chair_entity_objects(doc, kind, entity_id):
        if kind == "turnout":
            _turnout_add_identity_properties(obj, entity_id, updated)
        else:
            _crossover_add_identity_properties(obj, entity_id, updated)
    if kind == "turnout":
        _turnout_store_catalogue(doc, str(updated.get("template_set_id") or ""))
    else:
        _crossover_store_catalogue(doc, str(updated.get("template_set_id") or ""))
    return updated


def _chair_analysis_display_objects(doc, entity_kind, entity_id):
    return [
        obj for obj in _chair_entity_objects(doc, entity_kind, entity_id)
        if object_string_property(obj, "GeneratedRole", "") in (
            CHAIR_ANALYSIS_GROUP_ROLE, CHAIR_POSITION_MARKER_ROLE,
            CHAIR_PROTECTED_MARKER_ROLE, CHAIR_FOOTPRINT_MARKER_ROLE,
        )
    ]


def clear_chair_analysis_display(doc, entity_kind, entity_id):
    removed = 0
    objects = _chair_analysis_display_objects(doc, entity_kind, entity_id)
    # Remove children before their group to avoid FreeCAD ownership surprises.
    objects.sort(key=lambda obj: object_string_property(obj, "GeneratedRole", "") == CHAIR_ANALYSIS_GROUP_ROLE)
    for obj in objects:
        try:
            doc.removeObject(str(obj.Name)); removed += 1
        except Exception:
            pass
    return removed


def invalidate_chair_analysis(doc, entity_kind, entity_id, remove_display=True):
    if remove_display:
        clear_chair_analysis_display(doc, entity_kind, entity_id)
    config = turnout_config_by_id(doc, entity_id) if str(entity_kind).lower() == "turnout" else crossover_config_by_id(doc, entity_id)
    if not isinstance(config, dict) or not config.get("chair_analysis_signature"):
        return config
    updated = dict(config)
    updated["chair_analysis_status"] = CHAIR_STATUS_STALE
    updated["production_ready"] = False
    for obj in _chair_entity_objects(doc, entity_kind, entity_id):
        if str(entity_kind).lower() == "turnout":
            _turnout_add_identity_properties(obj, entity_id, updated)
        else:
            _crossover_add_identity_properties(obj, entity_id, updated)
    return updated


def _chair_cross_wires(point, tangent, half_size=0.55, z_height=0.12):
    px, py = _chair_xy(point)
    tx, ty = float(tangent[0]), float(tangent[1])
    normal = (-ty, tx)
    first = _turnout_wire([vector_xy(px - half_size * tx, py - half_size * ty), vector_xy(px + half_size * tx, py + half_size * ty)], z_height)
    second = _turnout_wire([vector_xy(px - half_size * normal[0], py - half_size * normal[1]), vector_xy(px + half_size * normal[0], py + half_size * normal[1])], z_height)
    return first, second



def _chair_make_display_feature(doc, group, entity_kind, entity_id, set_id, role, label, shapes, visible=True):
    if not shapes:
        return None
    shape = _turnout_compound(shapes, label)
    obj = doc.addObject("Part::Feature", unique_internal_name(doc, "{}_{}".format(role, entity_id.replace("-", "_"))))
    obj.Label = label
    obj.Shape = shape
    tag_generated_object(obj, role, set_id)
    if str(entity_kind).lower() == "turnout":
        prop = ensure_property(obj, "App::PropertyString", TURNOUT_ID_PROPERTY, "Chair analysis", "Parent turnout identity")
    else:
        prop = ensure_property(obj, "App::PropertyString", CROSSOVER_ID_PROPERTY, "Chair analysis", "Parent crossover identity")
    setattr(obj, TURNOUT_ID_PROPERTY if str(entity_kind).lower() == "turnout" else CROSSOVER_ID_PROPERTY, str(entity_id))
    set_read_only(obj, [prop])
    group.addObject(obj)
    try:
        obj.ViewObject.Visibility = bool(visible)
        obj.ViewObject.LineWidth = 2.4 if role in (CHAIR_POSITION_MARKER_ROLE, CHAIR_PROTECTED_MARKER_ROLE) else 1.4
    except Exception:
        pass
    return obj



def _chair_display_z_levels(doc, entity_kind, config):
    """Return diagnostic Z levels above the actual inherited template surface."""
    values = []
    try:
        configured = float((config or {}).get("template_thickness") or 0.0)
        if configured > 0.0:
            values.append(configured)
    except Exception:
        pass
    entity_id = str((config or {}).get("turnout_id") or (config or {}).get("crossover_id") or "")
    for obj in _chair_entity_objects(doc, entity_kind, entity_id):
        try:
            value = quantity_value(obj, "TemplateThickness", 0.0)
            if value > 0.0:
                values.append(float(value))
        except Exception:
            pass
    top = max(values) if values else float(TEMPLATE_THICKNESS)
    base = top + float(CENTRELINE_LIFT) + 0.10
    return {
        "footprints": base,
        "markers": base + 0.025,
        "protected": base + 0.050,
    }


def _create_chair_analysis_display(doc, entity_kind, config, result):
    kind = str(entity_kind).lower()
    entity_id = str(config.get("turnout_id") or config.get("crossover_id") or "")
    set_id = str(config.get("template_set_id") or "")
    clear_chair_analysis_display(doc, kind, entity_id)
    group = doc.addObject("App::DocumentObjectGroup", unique_internal_name(doc, "ChairAnalysis_{}".format(entity_id.replace("-", "_"))))
    group.Label = "{} chair analysis (temporary)".format(entity_id)
    tag_generated_object(group, CHAIR_ANALYSIS_GROUP_ROLE, set_id)
    if kind == "turnout":
        prop = ensure_property(group, "App::PropertyString", TURNOUT_ID_PROPERTY, "Chair analysis", "Parent turnout identity")
        setattr(group, TURNOUT_ID_PROPERTY, entity_id)
    else:
        prop = ensure_property(group, "App::PropertyString", CROSSOVER_ID_PROPERTY, "Chair analysis", "Parent crossover identity")
        setattr(group, CROSSOVER_ID_PROPERTY, entity_id)
    set_read_only(group, [prop])
    try:
        group.ViewObject.Visibility = True
    except Exception:
        pass

    levels = _chair_display_z_levels(doc, kind, config)
    settings = normalise_chair_analysis_settings(result.get("settings"))
    build_markers = bool(settings["markers_visible"])
    build_protected = bool(settings["protected_markers_visible"])
    build_footprints = bool(settings["footprints_visible"])
    marker_shapes = []
    protected_shapes = []
    footprint_shapes = []
    for item in result.get("positions") or []:
        if build_markers:
            marker_shapes.extend(_chair_cross_wires(
                item["centre_point"], item["local_rail_tangent"],
                half_size=0.80, z_height=levels["markers"]
            ))
        if build_protected and (item.get("mandatory") or item.get("protected_features")):
            protected_shapes.extend(_chair_cross_wires(
                item["centre_point"], item["local_rail_tangent"],
                half_size=1.15, z_height=levels["protected"]
            ))
        if build_footprints:
            polygon = item.get("chair_footprint_parameters", {}).get("polygon") or []
            if polygon:
                points = [vector_xy(point[0], point[1]) for point in polygon]
                points.append(points[0])
                footprint_shapes.append(_turnout_wire(points, levels["footprints"]))
    _chair_make_display_feature(doc, group, kind, entity_id, set_id, CHAIR_POSITION_MARKER_ROLE, "{} chair-position markers".format(entity_id), marker_shapes, build_markers)
    _chair_make_display_feature(doc, group, kind, entity_id, set_id, CHAIR_PROTECTED_MARKER_ROLE, "{} protected chair positions".format(entity_id), protected_shapes, build_protected)
    _chair_make_display_feature(doc, group, kind, entity_id, set_id, CHAIR_FOOTPRINT_MARKER_ROLE, "{} analytical chair footprints".format(entity_id), footprint_shapes, build_footprints)
    parent = production_parent_group_for_set(doc, set_id)
    if parent is not None:
        try:
            parent.addObject(group)
        except Exception:
            pass
    return group



def set_chair_analysis_visibility(doc, entity_kind, entity_id, markers=None, protected=None, footprints=None):
    kind = str(entity_kind).lower()
    identifier = str(entity_id or "")
    requested = {
        CHAIR_POSITION_MARKER_ROLE: markers,
        CHAIR_PROTECTED_MARKER_ROLE: protected,
        CHAIR_FOOTPRINT_MARKER_ROLE: footprints,
    }
    objects = _chair_analysis_display_objects(doc, kind, identifier)
    present_roles = {
        object_string_property(obj, "GeneratedRole", "")
        for obj in objects
    }
    missing_requested_layer = any(
        value is True and role not in present_roles
        for role, value in requested.items()
    )
    if missing_requested_layer:
        config = turnout_config_by_id(doc, identifier) if kind == "turnout" else crossover_config_by_id(doc, identifier)
        cached = _chair_read_cached_result(doc, kind, identifier)
        if isinstance(config, dict) and isinstance(cached, dict):
            rebuilt = dict(cached)
            settings = normalise_chair_analysis_settings(rebuilt.get("settings"))
            if markers is not None:
                settings["markers_visible"] = bool(markers)
            if protected is not None:
                settings["protected_markers_visible"] = bool(protected)
            if footprints is not None:
                settings["footprints_visible"] = bool(footprints)
            rebuilt["settings"] = settings
            _create_chair_analysis_display(doc, kind, config, rebuilt)
            try:
                _document_recompute(doc)
            except Exception:
                pass
            objects = _chair_analysis_display_objects(doc, kind, identifier)

    changed = 0
    show_any = any(value is True for value in (markers, protected, footprints))
    for obj in objects:
        role = object_string_property(obj, "GeneratedRole", "")
        if role == CHAIR_ANALYSIS_GROUP_ROLE and show_any:
            try:
                obj.ViewObject.Visibility = True
            except Exception:
                pass
            continue
        value = requested.get(role)
        if value is not None:
            try:
                obj.ViewObject.Visibility = bool(value)
                changed += 1
            except Exception:
                pass
    return changed


def chair_analysis_effective_status(doc, entity_kind, config):
    cfg = dict(config or {})
    stored_status = str(cfg.get("chair_analysis_status") or CHAIR_STATUS_NOT_ANALYSED)
    signature = str(cfg.get("chair_analysis_signature") or "")
    if not signature:
        return stored_status
    try:
        settings = normalise_chair_analysis_settings(cfg.get("chair_analysis_settings"))
        rails = chair_rail_records_for_entity(doc, entity_kind, cfg)
        timbers = chair_timber_records_for_entity(doc, entity_kind, cfg)
        current = _chair_geometry_signature(entity_kind, cfg, settings, rails, timbers)
    except Exception:
        return CHAIR_STATUS_STALE
    return stored_status if current == signature else CHAIR_STATUS_STALE


def analyse_entity_chair_positions(doc, entity_kind, entity_id, settings=None):
    overall_start = time.perf_counter()
    timings = {}
    kind = str(entity_kind).lower()
    config = turnout_config_by_id(doc, entity_id) if kind == "turnout" else crossover_config_by_id(doc, entity_id)
    if config is None:
        raise ValueError("{} {} was not found.".format(kind.capitalize(), entity_id or "selection"))
    settings = normalise_chair_analysis_settings(settings if settings is not None else config.get("chair_analysis_settings"))

    stage_start = time.perf_counter()
    rails = chair_rail_records_for_entity(doc, kind, config)
    timbers = chair_timber_records_for_entity(doc, kind, config)
    timings["record_extraction"] = (time.perf_counter() - stage_start) * 1000.0

    stage_start = time.perf_counter()
    signature = _chair_geometry_signature(kind, config, settings, rails, timbers)
    cached = _chair_read_cached_result(doc, kind, entity_id) if settings.get("cache_enabled") else None
    timings["signature_and_cache_lookup"] = (time.perf_counter() - stage_start) * 1000.0

    stage_start = time.perf_counter()
    if isinstance(cached, dict) and str(cached.get("geometry_signature") or "") == signature:
        result = dict(cached)
        result["cache_reused"] = True
        result["settings"] = settings
    else:
        result = analyse_chair_position_records(kind, config, rails, timbers, settings)
        result["geometry_signature"] = signature
        result["cache_reused"] = False
    timings["chair_calculation"] = (time.perf_counter() - stage_start) * 1000.0
    if not result.get("cache_reused"):
        for key, value in (result.get("performance_timings_ms") or {}).items():
            timings["core_" + str(key)] = float(value)

    objects = _chair_analysis_display_objects(doc, kind, entity_id)
    present_roles = {object_string_property(obj, "GeneratedRole", "") for obj in objects}
    positions = list(result.get("positions") or [])
    expected_roles = set()
    if settings.get("markers_visible") and positions:
        expected_roles.add(CHAIR_POSITION_MARKER_ROLE)
    if settings.get("protected_markers_visible") and any(
        item.get("mandatory") or item.get("protected_features") for item in positions
    ):
        expected_roles.add(CHAIR_PROTECTED_MARKER_ROLE)
    if settings.get("footprints_visible") and any(
        (item.get("chair_footprint_parameters") or {}).get("polygon") for item in positions
    ):
        expected_roles.add(CHAIR_FOOTPRINT_MARKER_ROLE)
    display_current = expected_roles.issubset(present_roles)
    if expected_roles:
        display_current = display_current and CHAIR_ANALYSIS_GROUP_ROLE in present_roles
    display_reused = bool(result.get("cache_reused")) and display_current

    old_result = _chair_read_cached_result(doc, kind, entity_id)
    transaction_open = False
    try:
        stage_start = time.perf_counter()
        doc.openTransaction("Analyse {} chair positions {}".format(kind, entity_id))
        transaction_open = True
        timings["transaction_open"] = (time.perf_counter() - stage_start) * 1000.0
        result["display_cache_reused"] = display_reused

        stage_start = time.perf_counter()
        result["performance_timings_ms"] = dict(timings)
        updated = _chair_write_metadata(doc, kind, config, result)
        timings["metadata_updates"] = (time.perf_counter() - stage_start) * 1000.0

        timings["diagnostic_display_construction"] = 0.0
        timings["visibility_updates"] = 0.0
        timings["document_recompute"] = 0.0
        if display_reused:
            stage_start = time.perf_counter()
            requested = {
                CHAIR_POSITION_MARKER_ROLE: bool(settings.get("markers_visible")),
                CHAIR_PROTECTED_MARKER_ROLE: bool(settings.get("protected_markers_visible")),
                CHAIR_FOOTPRINT_MARKER_ROLE: bool(settings.get("footprints_visible")),
            }
            show_group = any(requested.values())
            for obj in objects:
                role = object_string_property(obj, "GeneratedRole", "")
                try:
                    if role == CHAIR_ANALYSIS_GROUP_ROLE:
                        obj.ViewObject.Visibility = show_group
                    elif role in requested:
                        obj.ViewObject.Visibility = requested[role]
                except Exception:
                    pass
            timings["visibility_updates"] = (time.perf_counter() - stage_start) * 1000.0
        else:
            stage_start = time.perf_counter()
            _create_chair_analysis_display(doc, kind, updated, result)
            timings["diagnostic_display_construction"] = (time.perf_counter() - stage_start) * 1000.0

            stage_start = time.perf_counter()
            _document_recompute(doc)
            timings["document_recompute"] = (time.perf_counter() - stage_start) * 1000.0

        timings["metadata_display_and_recompute"] = (
            timings["metadata_updates"]
            + timings["diagnostic_display_construction"]
            + timings["visibility_updates"]
            + timings["document_recompute"]
        )
        stage_start = time.perf_counter()
        doc.commitTransaction()
        transaction_open = False
        timings["transaction_commit"] = (time.perf_counter() - stage_start) * 1000.0
    except Exception:
        if transaction_open:
            try:
                doc.abortTransaction()
            except Exception:
                pass
        try:
            if not display_reused:
                clear_chair_analysis_display(doc, kind, entity_id)
        except Exception:
            pass
        if old_result is not None:
            result = old_result
        raise
    timings["total"] = (time.perf_counter() - overall_start) * 1000.0
    result["performance_timings_ms"] = timings
    return result




def chair_analysis_summary(result, include_findings=True):
    if not isinstance(result, dict):
        return "No chair-position analysis has been stored."
    summary = dict(result.get("summary") or {})
    lines = [
        "Chair-position analysis — {}".format(result.get("entity_id") or "selection"),
        "Status: {}".format(result.get("status") or CHAIR_STATUS_NOT_ANALYSED),
        "Rails analysed: {}".format(summary.get("rail_count", 0)),
        "Final effective timbers analysed: {}".format(summary.get("timber_count", 0)),
        "Logical chair positions: {}".format(summary.get("chair_position_count", 0)),
        "Mandatory protected positions: {}".format(summary.get("mandatory_position_count", 0)),
        "Deliberately omitted/shared switch supports: {}".format(summary.get("deliberately_omitted_count", 0)),
        "Cache reused: {}".format("Yes" if result.get("cache_reused") else "No"),
        "Production geometry changed: No",
        "Temporary diagnostic markers generated: Yes — display objects only",
        "Detailed chair solids generated: No — later solid-generation stage",
        "Measured run time: {:.1f} ms{}".format(
            float((result.get("performance_timings_ms") or {}).get("total") or 0.0),
            " (calculation cache reused)" if result.get("cache_reused") else "",
        ),
        "Final solid/export validation complete: No — later validation stage",
        "",
        "Chair families:",
    ]
    for family, count in sorted((summary.get("family_counts") or {}).items()):
        lines.append("  - {}: {}".format(family, count))
    lines.extend(["", "Validation findings:"])
    counts = summary.get("severity_counts") or {}
    for severity in (CHAIR_SEVERITY_CRITICAL, CHAIR_SEVERITY_CONFLICT, CHAIR_SEVERITY_ADVISORY, CHAIR_SEVERITY_INFORMATION):
        lines.append("  - {}: {}".format(severity, counts.get(severity, 0)))
    if include_findings:
        findings = list(result.get("findings") or [])
        if not findings:
            lines.append("  No findings.")
            return "\n".join(lines)

        blocking = [item for item in findings if item.get("severity") in (CHAIR_SEVERITY_CRITICAL, CHAIR_SEVERITY_CONFLICT)]
        if blocking:
            lines.extend(["", "Production findings:"])
            for finding in blocking:
                lines.append("[{}] {}: {}".format(finding.get("severity"), finding.get("code"), finding.get("message")))

        grouped = {}
        for finding in findings:
            if finding.get("severity") in (CHAIR_SEVERITY_CRITICAL, CHAIR_SEVERITY_CONFLICT):
                continue
            key = (str(finding.get("severity") or ""), str(finding.get("code") or ""))
            grouped.setdefault(key, []).append(finding)
        if grouped:
            lines.extend(["", "Grouped advisory and informational findings:"])
            positions_by_id = {
                str(item.get("stable_chair_position_identity") or ""): item
                for item in result.get("positions") or []
            }
            for (severity, code), items in sorted(grouped.items()):
                if code == "KEY_ORIENTATION_REQUIRES_CONFIRMATION":
                    detail = "Final key orientation remains deferred to confirmed chair subtype and rail-side context."
                elif code == "EXCESSIVE_CHAIR_SKEW":
                    values = []
                    for finding in items:
                        for identity in finding.get("chair_position_identities") or []:
                            values.append(float((positions_by_id.get(identity) or {}).get("chair_skew_degrees") or 0.0))
                    detail = "Maximum reported analytical skew: {:.3f} degrees.".format(max(values) if values else 0.0)
                else:
                    detail = str(items[0].get("message") or "")
                lines.append("[{}] {}: {} position(s). {}".format(severity, code, len(items), detail))
            lines.append("Individual records remain stored in the chair-analysis metadata.")
    return "\n".join(lines)


class ChairAnalysisSettingsDialog(QtWidgets.QDialog):
    def __init__(self, settings, parent=None):
        super(ChairAnalysisSettingsDialog, self).__init__(parent)
        self.setWindowTitle(versioned_dialog_title("Chair tolerances and settings"))
        self._defaults = normalise_chair_analysis_settings(settings)
        layout = QtWidgets.QFormLayout(self)
        self.position = QtWidgets.QDoubleSpinBox(); self.position.setRange(0.0, 5.0); self.position.setDecimals(3); self.position.setSuffix(" mm"); self.position.setValue(self._defaults["position_tolerance"])
        self.position.setToolTip("Tolerance used to decide whether a rail support centre lies on a timber. It affects analysis only and never moves geometry.")
        self.footprint = QtWidgets.QDoubleSpinBox(); self.footprint.setRange(0.0, 5.0); self.footprint.setDecimals(3); self.footprint.setSuffix(" mm"); self.footprint.setValue(self._defaults["footprint_clearance"])
        self.footprint.setToolTip("Clearance added when broad-phase chair-footprint candidates are compared. It affects analysis only.")
        self.end_clearance = QtWidgets.QDoubleSpinBox(); self.end_clearance.setRange(0.0, 10.0); self.end_clearance.setDecimals(3); self.end_clearance.setSuffix(" mm"); self.end_clearance.setValue(self._defaults["timber_end_clearance"])
        self.end_clearance.setToolTip("Minimum desired model-scale clearance between the analytical chair footprint and a timber end.")
        self.skew = QtWidgets.QDoubleSpinBox(); self.skew.setRange(0.0, 30.0); self.skew.setDecimals(2); self.skew.setSuffix(" degrees"); self.skew.setValue(self._defaults["maximum_advisory_skew_degrees"])
        self.skew.setToolTip("Chair skew above this value is reported as advisory. It does not rotate rails or timbers.")
        self.span = QtWidgets.QDoubleSpinBox(); self.span.setRange(1.0, 100.0); self.span.setDecimals(3); self.span.setSuffix(" mm"); self.span.setValue(self._defaults["maximum_unsupported_span"])
        self.span.setToolTip("Largest permitted model-scale distance between adjacent logical rail supports before a production conflict is reported.")
        self.cache = QtWidgets.QCheckBox("Reuse analysis when signatures match"); self.cache.setChecked(self._defaults["cache_enabled"])
        self.cache.setToolTip("Reuses cached metadata only when rail, timber and setting signatures match exactly.")
        layout.addRow("Chair-position tolerance", self.position)
        layout.addRow("Footprint broad-phase clearance", self.footprint)
        layout.addRow("Minimum timber-end clearance", self.end_clearance)
        layout.addRow("Maximum advisory chair skew", self.skew)
        layout.addRow("Maximum unsupported rail span", self.span)
        layout.addRow("Analysis cache", self.cache)
        note = QtWidgets.QLabel("Future embed and Boolean tolerances remain stored defaults only; this stage creates no chair solids or Boolean operations.")
        note.setWordWrap(True); layout.addRow(note)
        buttons = QtWidgets.QDialogButtonBox(QtWidgets.QDialogButtonBox.Ok | QtWidgets.QDialogButtonBox.Cancel)
        buttons.accepted.connect(self.accept); buttons.rejected.connect(self.reject); layout.addRow(buttons)

    def values(self):
        result = dict(self._defaults)
        result.update({
            "position_tolerance": self.position.value(),
            "footprint_clearance": self.footprint.value(),
            "timber_end_clearance": self.end_clearance.value(),
            "maximum_advisory_skew_degrees": self.skew.value(),
            "maximum_unsupported_span": self.span.value(),
            "cache_enabled": self.cache.isChecked(),
        })
        return normalise_chair_analysis_settings(result)


class ChairAnalysisPanel(QtWidgets.QGroupBox):
    """Contained functional controls shared by turnout and crossover tabs."""
    def __init__(self, doc, entity_kind, config_getter, refresh_callback=None, parent=None):
        super(ChairAnalysisPanel, self).__init__("Chair analysis", parent)
        self.doc = doc
        self.entity_kind = str(entity_kind).lower()
        self.config_getter = config_getter
        self.refresh_callback = refresh_callback
        self.settings = default_chair_analysis_settings()
        layout = QtWidgets.QGridLayout(self)
        self.status = QtWidgets.QLabel(CHAIR_STATUS_NOT_ANALYSED); self.status.setWordWrap(True)
        self.analyse_button = QtWidgets.QPushButton("Analyse chair positions")
        self.marker_box = QtWidgets.QCheckBox("Show chair-position markers"); self.marker_box.setChecked(True)
        self.protected_box = QtWidgets.QCheckBox("Show protected chair positions")
        self.footprint_box = QtWidgets.QCheckBox("Show analytical chair footprints")
        self.details_button = QtWidgets.QPushButton("Show chair-assignment details")
        self.copy_button = QtWidgets.QPushButton("Copy readable chair summary")
        self.clear_button = QtWidgets.QPushButton("Clear temporary chair display")
        self.settings_button = QtWidgets.QPushButton("Chair tolerances and settings…")
        layout.addWidget(QtWidgets.QLabel("Selected item status"), 0, 0)
        layout.addWidget(self.status, 0, 1, 1, 4)
        layout.addWidget(self.analyse_button, 1, 0, 1, 2)
        layout.addWidget(self.marker_box, 1, 2)
        layout.addWidget(self.protected_box, 1, 3)
        layout.addWidget(self.footprint_box, 1, 4)
        layout.addWidget(self.details_button, 2, 0, 1, 2)
        layout.addWidget(self.copy_button, 2, 2)
        layout.addWidget(self.clear_button, 2, 3)
        layout.addWidget(self.settings_button, 2, 4)
        self.setToolTip("Creates logical rail-to-timber support records and lightweight diagnostics only. It does not alter production rails, timbers, host tracks or sectioning.")
        self.analyse_button.setToolTip("Analyses stable logical rail geometry from the stored turnout or crossover configuration against the final effective timber arrangement. Production geometry remains unchanged.")
        self.marker_box.setToolTip("Shows or hides temporary small crosses at logical chair positions. This affects display only.")
        self.protected_box.setToolTip("Shows or hides temporary larger crosses at mandatory switch, crossing, wing, check, vee and rail-joint supports.")
        self.footprint_box.setToolTip("Shows or hides lightweight analytical chair-base outlines. These are not production chair solids.")
        self.details_button.setToolTip("Shows the complete stored chair assignments and validation findings for the selected item.")
        self.copy_button.setToolTip("Copies a readable summary of the selected item's latest chair analysis.")
        self.clear_button.setToolTip("Removes temporary chair markers and outlines. Cached metadata and all production geometry remain unchanged.")
        self.settings_button.setToolTip("Adjusts model-scale analytical tolerances and cache behaviour. It does not create or alter production geometry.")
        self.analyse_button.clicked.connect(self.run_analysis)
        self.marker_box.toggled.connect(self.change_visibility)
        self.protected_box.toggled.connect(self.change_visibility)
        self.footprint_box.toggled.connect(self.change_visibility)
        self.details_button.clicked.connect(self.show_details)
        self.copy_button.clicked.connect(self.copy_summary)
        self.clear_button.clicked.connect(self.clear_display)
        self.settings_button.clicked.connect(self.edit_settings)
        self.refresh()

    def current_config(self):
        try:
            return self.config_getter()
        except Exception:
            return None

    def entity_id(self, config):
        return str((config or {}).get("turnout_id") or (config or {}).get("crossover_id") or "")

    def refresh(self):
        config = self.current_config()
        enabled = isinstance(config, dict)
        for widget in (self.analyse_button, self.marker_box, self.protected_box, self.footprint_box, self.details_button, self.copy_button, self.clear_button, self.settings_button):
            widget.setEnabled(enabled)
        if not enabled:
            self.status.setText("Select a {} to analyse.".format(self.entity_kind))
            return
        self.settings = normalise_chair_analysis_settings(config.get("chair_analysis_settings"))
        self.marker_box.blockSignals(True); self.protected_box.blockSignals(True); self.footprint_box.blockSignals(True)
        self.marker_box.setChecked(self.settings["markers_visible"])
        self.protected_box.setChecked(self.settings["protected_markers_visible"])
        self.footprint_box.setChecked(self.settings["footprints_visible"])
        self.marker_box.blockSignals(False); self.protected_box.blockSignals(False); self.footprint_box.blockSignals(False)
        self.status.setText(chair_analysis_effective_status(self.doc, self.entity_kind, config))
        cached = _chair_read_cached_result(self.doc, self.entity_kind, self.entity_id(config))
        self.details_button.setEnabled(cached is not None); self.copy_button.setEnabled(cached is not None)

    def run_analysis(self):
        config = self.current_config()
        if not config:
            return
        try:
            self.settings.update({
                "markers_visible": self.marker_box.isChecked(),
                "protected_markers_visible": self.protected_box.isChecked(),
                "footprints_visible": self.footprint_box.isChecked(),
            })
            result = analyse_entity_chair_positions(self.doc, self.entity_kind, self.entity_id(config), self.settings)
            self.status.setText(str(result.get("status") or CHAIR_STATUS_GENERATED))
            if callable(self.refresh_callback):
                self.refresh_callback(self.entity_id(config))
        except Exception as error:
            QtWidgets.QMessageBox.critical(self, versioned_dialog_title("Chair analysis error"), str(error))
        self.refresh()

    def change_visibility(self):
        config = self.current_config()
        if not config:
            return
        set_chair_analysis_visibility(
            self.doc, self.entity_kind, self.entity_id(config),
            markers=self.marker_box.isChecked(),
            protected=self.protected_box.isChecked(),
            footprints=self.footprint_box.isChecked(),
        )

    def show_details(self):
        config = self.current_config()
        if not config:
            return
        result = _chair_read_cached_result(self.doc, self.entity_kind, self.entity_id(config))
        QtWidgets.QMessageBox.information(self, versioned_dialog_title("Chair-assignment details"), chair_analysis_summary(result, True))

    def copy_summary(self):
        config = self.current_config()
        if not config:
            return
        result = _chair_read_cached_result(self.doc, self.entity_kind, self.entity_id(config))
        try:
            QtWidgets.QApplication.clipboard().setText(chair_analysis_summary(result, True))
        except Exception:
            pass

    def clear_display(self):
        config = self.current_config()
        if not config:
            return
        clear_chair_analysis_display(self.doc, self.entity_kind, self.entity_id(config))
        try:
            _document_recompute(self.doc)
        except Exception:
            pass

    def edit_settings(self):
        dialog = ChairAnalysisSettingsDialog(self.settings, self)
        if dialog.exec_() != QtWidgets.QDialog.Accepted:
            return
        self.settings = dialog.values()
        self.settings.update({
            "markers_visible": self.marker_box.isChecked(),
            "protected_markers_visible": self.protected_box.isChecked(),
            "footprints_visible": self.footprint_box.isChecked(),
        })
        self.status.setText(CHAIR_STATUS_STALE)


class GuidedTrackworkWorkflowPanel(QtWidgets.QGroupBox):
    """Small operator-facing step controller around existing manager actions.

    The panel owns no railway geometry, timbering, chair or integration logic. It
    only exposes callbacks already implemented by the turnout and crossover
    managers and reports their current stored status.
    """
    STATE_PREFIXES = {
        "complete": "Complete — ",
        "ready": "Next — ",
        "attention": "Review — ",
        "blocked": "Blocked — ",
        "waiting": "Waiting — ",
    }

    def __init__(self, title, step_titles, parent=None):
        super(GuidedTrackworkWorkflowPanel, self).__init__(title, parent)
        self._rows = []
        outer = QtWidgets.QVBoxLayout(self)
        self.summary_label = QtWidgets.QLabel(
            "Work from the first incomplete step. Each action calls the same established function as the specialist controls below."
        )
        self.summary_label.setWordWrap(True)
        outer.addWidget(self.summary_label)

        grid = QtWidgets.QGridLayout()
        grid.setColumnStretch(2, 1)
        for index, title_text in enumerate(step_titles):
            step_label = QtWidgets.QLabel("Step {}".format(index + 1))
            title_label = QtWidgets.QLabel("<b>{}</b>".format(title_text))
            status_label = QtWidgets.QLabel("Waiting")
            status_label.setWordWrap(True)
            primary = QtWidgets.QPushButton("Continue")
            secondary = QtWidgets.QPushButton("Details")
            grid.addWidget(step_label, index, 0)
            grid.addWidget(title_label, index, 1)
            grid.addWidget(status_label, index, 2)
            grid.addWidget(primary, index, 3)
            grid.addWidget(secondary, index, 4)
            self._rows.append({
                "step": step_label,
                "title": title_label,
                "status": status_label,
                "primary": primary,
                "secondary": secondary,
            })
        outer.addLayout(grid)

        controls = QtWidgets.QHBoxLayout()
        self.run_next_button = QtWidgets.QPushButton("Run next safe step")
        self.run_next_button.setToolTip(
            "Runs only the next incomplete guided stage. It stops at failed or blocked validation and never bypasses an existing safety or production-readiness gate."
        )
        self.advanced_checkbox = QtWidgets.QCheckBox("Show specialist and maintenance controls")
        self.advanced_checkbox.setChecked(False)
        self.advanced_checkbox.setToolTip(
            "Shows the original detailed controls for diagnostics, manual timber stages, settings, removal and reference-copy work."
        )
        controls.addWidget(self.run_next_button)
        controls.addStretch(1)
        controls.addWidget(self.advanced_checkbox)
        outer.addLayout(controls)

    def primary_button(self, index):
        return self._rows[int(index)]["primary"]

    def secondary_button(self, index):
        return self._rows[int(index)]["secondary"]

    def set_summary(self, text):
        self.summary_label.setText(str(text or ""))

    def set_step(self, index, status, state="waiting", primary_text="", primary_enabled=False,
                 secondary_text="", secondary_enabled=False):
        row = self._rows[int(index)]
        prefix = self.STATE_PREFIXES.get(str(state), "")
        row["status"].setText(prefix + str(status or ""))
        row["primary"].setText(str(primary_text or "Continue"))
        row["primary"].setEnabled(bool(primary_enabled))
        row["secondary"].setText(str(secondary_text or "Details"))
        row["secondary"].setEnabled(bool(secondary_enabled))
        row["secondary"].setVisible(bool(secondary_text))


def _chair_preflight_record_entity(doc, record):
    """Resolve production records through stable source-object identities.

    Turnout production records deliberately retain the host route identifier in
    ``route_id``.  Therefore chair preflight must read TurnoutID/CrossoverID from
    the bound source object rather than mistaking a host route for a turnout.
    """
    candidate_names = []
    for field in ("source_name", "base_source_name"):
        raw = str((record or {}).get(field) or "").strip()
        if not raw:
            continue
        for token in raw.replace("::", "+").split("+"):
            name = str(token or "").strip()
            if name and name not in candidate_names:
                candidate_names.append(name)
    for name in candidate_names:
        try:
            obj = doc.getObject(name)
        except Exception:
            obj = None
        if obj is None:
            continue
        turnout_id = object_string_property(obj, TURNOUT_ID_PROPERTY, "").strip()
        if turnout_id:
            return "turnout", turnout_id
        crossover_id = object_string_property(obj, CROSSOVER_ID_PROPERTY, "").strip()
        if crossover_id:
            return "crossover", crossover_id

    # Fallbacks are retained for synthetic or legacy records which already use
    # the managed entity identifier as route_id.  Never infer a turnout ID from
    # its subtype alone because ordinary turnout records use their host route ID.
    route_id = str((record or {}).get("route_id") or "").strip()
    if route_id.startswith("TURNOUT-"):
        return "turnout", route_id
    if route_id.startswith("CROSSOVER-"):
        return "crossover", route_id
    return None, ""


def preflight_chair_analysis_readiness(doc, records, set_id):
    """Report logical chair readiness without blocking inspection exports."""
    representatives = {}
    for record in records or []:
        kind, identifier = _chair_preflight_record_entity(doc, record)
        if kind and identifier:
            representatives.setdefault((kind, identifier), record)
    issues = []
    for (kind, identifier), record in sorted(representatives.items()):
        if not identifier:
            continue
        config = turnout_config_by_id(doc, identifier) if kind == "turnout" else crossover_config_by_id(doc, identifier)
        if not isinstance(config, dict):
            continue
        status = chair_analysis_effective_status(doc, kind, config)
        if status in (CHAIR_STATUS_NOT_ANALYSED, CHAIR_STATUS_STALE):
            issues.append(make_preflight_issue(
                "CHAIR_ANALYSIS_{}".format("STALE" if status == CHAIR_STATUS_STALE else "NOT_RUN"),
                PRODUCTION_PREFLIGHT_SEVERITY_WARNING,
                "{} {} chair-position analysis is {}. Inspection export remains available, but this is not a chair-validated production assembly.".format(kind.capitalize(), identifier, status.lower()),
                set_id, record, blocks_export=False,
            ))
        elif status == CHAIR_STATUS_CRITICAL:
            issues.append(make_preflight_issue(
                "CHAIR_PRODUCTION_CRITICAL_CONFLICTS",
                PRODUCTION_PREFLIGHT_SEVERITY_WARNING,
                "{} {} has production-critical logical chair conflicts. Inspection export remains available; production readiness is blocked.".format(kind.capitalize(), identifier),
                set_id, record, blocks_export=False,
            ))
        elif status in (CHAIR_STATUS_CONFLICTS, CHAIR_STATUS_INCOMPLETE):
            issues.append(make_preflight_issue(
                "CHAIR_ASSIGNMENTS_INCOMPLETE",
                PRODUCTION_PREFLIGHT_SEVERITY_WARNING,
                "{} {} logical chair assignments are not complete ({}). Inspection export remains available.".format(kind.capitalize(), identifier, status),
                set_id, record, blocks_export=False,
            ))
        else:
            issues.append(make_preflight_issue(
                "CHAIR_SOLIDS_AND_FINAL_VALIDATION_OUTSTANDING",
                PRODUCTION_PREFLIGHT_SEVERITY_INFORMATION,
                "{} {} logical chair positions are current, but detailed chair solids and final solid/export validation remain staged for later chair development.".format(kind.capitalize(), identifier),
                set_id, record, blocks_export=False,
            ))
    return issues


class CrossoverManagerPanel(QtWidgets.QWidget):
    """Embedded crossover controls.

    This must remain a plain QWidget. An earlier revision embedded a QDialog inside the
    modal TurnoutManagerDialog and then changed its window flags.  That can
    invalidate native Qt ownership in FreeCAD/PySide and cause a hard crash
    without a Python exception.
    """
    def __init__(self, doc, parent=None):
        super(CrossoverManagerPanel, self).__init__(parent)
        self.doc = doc
        self.hosts = []
        self.crossovers = []
        self._last_preview_signature = None
        self._last_preview_result = None
        self.extending_turnout_id = None
        self.extending_turnout_config = None
        self.editing_crossover_id = None
        self.editing_crossover_config = None
        self.turnout_refresh_callback = None
        self.setWindowTitle(crossover_dialog_title("REA C10 crossovers and timbering"))
        self.resize(1180, 900)
        layout = QtWidgets.QVBoxLayout(self)

        warning = QtWidgets.QLabel(
            "The automatic timber resolver builds the complete shared long-timber envelope, then applies interlacing or the smallest permitted longitudinal movement only where required. "
            "Unsafe positions remain explicit. A complete final timber arrangement can be integrated reversibly with both host templates; chair validation remains a later stage."
        )
        warning.setWordWrap(True)
        layout.addWidget(warning)

        self.workflow_panel = GuidedTrackworkWorkflowPanel(
            "Guided crossover workflow",
            (
                "Place and create crossover geometry",
                "Resolve the shared timbering",
                "Analyse chair positions",
                "Adjust model timber support",
                "Build and validate the 2D chair layout",
                "Integrate with the host templates",
                "Finish, export or convert the result",
            ),
            self,
        )
        layout.addWidget(self.workflow_panel)

        host_group = QtWidgets.QGroupBox("Crossover hosts and geometry")
        self.crossover_host_group = host_group
        form = QtWidgets.QFormLayout(host_group)
        self.host_a_combo = QtWidgets.QComboBox()
        self.host_b_combo = QtWidgets.QComboBox()
        form.addRow("Host Track A", self.host_a_combo)
        form.addRow("Host Track B", self.host_b_combo)
        selection_row = QtWidgets.QHBoxLayout()
        self.use_picked_position_button = QtWidgets.QPushButton("Use picked crossover position")
        self.use_picked_position_button.setToolTip(
            "Click a recognised host centreline at the required crossover position. The clicked host becomes "
            "Host A, its nearest valid chainage is used, and the nearest compatible host becomes Host B. "
            "Control-selecting two hosts overrides the automatic Host B choice."
        )
        self.use_selected_a_button = QtWidgets.QPushButton("Use selected centreline as A")
        self.use_selected_b_button = QtWidgets.QPushButton("Use selected centreline as B")
        self.refresh_hosts_button = QtWidgets.QPushButton("Refresh hosts")
        selection_row.addWidget(self.use_picked_position_button)
        selection_row.addWidget(self.use_selected_a_button)
        selection_row.addWidget(self.use_selected_b_button)
        selection_row.addWidget(self.refresh_hosts_button)
        form.addRow("Host selection", selection_row)

        self.selection_status = QtWidgets.QLabel(
            "Pick a point on either intended host centreline, then choose Use picked crossover position."
        )
        self.selection_status.setWordWrap(True)
        form.addRow("Picked placement", self.selection_status)

        self.chainage_box = QtWidgets.QDoubleSpinBox()
        self.chainage_box.setDecimals(3)
        self.chainage_box.setRange(0.0, 1000000.0)
        self.chainage_box.setSingleStep(1.0)
        self.chainage_box.setSuffix(" mm")
        form.addRow("Host A reference/toe chainage", self.chainage_box)
        nudge_row = QtWidgets.QHBoxLayout()
        self.nudge_buttons = []
        for delta in (-100.0, -10.0, -1.0, 1.0, 10.0, 100.0):
            label = "{:+g}".format(delta)
            button = QtWidgets.QPushButton(label)
            button.setToolTip("Move the crossover reference position {} mm along Host A.".format(label))
            button.clicked.connect(lambda _checked=False, amount=delta: self.nudge_chainage(amount))
            nudge_row.addWidget(button)
            self.nudge_buttons.append(button)
        form.addRow("Exact position nudge", nudge_row)
        self.arrangement_combo = QtWidgets.QComboBox()
        self.arrangement_combo.addItems([CROSSOVER_ARRANGEMENT_FACING, CROSSOVER_ARRANGEMENT_TRAILING])
        form.addRow("Arrangement", self.arrangement_combo)
        self.handing_combo = QtWidgets.QComboBox()
        self.handing_combo.addItems([CROSSOVER_HAND_AUTO, TURNOUT_HAND_LEFT, TURNOUT_HAND_RIGHT])
        form.addRow("Handing", self.handing_combo)
        self.gauge_box = QtWidgets.QDoubleSpinBox()
        self.gauge_box.setDecimals(3)
        self.gauge_box.setRange(TURNOUT_MIN_GAUGE, TURNOUT_MAX_GAUGE)
        self.gauge_box.setValue(TURNOUT_DEFAULT_GAUGE)
        self.gauge_box.setSuffix(" mm")
        form.addRow("Track gauge", self.gauge_box)
        self.flangeway_box = QtWidgets.QDoubleSpinBox()
        self.flangeway_box.setDecimals(3)
        self.flangeway_box.setRange(TURNOUT_MIN_FLANGEWAY, TURNOUT_MAX_FLANGEWAY)
        self.flangeway_box.setValue(TURNOUT_DEFAULT_FLANGEWAY)
        self.flangeway_box.setSuffix(" mm")
        form.addRow("Design flangeway", self.flangeway_box)
        self.minimum_radius_box = QtWidgets.QDoubleSpinBox()
        self.minimum_radius_box.setDecimals(3)
        self.minimum_radius_box.setRange(CROSSOVER_MINIMUM_ALLOWED_RADIUS, 100000.0)
        self.minimum_radius_box.setValue(CROSSOVER_DEFAULT_MINIMUM_RADIUS)
        self.minimum_radius_box.setSuffix(" mm")
        form.addRow("Minimum permitted radius", self.minimum_radius_box)
        layout.addWidget(host_group)

        self.diagnostics = QtWidgets.QPlainTextEdit()
        self.diagnostics.setReadOnly(True)
        self.diagnostics.setMinimumHeight(230)
        layout.addWidget(self.diagnostics)

        self.table = QtWidgets.QTableWidget(0, 9)
        self.table.setHorizontalHeaderLabels([
            "ID", "Host A", "Host B", "Arrangement", "Hand", "Toe A", "Toe B", "Timber analysis and resolution status", "Host integration"
        ])
        self.table.setSelectionBehavior(QtWidgets.QAbstractItemView.SelectRows)
        self.table.setSelectionMode(QtWidgets.QAbstractItemView.SingleSelection)
        self.table.setEditTriggers(QtWidgets.QAbstractItemView.NoEditTriggers)
        self.table.horizontalHeader().setStretchLastSection(True)
        layout.addWidget(self.table)

        self.timber_analysis_settings = default_crossover_timber_analysis_settings()
        analysis_group = QtWidgets.QGroupBox(CROSSOVER_TIMBERING_UI_TEXT["group_title"])
        self.crossover_advanced_timber_group = analysis_group
        analysis_layout = QtWidgets.QGridLayout(analysis_group)
        self.timber_analysis_status = QtWidgets.QLabel(CROSSOVER_TIMBER_ANALYSIS_STATUS_NOT_ANALYSED)
        self.timber_analysis_status.setWordWrap(True)
        analysis_layout.addWidget(QtWidgets.QLabel("Selected crossover status"), 0, 0)
        analysis_layout.addWidget(self.timber_analysis_status, 0, 1, 1, 5)
        self.analyse_timber_button = QtWidgets.QPushButton("Analyse selected crossover timbering")
        self.show_conflict_markers_checkbox = QtWidgets.QCheckBox("Show conflict markers")
        self.show_conflict_markers_checkbox.setChecked(True)
        self.show_support_markers_checkbox = QtWidgets.QCheckBox("Show protected support markers")
        self.show_support_markers_checkbox.setChecked(False)
        self.timber_analysis_details_button = QtWidgets.QPushButton("Show timber analysis details")
        self.clear_timber_analysis_button = QtWidgets.QPushButton("Clear temporary analysis display")
        self.copy_timber_analysis_button = QtWidgets.QPushButton("Copy readable analysis summary")
        self.timber_analysis_tolerances_button = QtWidgets.QPushButton("Analysis tolerances…")
        analysis_layout.addWidget(self.analyse_timber_button, 1, 0, 1, 2)
        analysis_layout.addWidget(self.show_conflict_markers_checkbox, 1, 2)
        analysis_layout.addWidget(self.show_support_markers_checkbox, 1, 3)
        analysis_layout.addWidget(self.timber_analysis_tolerances_button, 1, 4)
        analysis_layout.addWidget(self.timber_analysis_details_button, 2, 0, 1, 2)
        analysis_layout.addWidget(self.copy_timber_analysis_button, 2, 2, 1, 2)
        analysis_layout.addWidget(self.clear_timber_analysis_button, 2, 4)
        self.shared_timber_settings = default_crossover_shared_timber_settings()
        self.apply_shared_timbers_button = QtWidgets.QPushButton(CROSSOVER_TIMBERING_UI_TEXT["build_shared"])
        self.remove_shared_timbers_button = QtWidgets.QPushButton(CROSSOVER_TIMBERING_UI_TEXT["remove_shared"])
        self.shared_timber_details_button = QtWidgets.QPushButton(CROSSOVER_TIMBERING_UI_TEXT["shared_details"])
        self.shared_timber_settings_button = QtWidgets.QPushButton(CROSSOVER_TIMBERING_UI_TEXT["shared_settings"])
        self.show_shared_timbers_checkbox = QtWidgets.QCheckBox(CROSSOVER_TIMBERING_UI_TEXT["show_shared"])
        self.show_shared_timbers_checkbox.setChecked(True)
        analysis_layout.addWidget(self.apply_shared_timbers_button, 5, 0, 1, 2)
        analysis_layout.addWidget(self.remove_shared_timbers_button, 5, 2)
        analysis_layout.addWidget(self.shared_timber_details_button, 5, 3)
        analysis_layout.addWidget(self.shared_timber_settings_button, 5, 4)
        analysis_layout.addWidget(self.show_shared_timbers_checkbox, 6, 0, 1, 3)
        self.b3_settings = default_crossover_b3_settings()
        self.apply_b3_button = QtWidgets.QPushButton(CROSSOVER_TIMBERING_UI_TEXT["resolve_remaining"])
        self.remove_b3_button = QtWidgets.QPushButton(CROSSOVER_TIMBERING_UI_TEXT["remove_adjustment"])
        self.b3_details_button = QtWidgets.QPushButton(CROSSOVER_TIMBERING_UI_TEXT["adjustment_details"])
        self.b3_settings_button = QtWidgets.QPushButton(CROSSOVER_TIMBERING_UI_TEXT["adjustment_settings"])
        self.show_b3_checkbox = QtWidgets.QCheckBox(CROSSOVER_TIMBERING_UI_TEXT["show_adjusted"])
        self.show_b3_checkbox.setChecked(True)
        analysis_layout.addWidget(self.apply_b3_button, 7, 0, 1, 2)
        analysis_layout.addWidget(self.remove_b3_button, 7, 2)
        analysis_layout.addWidget(self.b3_details_button, 7, 3)
        analysis_layout.addWidget(self.b3_settings_button, 7, 4)
        analysis_layout.addWidget(self.show_b3_checkbox, 8, 0, 1, 3)
        self.b4_settings = default_crossover_b4_settings()
        self.apply_b4_button = QtWidgets.QPushButton(CROSSOVER_TIMBERING_UI_TEXT["apply_automatic"])
        self.apply_b4_button.setToolTip(CROSSOVER_TIMBERING_TOOLTIPS["apply_automatic"])
        self.remove_b4_button = QtWidgets.QPushButton(CROSSOVER_TIMBERING_UI_TEXT["remove_automatic"])
        self.b4_details_button = QtWidgets.QPushButton(CROSSOVER_TIMBERING_UI_TEXT["automatic_details"])
        self.show_b4_checkbox = QtWidgets.QCheckBox(CROSSOVER_TIMBERING_UI_TEXT["show_automatic"])
        self.show_b4_checkbox.setChecked(True)

        analysis_group.setToolTip("Analyse and resolve crossover timbering without altering the established rail solver or host tracks.")
        self.timber_analysis_status.setToolTip(CROSSOVER_TIMBERING_TOOLTIPS["status"])
        self.analyse_timber_button.setToolTip(CROSSOVER_TIMBERING_TOOLTIPS["analyse"])
        self.show_conflict_markers_checkbox.setToolTip(CROSSOVER_TIMBERING_TOOLTIPS["show_conflicts"])
        self.show_support_markers_checkbox.setToolTip(CROSSOVER_TIMBERING_TOOLTIPS["show_supports"])
        self.timber_analysis_tolerances_button.setToolTip(CROSSOVER_TIMBERING_TOOLTIPS["analysis_settings"])
        self.timber_analysis_details_button.setToolTip(CROSSOVER_TIMBERING_TOOLTIPS["analysis_details"])
        self.copy_timber_analysis_button.setToolTip(CROSSOVER_TIMBERING_TOOLTIPS["copy_analysis"])
        self.clear_timber_analysis_button.setToolTip(CROSSOVER_TIMBERING_TOOLTIPS["clear_analysis"])
        self.apply_shared_timbers_button.setToolTip(CROSSOVER_TIMBERING_TOOLTIPS["build_shared"])
        self.remove_shared_timbers_button.setToolTip(CROSSOVER_TIMBERING_TOOLTIPS["remove_shared"])
        self.shared_timber_details_button.setToolTip(CROSSOVER_TIMBERING_TOOLTIPS["shared_details"])
        self.shared_timber_settings_button.setToolTip(CROSSOVER_TIMBERING_TOOLTIPS["shared_settings"])
        self.show_shared_timbers_checkbox.setToolTip(CROSSOVER_TIMBERING_TOOLTIPS["show_shared"])
        self.apply_b3_button.setToolTip(CROSSOVER_TIMBERING_TOOLTIPS["resolve_remaining"])
        self.remove_b3_button.setToolTip(CROSSOVER_TIMBERING_TOOLTIPS["remove_adjustment"])
        self.b3_details_button.setToolTip(CROSSOVER_TIMBERING_TOOLTIPS["adjustment_details"])
        self.b3_settings_button.setToolTip(CROSSOVER_TIMBERING_TOOLTIPS["adjustment_settings"])
        self.show_b3_checkbox.setToolTip(CROSSOVER_TIMBERING_TOOLTIPS["show_adjusted"])
        self.remove_b4_button.setToolTip(CROSSOVER_TIMBERING_TOOLTIPS["remove_automatic"])
        self.b4_details_button.setToolTip(CROSSOVER_TIMBERING_TOOLTIPS["automatic_details"])
        self.show_b4_checkbox.setToolTip(CROSSOVER_TIMBERING_TOOLTIPS["show_automatic"])
        analysis_layout.addWidget(self.apply_b4_button, 3, 0, 1, 2)
        analysis_layout.addWidget(self.remove_b4_button, 3, 2)
        analysis_layout.addWidget(self.b4_details_button, 3, 3)
        analysis_layout.addWidget(self.show_b4_checkbox, 4, 0, 1, 3)
        layout.addWidget(analysis_group)
        self.chair_analysis_panel = ChairAnalysisPanel(self.doc, "crossover", self.current_config, self.refresh_crossovers, self)
        layout.addWidget(self.chair_analysis_panel)

        integration_group = QtWidgets.QGroupBox(CROSSOVER_TIMBERING_UI_TEXT["integration_group_title"])
        self.crossover_advanced_integration_group = integration_group
        integration_layout = QtWidgets.QGridLayout(integration_group)
        self.integration_status = QtWidgets.QLabel(CROSSOVER_INTEGRATION_STATUS_NOT_INTEGRATED)
        self.integration_status.setWordWrap(True)
        self.edit_crossover_button = QtWidgets.QPushButton(CROSSOVER_TIMBERING_UI_TEXT["edit_crossover"])
        self.cancel_edit_button = QtWidgets.QPushButton(CROSSOVER_TIMBERING_UI_TEXT["cancel_edit"])
        self.cancel_edit_button.setVisible(False)
        self.integrate_hosts_button = QtWidgets.QPushButton(CROSSOVER_TIMBERING_UI_TEXT["integrate_hosts"])
        self.remove_integration_button = QtWidgets.QPushButton(CROSSOVER_TIMBERING_UI_TEXT["remove_integration"])
        self.integration_details_button = QtWidgets.QPushButton(CROSSOVER_TIMBERING_UI_TEXT["integration_details"])
        self.edit_crossover_button.setToolTip(CROSSOVER_TIMBERING_TOOLTIPS["edit_crossover"])
        self.cancel_edit_button.setToolTip(CROSSOVER_TIMBERING_TOOLTIPS["cancel_edit"])
        self.integrate_hosts_button.setToolTip(CROSSOVER_TIMBERING_TOOLTIPS["integrate_hosts"])
        self.remove_integration_button.setToolTip(CROSSOVER_TIMBERING_TOOLTIPS["remove_integration"])
        self.integration_details_button.setToolTip(CROSSOVER_TIMBERING_TOOLTIPS["integration_details"])
        integration_layout.addWidget(QtWidgets.QLabel("Selected crossover integration"), 0, 0)
        integration_layout.addWidget(self.integration_status, 0, 1, 1, 4)
        integration_layout.addWidget(self.edit_crossover_button, 1, 0)
        integration_layout.addWidget(self.cancel_edit_button, 1, 1)
        integration_layout.addWidget(self.integrate_hosts_button, 1, 2)
        integration_layout.addWidget(self.remove_integration_button, 1, 3)
        integration_layout.addWidget(self.integration_details_button, 1, 4)
        layout.addWidget(integration_group)

        buttons = QtWidgets.QHBoxLayout()
        self.preview_button = QtWidgets.QPushButton("Preview geometry diagnostics")
        self.create_button = QtWidgets.QPushButton("Create crossover")
        self.cancel_extension_button = QtWidgets.QPushButton("Cancel turnout extension")
        self.cancel_extension_button.setVisible(False)
        self.details_button = QtWidgets.QPushButton("Show crossover details")
        self.revert_button = QtWidgets.QPushButton("Convert selected crossover to turnout")
        self.revert_button.setToolTip(
            "Restore the original source turnout where available, or choose which constituent turnout to retain. "
            "The crossover is removed only after the standalone turnout has been rebuilt successfully."
        )
        self.remove_button = QtWidgets.QPushButton("Remove selected crossover")
        self.close_button = QtWidgets.QPushButton("Close")
        for button in (self.preview_button, self.create_button, self.cancel_extension_button, self.details_button, self.revert_button, self.remove_button, self.close_button):
            buttons.addWidget(button)
        layout.addLayout(buttons)

        self.refresh_hosts_button.clicked.connect(self.refresh_hosts)
        self.use_picked_position_button.clicked.connect(self.use_picked_crossover_position)
        self.use_selected_a_button.clicked.connect(lambda: self.use_selected_host(self.host_a_combo))
        self.use_selected_b_button.clicked.connect(lambda: self.use_selected_host(self.host_b_combo))
        self.host_a_combo.currentIndexChanged.connect(self.update_chainage_range)
        self.arrangement_combo.currentIndexChanged.connect(self.update_chainage_range)
        self.gauge_box.valueChanged.connect(self.update_chainage_range)
        self.flangeway_box.valueChanged.connect(self.update_chainage_range)
        self.preview_button.clicked.connect(self.preview_geometry)
        self.create_button.clicked.connect(self.create_crossover)
        self.cancel_extension_button.clicked.connect(self.cancel_turnout_extension)
        self.details_button.clicked.connect(self.show_details)
        self.revert_button.clicked.connect(self.convert_crossover_to_turnout)
        self.remove_button.clicked.connect(self.remove_crossover)
        self.edit_crossover_button.clicked.connect(self.begin_crossover_edit)
        self.cancel_edit_button.clicked.connect(self.cancel_crossover_edit)
        self.integrate_hosts_button.clicked.connect(self.integrate_selected_crossover)
        self.remove_integration_button.clicked.connect(self.remove_selected_integration)
        self.integration_details_button.clicked.connect(self.show_integration_details)
        self.analyse_timber_button.clicked.connect(self.analyse_selected_timbering)
        self.show_conflict_markers_checkbox.toggled.connect(self.set_conflict_marker_visibility)
        self.show_support_markers_checkbox.toggled.connect(self.set_support_marker_visibility)
        self.timber_analysis_details_button.clicked.connect(self.show_timber_analysis_details)
        self.clear_timber_analysis_button.clicked.connect(self.clear_timber_analysis_display)
        self.copy_timber_analysis_button.clicked.connect(self.copy_timber_analysis_summary)
        self.timber_analysis_tolerances_button.clicked.connect(self.edit_timber_analysis_tolerances)
        self.apply_shared_timbers_button.clicked.connect(self.apply_shared_long_timbers)
        self.remove_shared_timbers_button.clicked.connect(self.remove_shared_long_timbers)
        self.shared_timber_details_button.clicked.connect(self.show_shared_timber_details)
        self.shared_timber_settings_button.clicked.connect(self.edit_shared_timber_settings)
        self.show_shared_timbers_checkbox.toggled.connect(self.set_shared_timber_visibility)
        self.apply_b3_button.clicked.connect(self.apply_b3_timbering)
        self.remove_b3_button.clicked.connect(self.remove_b3_timbering)
        self.b3_details_button.clicked.connect(self.show_b3_details)
        self.b3_settings_button.clicked.connect(self.edit_b3_settings)
        self.show_b3_checkbox.toggled.connect(self.set_b3_visibility)
        self.apply_b4_button.clicked.connect(self.apply_b4_timbering)
        self.remove_b4_button.clicked.connect(self.remove_b4_timbering)
        self.b4_details_button.clicked.connect(self.show_b4_details)
        self.show_b4_checkbox.toggled.connect(self.set_b4_visibility)
        # This panel is embedded in the parent manager.  Do not call QDialog.accept()
        # or create a nested modal lifecycle.  The button remains for backwards
        # layout compatibility but is hidden by the unified manager.
        self.close_button.clicked.connect(self.close)
        self.table.itemSelectionChanged.connect(self.update_selection_buttons)
        self.workflow_panel.run_next_button.clicked.connect(self.run_next_guided_step)
        self.workflow_panel.advanced_checkbox.toggled.connect(self.set_guided_advanced_visibility)
        self.workflow_panel.primary_button(0).clicked.connect(self.guided_geometry_primary)
        self.workflow_panel.secondary_button(0).clicked.connect(self.guided_geometry_secondary)
        self.workflow_panel.primary_button(1).clicked.connect(self.guided_timber_primary)
        self.workflow_panel.secondary_button(1).clicked.connect(self.guided_timber_secondary)
        self.workflow_panel.primary_button(2).clicked.connect(self.guided_chair_primary)
        self.workflow_panel.secondary_button(2).clicked.connect(self.guided_chair_secondary)
        self.workflow_panel.primary_button(3).clicked.connect(self.guided_model_support_primary)
        self.workflow_panel.secondary_button(3).clicked.connect(self.guided_model_support_secondary)
        self.workflow_panel.primary_button(4).clicked.connect(self.guided_2d_layout_primary)
        self.workflow_panel.secondary_button(4).clicked.connect(self.guided_2d_layout_secondary)
        self.workflow_panel.primary_button(5).clicked.connect(self.guided_integration_primary)
        self.workflow_panel.secondary_button(5).clicked.connect(self.guided_integration_secondary)
        self.workflow_panel.primary_button(6).clicked.connect(self.guided_export_chairs_primary)
        self.workflow_panel.secondary_button(6).clicked.connect(self.guided_finish_primary)
        self.crossover_legacy_action_buttons = (
            self.preview_button, self.create_button, self.cancel_extension_button, self.details_button,
            self.revert_button, self.remove_button,
        )
        self.set_guided_advanced_visibility(False)
        self.refresh_hosts()
        self.refresh_crossovers()

    def set_guided_advanced_visibility(self, visible):
        show = bool(visible)
        for widget in (
            getattr(self, "crossover_advanced_timber_group", None),
            getattr(self, "chair_analysis_panel", None),
            getattr(self, "crossover_advanced_integration_group", None),
        ):
            if widget is not None:
                widget.setVisible(show)
        extending = bool(getattr(self, "extending_turnout_id", None))
        visibility = {
            self.preview_button: show,
            self.create_button: show,
            self.cancel_extension_button: show and extending,
            self.details_button: show,
            self.revert_button: show,
            self.remove_button: show,
        }
        for button, required in visibility.items():
            button.setVisible(bool(required))
        # This panel remains embedded in the parent manager; never expose its
        # legacy standalone Close action because it would hide the tab content.
        self.close_button.setVisible(False)
        try:
            self.workflow_panel.advanced_checkbox.blockSignals(True)
            self.workflow_panel.advanced_checkbox.setChecked(show)
            self.workflow_panel.advanced_checkbox.blockSignals(False)
        except Exception:
            pass

    def guided_geometry_primary(self):
        if self.editing_crossover_id:
            self.preview_geometry()
        elif self.current_config() is not None:
            self.begin_crossover_edit()
        else:
            self.preview_geometry()
        self.update_guided_workflow()

    def guided_geometry_secondary(self):
        if self.editing_crossover_id:
            self.create_crossover()
        elif self.current_config() is not None:
            self.show_details()
        else:
            self.create_crossover()
        self.update_guided_workflow()

    def guided_timber_primary(self):
        self.apply_b4_timbering()
        self.update_guided_workflow()

    def guided_timber_secondary(self):
        config = self.current_config()
        if config is not None and config.get("b4_result"):
            self.show_b4_details()
        elif config is not None:
            self.analyse_selected_timbering()
        self.update_guided_workflow()

    def guided_chair_primary(self):
        self.chair_analysis_panel.run_analysis()
        self.update_guided_workflow()

    def guided_chair_secondary(self):
        config = self.current_config()
        if config is None:
            return
        if _chair_read_cached_result(self.doc, "crossover", str(config.get("crossover_id") or "")) is not None:
            self.chair_analysis_panel.show_details()
        else:
            self.chair_analysis_panel.edit_settings()
        self.update_guided_workflow()

    def guided_integration_primary(self):
        config = self.current_config()
        if config is None:
            return
        if bool(config.get("integration_active", False)):
            self.remove_selected_integration()
        else:
            self.integrate_selected_crossover()
        self.update_guided_workflow()

    def guided_integration_secondary(self):
        self.show_integration_details()
        self.update_guided_workflow()

    def guided_finish_primary(self):
        self.convert_crossover_to_turnout()
        self.update_guided_workflow()

    def guided_finish_secondary(self):
        self.set_guided_advanced_visibility(True)

    def run_next_guided_step(self):
        config = self.current_config()
        if config is None or self.editing_crossover_id or self.extending_turnout_id:
            try:
                values = self.proposed_values()
                signature = self._preview_signature(values)
                if self._last_preview_signature == signature and self._last_preview_result is not None:
                    self.create_crossover()
                else:
                    self.preview_geometry()
            except Exception as error:
                QtWidgets.QMessageBox.critical(self, crossover_dialog_title("Guided crossover workflow"), str(error))
            self.update_guided_workflow()
            return
        if crossover_b4_effective_status(self.doc, config) != CROSSOVER_B4_STATUS_CLEAR:
            self.apply_b4_timbering()
            self.update_guided_workflow()
            return
        chair_status = chair_analysis_effective_status(self.doc, "crossover", config)
        if chair_status in (CHAIR_STATUS_NOT_ANALYSED, CHAIR_STATUS_STALE):
            self.chair_analysis_panel.run_analysis()
            self.update_guided_workflow()
            return
        if chair_status in (CHAIR_STATUS_INCOMPLETE, CHAIR_STATUS_CONFLICTS, CHAIR_STATUS_CRITICAL):
            QtWidgets.QMessageBox.information(
                self, crossover_dialog_title("Guided workflow stopped"),
                "Chair-position analysis needs review before the guided workflow can continue. No geometry, timbering or readiness gate has been changed.",
            )
            return
        if bool(config.get("integration_active", False)):
            QtWidgets.QMessageBox.information(
                self, crossover_dialog_title("Guided workflow"),
                "The selected crossover has completed every currently available guided stage and is integrated with both host templates.",
            )
            return
        if self.integrate_hosts_button.isEnabled():
            self.integrate_selected_crossover()
            self.update_guided_workflow()
            return
        QtWidgets.QMessageBox.information(
            self, crossover_dialog_title("Guided workflow stopped"),
            "Geometry, automatic timbering and chair-position analysis are available, but the existing host-integration readiness gate is still blocking integration. No geometry or calculation has been bypassed. Open host-integration details or specialist controls to review the stored reason.",
        )

    def update_guided_workflow(self):
        panel = getattr(self, "workflow_panel", None)
        if panel is None:
            return
        config = self.current_config()
        editing = bool(self.editing_crossover_id)
        extending = bool(self.extending_turnout_id)
        preview_current = False
        try:
            preview_current = self._last_preview_signature == self._preview_signature(self.proposed_values()) and self._last_preview_result is not None
        except Exception:
            preview_current = False

        if config is None:
            geometry_status = (
                "A valid geometry preview is ready. Create it transactionally when satisfied."
                if preview_current else
                ("The selected turnout is ready to extend. Confirm the second host and preview the crossover." if extending else "Choose or pick both hosts, the Host A chainage, arrangement and handing, then preview the geometry.")
            )
            panel.set_step(0, geometry_status, "ready",
                           "Preview geometry", True,
                           "Extend turnout" if extending else "Create crossover", bool(preview_current))
            for index, message in (
                (1, "Create a crossover before resolving timbering."),
                (2, "Create and timber the crossover before analysing chair positions."),
                (3, "Integration remains unavailable until the preceding checks pass."),
                (4, "A completed crossover can be reviewed or converted back into a turnout."),
            ):
                panel.set_step(index, message, "waiting", "Continue", False, "", False)
            panel.set_summary("The guided workflow will reuse the established geometry solver and stop before creating anything if topology or geometry validation fails.")
            panel.run_next_button.setText("{}".format("Create previewed crossover" if preview_current else "Run next safe step"))
            return

        identifier = str(config.get("crossover_id") or "the selected crossover")
        if editing:
            panel.set_step(0, "Editing {} transactionally. Preview the revised geometry, then apply it.".format(identifier), "ready",
                           "Preview changes", True, "Apply changes", bool(preview_current))
        else:
            panel.set_step(0, "{} has accepted crossover geometry and topology.".format(identifier), "complete",
                           "Edit position", self.edit_crossover_button.isEnabled(), "Show geometry details", True)

        integration_active = bool(config.get("integration_active", False))
        b4_status = crossover_b4_effective_status(self.doc, config)
        b4_clear = b4_status == CROSSOVER_B4_STATUS_CLEAR
        panel.set_step(1, self._operator_timber_status(b4_status), "complete" if b4_clear else "ready",
                       "Rebuild automatic timbering" if b4_clear else "Resolve timbering automatically",
                       not integration_active,
                       "Show timber result" if config.get("b4_result") else "Analyse timbering", True)

        chair_status = chair_analysis_effective_status(self.doc, "crossover", config)
        chair_state = "ready" if chair_status in (CHAIR_STATUS_NOT_ANALYSED, CHAIR_STATUS_STALE) else (
            "attention" if chair_status in (CHAIR_STATUS_INCOMPLETE, CHAIR_STATUS_CONFLICTS, CHAIR_STATUS_CRITICAL) else "complete"
        )
        chair_cached = _chair_read_cached_result(self.doc, "crossover", identifier) is not None
        panel.set_step(2, chair_status, chair_state, "Analyse chair positions", True,
                       "Show chair details" if chair_cached else "Chair settings", True)

        allowed = bool(config.get("host_integration_allowed")) and b4_clear
        if integration_active:
            integration_status = crossover_host_integration_effective_status(self.doc, config)
            panel.set_step(3, integration_status, "complete", "Remove integration", True, "Integration details", True)
        elif allowed:
            panel.set_step(3, "All existing integration gates report ready.", "ready", "Integrate hosts", True, "Integration details", True)
        else:
            reason = crossover_host_integration_effective_status(self.doc, config)
            panel.set_step(3, reason, "blocked", "Integrate hosts", False, "Integration details", True)

        panel.set_step(4, "Review the managed assembly, retain it, or restore a standalone turnout.", "ready",
                       "Convert to turnout", self.revert_button.isEnabled(), "Show all controls", True)
        panel.set_summary(
            "Selected {}. Work down the steps; invalid geometry, unresolved timbering or a blocked readiness gate stops the sequence without weakening any calculation.".format(identifier)
        )
        panel.run_next_button.setText("Run next safe step")

    def _set_extension_controls(self, enabled):
        locked = bool(enabled)
        self.host_a_combo.setEnabled(not locked)
        self.use_selected_a_button.setEnabled(not locked)
        self.chainage_box.setEnabled(not locked)
        self.arrangement_combo.setEnabled(not locked)
        self.handing_combo.setEnabled(not locked)
        self.gauge_box.setEnabled(not locked)
        self.flangeway_box.setEnabled(not locked)
        for button in self.nudge_buttons:
            button.setEnabled(not locked)
        self.cancel_extension_button.setVisible(locked)
        self.create_button.setText(
            "Extend {} to crossover".format(self.extending_turnout_id)
            if locked else "Create crossover"
        )
        self.use_picked_position_button.setText(
            "Use selected / picked second host"
            if locked else "Use picked crossover position"
        )

    def begin_turnout_extension(self, turnout_config):
        config = dict(turnout_config or {})
        identifier = str(config.get("turnout_id") or "").strip()
        if not identifier:
            raise ValueError("Select a turnout to extend.")
        if turnout_integration_by_id(self.doc, identifier) is not None:
            raise ValueError(
                "Remove the host-template integration before extending {}.".format(identifier)
            )
        self.refresh_hosts()
        host_name = str(config.get("host_object") or "")
        host_index = next(
            (index for index, host in enumerate(self.hosts) if str(getattr(host, "Name", "")) == host_name),
            -1,
        )
        if host_index < 0:
            raise ValueError("The original host centreline for {} is no longer available.".format(identifier))
        self.extending_turnout_id = identifier
        self.extending_turnout_config = config
        self.host_a_combo.setCurrentIndex(host_index)
        orientation = str(config.get("orientation") or TURNOUT_ORIENTATION_FACING)
        arrangement = (
            CROSSOVER_ARRANGEMENT_FACING
            if orientation == TURNOUT_ORIENTATION_FACING
            else CROSSOVER_ARRANGEMENT_TRAILING
        )
        arrangement_index = self.arrangement_combo.findText(arrangement)
        if arrangement_index >= 0:
            self.arrangement_combo.setCurrentIndex(arrangement_index)
        hand_index = self.handing_combo.findText(str(config.get("handing") or ""))
        if hand_index >= 0:
            self.handing_combo.setCurrentIndex(hand_index)
        self.gauge_box.setValue(float(config.get("track_gauge", TURNOUT_DEFAULT_GAUGE)))
        self.flangeway_box.setValue(float(config.get("flangeway", TURNOUT_DEFAULT_FLANGEWAY)))
        self.update_chainage_range()
        self.chainage_box.setValue(float(config.get("toe_chainage", 0.0)))
        if len(self.hosts) > 1 and self.host_b_combo.currentIndex() == host_index:
            self.host_b_combo.setCurrentIndex(0 if host_index != 0 else 1)
        self._last_preview_signature = None
        self._last_preview_result = None
        self._set_extension_controls(True)
        self.selection_status.setText(
            "Extending {} transactionally. Host A, toe chainage, orientation, handing, gauge and flangeway are locked to the existing turnout. Select or click only the second host, then preview.".format(identifier)
        )
        self.diagnostics.setPlainText(
            "Source turnout: {}\nHost A: {}\nToe chainage: {:.3f} mm\nSelect Host B and preview the crossover before committing.".format(
                identifier,
                str(config.get("track_name") or config.get("host_label") or host_name),
                float(config.get("toe_chainage", 0.0)),
            )
        )

    def cancel_turnout_extension(self):
        identifier = self.extending_turnout_id
        self.extending_turnout_id = None
        self.extending_turnout_config = None
        self._last_preview_signature = None
        self._last_preview_result = None
        self._set_extension_controls(False)
        self.selection_status.setText(
            "Turnout extension cancelled. No turnout or crossover objects were changed."
            if identifier else
            "Pick a point on either intended host centreline, then choose Use picked crossover position."
        )

    def begin_crossover_edit(self):
        config = self.current_config()
        if config is None:
            return
        identifier = str(config.get("crossover_id") or "")
        self.refresh_hosts()
        indices = {}
        for side in ("a", "b"):
            name = str(config.get("host_{}_object".format(side)) or "")
            indices[side] = next((i for i, host in enumerate(self.hosts) if str(getattr(host, "Name", "")) == name), -1)
        if indices["a"] < 0 or indices["b"] < 0:
            QtWidgets.QMessageBox.critical(self, crossover_dialog_title("Crossover editing"), "One or both original host centrelines are no longer available.")
            return
        self.editing_crossover_id = identifier
        self.editing_crossover_config = dict(config)
        self.host_a_combo.setCurrentIndex(indices["a"])
        self.host_b_combo.setCurrentIndex(indices["b"])
        self.update_chainage_range()
        self.chainage_box.setValue(float(config.get("toe_chainage_a") or 0.0))
        for combo, value in ((self.arrangement_combo, config.get("arrangement")), (self.handing_combo, config.get("handing"))):
            index = combo.findText(str(value or ""))
            if index >= 0:
                combo.setCurrentIndex(index)
        self.gauge_box.setValue(float(config.get("track_gauge", TURNOUT_DEFAULT_GAUGE)))
        self.flangeway_box.setValue(float(config.get("flangeway", TURNOUT_DEFAULT_FLANGEWAY)))
        self.minimum_radius_box.setValue(float(config.get("minimum_requested_radius", CROSSOVER_DEFAULT_MINIMUM_RADIUS)))
        self.create_button.setText("Apply crossover changes")
        self.cancel_edit_button.setVisible(True)
        self._last_preview_signature = None
        self._last_preview_result = None
        self.selection_status.setText("Editing {}. Adjust hosts or exact Host A chainage, preview the geometry, then apply changes transactionally. Active host integration will be restored automatically inside the same transaction.".format(identifier))
        self.preview_geometry()

    def cancel_crossover_edit(self):
        identifier = self.editing_crossover_id
        self.editing_crossover_id = None
        self.editing_crossover_config = None
        self._last_preview_signature = None
        self._last_preview_result = None
        self.cancel_edit_button.setVisible(False)
        self.create_button.setText("Create crossover")
        self.selection_status.setText("Editing {} cancelled. No crossover geometry changed.".format(identifier) if identifier else "Select or create a crossover.")

    def current_host(self, combo):
        index = combo.currentIndex()
        return self.hosts[index] if 0 <= index < len(self.hosts) else None

    def _host_index_for_object(self, obj):
        object_name = str(getattr(obj, "Name", ""))
        for index, host in enumerate(self.hosts):
            if str(getattr(host, "Name", "")) == object_name:
                return index
        return -1

    def _selection_host_entries(self):
        if Gui is None:
            return []
        try:
            selection_ex = list(Gui.Selection.getSelectionEx())
        except Exception:
            selection_ex = []
        entries = []
        seen = set()
        for selected_ex in selection_ex:
            selected = getattr(selected_ex, "Object", None)
            index = self._host_index_for_object(selected)
            if index < 0 or index in seen:
                continue
            seen.add(index)
            entries.append({
                "index": index,
                "host": self.hosts[index],
                "picked": list(getattr(selected_ex, "PickedPoints", []) or []),
            })
        return entries

    def _nearest_compatible_host_index(self, anchor_host, point):
        anchor_name = str(getattr(anchor_host, "Name", ""))
        anchor_set = object_string_property(anchor_host, "TemplateSetID", "")
        best = None
        for index, candidate in enumerate(self.hosts):
            if str(getattr(candidate, "Name", "")) == anchor_name:
                continue
            candidate_set = object_string_property(candidate, "TemplateSetID", "")
            if anchor_set and candidate_set and candidate_set != anchor_set:
                continue
            try:
                _station, _nearest, _heading, separation = _crossover_nearest_point_on_alignment(
                    turnout_host_alignment(candidate), point
                )
            except Exception:
                continue
            score = float(separation)
            if best is None or score < best[0]:
                best = (score, index)
        return best[1] if best is not None else -1

    def nudge_chainage(self, amount):
        value = float(self.chainage_box.value()) + float(amount)
        value = min(max(value, float(self.chainage_box.minimum())), float(self.chainage_box.maximum()))
        self.chainage_box.setValue(value)

    def use_picked_crossover_position(self):
        entries = self._selection_host_entries()
        if getattr(self, "extending_turnout_id", None):
            if not entries:
                QtWidgets.QMessageBox.information(
                    self,
                    crossover_dialog_title("Second crossover host"),
                    "Select or click the second generated host centreline, then try again.",
                )
                return
            host_a = self.current_host(self.host_a_combo)
            host_a_name = str(getattr(host_a, "Name", ""))
            candidate = next(
                (entry for entry in reversed(entries) if str(getattr(entry["host"], "Name", "")) != host_a_name),
                None,
            )
            if candidate is None:
                QtWidgets.QMessageBox.information(
                    self,
                    crossover_dialog_title("Second crossover host"),
                    "The selected line is the turnout's existing host. Select or click the adjacent second host instead.",
                )
                return
            self.host_b_combo.setCurrentIndex(candidate["index"])
            self._last_preview_signature = None
            self._last_preview_result = None
            self.selection_status.setText(
                "Selected Host B: {}. {} remains fixed at toe chainage {:.3f} mm on Host A. Preview diagnostics before extension.".format(
                    str(getattr(candidate["host"], "Label", getattr(candidate["host"], "Name", "Host B"))),
                    self.extending_turnout_id,
                    float(self.chainage_box.value()),
                )
            )
            self.preview_geometry()
            return
        if not entries:
            QtWidgets.QMessageBox.information(
                self,
                crossover_dialog_title("Picked crossover position"),
                "Click one recognised generated centreline at the required crossover position. "
                "You may Control-select the second host first or let the manager choose the nearest compatible host automatically.",
            )
            return

        anchor = None
        for entry in reversed(entries):
            if entry["picked"]:
                anchor = entry
                break
        if anchor is None:
            anchor = entries[-1]

        anchor_host = anchor["host"]
        anchor_index = anchor["index"]
        anchor_data = turnout_host_alignment(anchor_host)
        if anchor["picked"]:
            picked_point = anchor["picked"][-1]
        else:
            station = min(max(float(self.chainage_box.value()), 0.0), float(anchor_data["total"]))
            picked_point, _heading = interpolate_alignment_station(anchor_data, station)

        other_index = -1
        for entry in entries:
            if entry["index"] != anchor_index:
                other_index = entry["index"]
                break
        if other_index < 0:
            other_index = self._nearest_compatible_host_index(anchor_host, picked_point)
        if other_index < 0:
            QtWidgets.QMessageBox.information(
                self,
                crossover_dialog_title("Picked crossover position"),
                "No second compatible generated host centreline could be resolved. Select both intended hosts and try again.",
            )
            return

        self.host_a_combo.blockSignals(True)
        self.host_b_combo.blockSignals(True)
        self.host_a_combo.setCurrentIndex(anchor_index)
        self.host_b_combo.setCurrentIndex(other_index)
        self.host_a_combo.blockSignals(False)
        self.host_b_combo.blockSignals(False)
        self.update_chainage_range()
        projected = nearest_alignment_station(anchor_data, picked_point)
        projected = min(max(projected, float(self.chainage_box.minimum())), float(self.chainage_box.maximum()))
        self.chainage_box.setValue(projected)
        self.selection_status.setText(
            "Picked {:.3f} mm on Host A: {}. Host B: {}. Preview diagnostics before creation.".format(
                projected,
                str(getattr(anchor_host, "Label", getattr(anchor_host, "Name", "Host A"))),
                str(getattr(self.hosts[other_index], "Label", getattr(self.hosts[other_index], "Name", "Host B"))),
            )
        )
        self.preview_geometry()

    def use_selected_host(self, combo):
        if getattr(self, "extending_turnout_id", None) and combo is self.host_a_combo:
            return
        entries = self._selection_host_entries()
        for entry in reversed(entries):
            combo.setCurrentIndex(entry["index"])
            if entry["picked"]:
                picked_point = entry["picked"][-1]
                try:
                    if combo is self.host_a_combo:
                        data = turnout_host_alignment(entry["host"])
                    else:
                        host_a = self.current_host(self.host_a_combo)
                        data = turnout_host_alignment(host_a) if host_a is not None else None
                    if data is not None:
                        projected = nearest_alignment_station(data, picked_point)
                        projected = min(max(projected, float(self.chainage_box.minimum())), float(self.chainage_box.maximum()))
                        self.chainage_box.setValue(projected)
                except Exception:
                    pass
            self.selection_status.setText(
                "Selected {}. A picked point on either host also updates the Host A crossover reference position.".format(
                    "Host A" if combo is self.host_a_combo else "Host B"
                )
            )
            return
        QtWidgets.QMessageBox.information(
            self,
            crossover_dialog_title("Crossover host selection"),
            "Select or click one recognised generated centreline in the FreeCAD tree or 3D view, then try again.",
        )

    def refresh_hosts(self):
        self._last_preview_signature = None
        self._last_preview_result = None
        current_a = str(getattr(self.current_host(self.host_a_combo), "Name", "")) if self.hosts else ""
        current_b = str(getattr(self.current_host(self.host_b_combo), "Name", "")) if self.hosts else ""
        self.hosts = turnout_host_objects(self.doc)
        for combo, current in ((self.host_a_combo, current_a), (self.host_b_combo, current_b)):
            combo.blockSignals(True)
            combo.clear()
            selected = 0
            for index, host in enumerate(self.hosts):
                combo.addItem(turnout_host_label(host))
                if str(host.Name) == current:
                    selected = index
            combo.setCurrentIndex(selected if self.hosts else -1)
            combo.blockSignals(False)
        if len(self.hosts) > 1 and self.host_b_combo.currentIndex() == self.host_a_combo.currentIndex():
            self.host_b_combo.setCurrentIndex(1)
        self.update_chainage_range()

    def update_chainage_range(self):
        host = self.current_host(self.host_a_combo)
        if host is None:
            self.chainage_box.setRange(0.0, 0.0)
            return
        try:
            data = turnout_host_alignment(host)
            dimensions = rea_c10_dimensions(self.gauge_box.value(), self.flangeway_box.value())
            orientation = (
                TURNOUT_ORIENTATION_FACING
                if str(self.arrangement_combo.currentText()) == CROSSOVER_ARRANGEMENT_FACING
                else TURNOUT_ORIENTATION_TRAILING
            )
            minimum, maximum = turnout_valid_toe_range(data["total"], dimensions, orientation)
            previous = self.chainage_box.value()
            self.chainage_box.setRange(minimum, max(minimum, maximum))
            self.chainage_box.setValue(min(max(previous, minimum), max(minimum, maximum)))
        except Exception as error:
            self.diagnostics.setPlainText(str(error))

    def proposed_values(self):
        return (
            self.current_host(self.host_a_combo),
            self.current_host(self.host_b_combo),
            float(self.chainage_box.value()),
            str(self.arrangement_combo.currentText()),
            str(self.handing_combo.currentText()),
            float(self.gauge_box.value()),
            float(self.flangeway_box.value()),
            float(self.minimum_radius_box.value()),
        )

    def _preview_signature(self, values):
        host_a, host_b, chainage, arrangement, handing, gauge, flangeway, minimum_radius = values
        return (
            str(getattr(host_a, "Name", "")),
            str(getattr(host_b, "Name", "")),
            round(float(chainage), 7),
            str(arrangement),
            str(handing),
            round(float(gauge), 7),
            round(float(flangeway), 7),
            round(float(minimum_radius), 7),
            str(getattr(self, "extending_turnout_id", None) or ""),
            str(getattr(self, "editing_crossover_id", None) or ""),
        )

    def preview_geometry(self):
        values = self.proposed_values()
        signature = self._preview_signature(values)
        if self._last_preview_signature == signature and self._last_preview_result is not None:
            self.diagnostics.setPlainText(crossover_geometry_diagnostics_text(self._last_preview_result))
            return self._last_preview_result
        try:
            result = solve_rea_c10_crossover_geometry(
                self.doc, *values,
                ignored_crossover_id=getattr(self, "editing_crossover_id", None),
                ignored_turnout_id=getattr(self, "extending_turnout_id", None),
            )
            self._last_preview_signature = signature
            self._last_preview_result = result
            self.diagnostics.setPlainText(crossover_geometry_diagnostics_text(result))
            return result
        except Exception as error:
            self._last_preview_signature = None
            self._last_preview_result = None
            trace_text = crossover_solver_trace_text()
            rejection_text = "REJECTED\n{}\n\nDETAILED SOLVER TRACE\n{}".format(error, trace_text)
            self.diagnostics.setPlainText(rejection_text)
            try:
                App.Console.PrintWarning("{}\n".format(rejection_text))
            except Exception:
                pass
            return None

    def create_crossover(self):
        result = self.preview_geometry()
        if result is None:
            return
        extending = bool(getattr(self, "extending_turnout_id", None))
        editing = bool(getattr(self, "editing_crossover_id", None))
        answer = QtWidgets.QMessageBox.question(
            self,
            crossover_dialog_title(
                "Extend turnout to crossover" if extending else ("Apply crossover changes" if editing else "Create managed crossover geometry")
            ),
            (
                "Replace {} with this managed crossover in one transaction? The original turnout remains untouched if any validation, geometry, object or production-record step fails. Timber outlines start as inherited references; run the analyser and build the shared long-timber envelope afterwards. Host integration stays blocked."
                .format(self.extending_turnout_id)
                if extending else (
                    "Apply these geometry changes to {} in one transaction? Its stable crossover identity is retained, while earlier timber-analysis and resolution results are invalidated and must be rebuilt before host integration.".format(self.editing_crossover_id)
                    if editing else
                    "Create this managed crossover geometry now? Timber outlines start as inherited reference geometry; the shared long-timber envelope can then be built and resolved."
                )
            ),
            QtWidgets.QMessageBox.Yes | QtWidgets.QMessageBox.No,
            QtWidgets.QMessageBox.No,
        )
        if answer != QtWidgets.QMessageBox.Yes:
            return
        previous_text = self.diagnostics.toPlainText()
        self.create_button.setEnabled(False)
        self.diagnostics.setPlainText(
            "Building the two turnout modules and connecting template...\n"
            "The validated preview is being reused; FreeCAD Part booleans may still take a moment."
        )
        try:
            QtWidgets.QApplication.setOverrideCursor(QtCore.Qt.WaitCursor)
            QtWidgets.QApplication.processEvents()
        except Exception:
            pass
        try:
            if editing:
                config = edit_rea_c10_crossover(
                    self.doc,
                    self.editing_crossover_id,
                    *self.proposed_values(),
                    pre_solved=result,
                )
            elif extending:
                host_b = self.current_host(self.host_b_combo)
                config = extend_turnout_to_rea_c10_crossover(
                    self.doc,
                    self.extending_turnout_id,
                    host_b,
                    self.minimum_radius_box.value(),
                    pre_solved=result,
                )
            else:
                config = create_rea_c10_crossover(
                    self.doc, *self.proposed_values(), pre_solved=result
                )
            source_turnout = self.extending_turnout_id
            edited_crossover = self.editing_crossover_id
            self._last_preview_signature = None
            self._last_preview_result = None
            if editing:
                self.editing_crossover_id = None
                self.editing_crossover_config = None
                self.cancel_edit_button.setVisible(False)
                self.create_button.setText("Create crossover")
            if extending:
                self.extending_turnout_id = None
                self.extending_turnout_config = None
                self._set_extension_controls(False)
                callback = getattr(self, "turnout_refresh_callback", None)
                if callable(callback):
                    callback()
            self.refresh_crossovers(config.get("crossover_id"))
            self.diagnostics.setPlainText(
                "{} {} transactionally.\n\n{}".format(
                    "Extended {} into".format(source_turnout) if extending else ("Updated" if edited_crossover else "Created"),
                    config.get("crossover_id"),
                    previous_text,
                )
            )
        except Exception as error:
            self.diagnostics.setPlainText(previous_text)
            QtWidgets.QMessageBox.critical(self, crossover_dialog_title("Crossover creation error"), str(error))
        finally:
            self.create_button.setEnabled(True)
            try:
                QtWidgets.QApplication.restoreOverrideCursor()
            except Exception:
                pass

    @staticmethod
    def _operator_timber_status(status):
        text = str(status or "")
        replacements = (
            ("B3 interlacing/shoving", "Interlacing and timber movement"),
            ("B4 hybrid timbering", "Automatic timbering"),
            ("A8A6B3", "controlled timber adjustment"),
            ("A8A6B4", "automatic timber resolution"),
            ("A8A6B2A2", "shared long-timber envelope"),
        )
        for old, new in replacements:
            text = text.replace(old, new)
        return text

    def refresh_crossovers(self, selected_id=None):
        self.crossovers = existing_crossover_configs(self.doc)
        self.table.setRowCount(len(self.crossovers))
        selected_row = -1
        for row, config in enumerate(self.crossovers):
            values = (
                config.get("crossover_id", ""),
                config.get("host_a_track_name", config.get("host_a_label", "")),
                config.get("host_b_track_name", config.get("host_b_label", "")),
                config.get("arrangement", ""),
                config.get("handing", ""),
                "{:.3f}".format(float(config.get("toe_chainage_a") or 0.0)),
                "{:.3f}".format(float(config.get("toe_chainage_b") or 0.0)),
                "{} | {} | {} | {}".format(
                    self._operator_timber_status(config.get("timber_analysis_status", CROSSOVER_TIMBER_ANALYSIS_STATUS_NOT_ANALYSED)),
                    self._operator_timber_status(config.get("shared_timber_status", CROSSOVER_SHARED_TIMBER_STATUS_NOT_APPLIED)),
                    self._operator_timber_status(config.get("b3_status", CROSSOVER_B3_STATUS_NOT_APPLIED)),
                    self._operator_timber_status(config.get("b4_status", CROSSOVER_B4_STATUS_NOT_APPLIED)),
                ),
                crossover_host_integration_effective_status(self.doc, config),
            )
            for column, value in enumerate(values):
                self.table.setItem(row, column, QtWidgets.QTableWidgetItem(str(value)))
            if selected_id and str(config.get("crossover_id")) == str(selected_id):
                selected_row = row
        if selected_row >= 0:
            self.table.selectRow(selected_row)
        self.update_selection_buttons()

    def current_config(self):
        row = self.table.currentRow()
        return self.crossovers[row] if 0 <= row < len(self.crossovers) else None

    def update_selection_buttons(self):
        config = self.current_config()
        selected = config is not None
        integration_active = selected and bool((config or {}).get("integration_active", False))
        self.details_button.setEnabled(selected)
        self.revert_button.setEnabled(selected)
        self.remove_button.setEnabled(selected)
        self.analyse_timber_button.setEnabled(selected)
        self.timber_analysis_details_button.setEnabled(selected)
        self.clear_timber_analysis_button.setEnabled(selected)
        self.copy_timber_analysis_button.setEnabled(selected)
        self.timber_analysis_tolerances_button.setEnabled(selected)
        self.show_conflict_markers_checkbox.setEnabled(selected)
        self.show_support_markers_checkbox.setEnabled(selected)
        self.apply_shared_timbers_button.setEnabled(selected and not integration_active)
        self.remove_shared_timbers_button.setEnabled(selected and not integration_active and bool((config or {}).get("shared_timber_result")))
        self.shared_timber_details_button.setEnabled(selected and bool((config or {}).get("shared_timber_result")))
        self.shared_timber_settings_button.setEnabled(selected and not integration_active)
        self.show_shared_timbers_checkbox.setEnabled(selected and not integration_active and bool((config or {}).get("shared_timber_result")))
        shared_current = selected and bool((config or {}).get("shared_timber_result")) and crossover_shared_timber_effective_status(self.doc, config) != CROSSOVER_SHARED_TIMBER_STATUS_STALE
        self.apply_b3_button.setEnabled(bool(shared_current and not integration_active))
        self.remove_b3_button.setEnabled(selected and not integration_active and bool((config or {}).get("b3_result")))
        self.b3_details_button.setEnabled(selected and bool((config or {}).get("b3_result")))
        self.b3_settings_button.setEnabled(bool(shared_current and not integration_active))
        self.show_b3_checkbox.setEnabled(selected and not integration_active and bool((config or {}).get("b3_result")))
        self.apply_b4_button.setEnabled(selected and not integration_active)
        self.remove_b4_button.setEnabled(selected and not integration_active and bool((config or {}).get("b4_result")))
        self.b4_details_button.setEnabled(selected and bool((config or {}).get("b4_result")))
        self.show_b4_checkbox.setEnabled(selected and not integration_active and bool((config or {}).get("b4_result")))
        b4_ready = selected and crossover_b4_effective_status(self.doc, config) == CROSSOVER_B4_STATUS_CLEAR and bool((config or {}).get("host_integration_allowed"))
        self.edit_crossover_button.setEnabled(selected and not bool(getattr(self, "extending_turnout_id", None)))
        self.integrate_hosts_button.setEnabled(bool(b4_ready and not integration_active))
        self.remove_integration_button.setEnabled(bool(integration_active))
        self.integration_details_button.setEnabled(selected)
        if selected:
            self.timber_analysis_settings = normalise_crossover_timber_analysis_settings(
                config.get("timber_analysis_settings")
            )
            self.show_conflict_markers_checkbox.blockSignals(True)
            self.show_support_markers_checkbox.blockSignals(True)
            self.show_conflict_markers_checkbox.setChecked(bool(self.timber_analysis_settings.get("show_conflict_markers", True)))
            self.show_support_markers_checkbox.setChecked(bool(self.timber_analysis_settings.get("show_support_markers", False)))
            self.show_conflict_markers_checkbox.blockSignals(False)
            self.show_support_markers_checkbox.blockSignals(False)
            self.shared_timber_settings = normalise_crossover_shared_timber_settings(config.get("shared_timber_settings"))
            self.show_shared_timbers_checkbox.blockSignals(True)
            self.show_shared_timbers_checkbox.setChecked(bool(self.shared_timber_settings.get("show_shared_timber_geometry", True)))
            self.show_shared_timbers_checkbox.blockSignals(False)
            self.b3_settings = normalise_crossover_b3_settings(config.get("b3_settings"))
            self.show_b3_checkbox.blockSignals(True)
            self.show_b3_checkbox.setChecked(bool(self.b3_settings.get("show_b3_geometry", True)))
            self.show_b3_checkbox.blockSignals(False)
            self.b4_settings = normalise_crossover_b4_settings(config.get("b4_settings"))
            self.show_b4_checkbox.blockSignals(True)
            self.show_b4_checkbox.setChecked(bool(self.b4_settings.get("show_b4_geometry", True)))
            self.show_b4_checkbox.blockSignals(False)
            self.timber_analysis_status.setText("{} | {} | {} | {}".format(
                self._operator_timber_status(crossover_timber_analysis_effective_status(self.doc, config)),
                self._operator_timber_status(crossover_shared_timber_effective_status(self.doc, config)),
                self._operator_timber_status(crossover_b3_effective_status(self.doc, config)),
                self._operator_timber_status(crossover_b4_effective_status(self.doc, config)),
            ))
            self.integration_status.setText(crossover_host_integration_effective_status(self.doc, config))
        else:
            self.timber_analysis_status.setText("Select a managed crossover to analyse or resolve its timbering.")
            self.integration_status.setText("Select a managed crossover to edit or integrate.")
        if hasattr(self, "chair_analysis_panel"):
            self.chair_analysis_panel.refresh()
        if hasattr(self, "workflow_panel"):
            self.update_guided_workflow()

    def edit_timber_analysis_tolerances(self):
        config = self.current_config()
        if config is None:
            return
        settings = normalise_crossover_timber_analysis_settings(self.timber_analysis_settings)
        dialog = QtWidgets.QDialog(self)
        dialog.setWindowTitle(crossover_dialog_title("Timber analysis tolerances"))
        layout = QtWidgets.QFormLayout(dialog)
        boxes = {}
        specifications = (
            ("intersection_tolerance", "Intersection tolerance", 0.001, 5.0, 3),
            ("near_touching_tolerance", "Near-touching tolerance", 0.01, 10.0, 3),
            ("minimum_clear_spacing", "Minimum clear spacing", 0.01, 20.0, 3),
            ("same_station_tolerance", "Same longitudinal-position tolerance", 0.01, 20.0, 3),
            ("maximum_advisory_skew_degrees", "Maximum advisory skew", 0.1, 45.0, 2),
        )
        for key, label, minimum, maximum, decimals in specifications:
            box = QtWidgets.QDoubleSpinBox()
            box.setDecimals(decimals)
            box.setRange(minimum, maximum)
            box.setValue(float(settings[key]))
            box.setSuffix("°" if key == "maximum_advisory_skew_degrees" else " mm")
            analysis_tips = {
                "intersection_tolerance": "Permitted numerical overlap before timber bodies count as intersecting.",
                "near_touching_tolerance": "Maximum end gap reported as near-touching rather than clearly separated.",
                "minimum_clear_spacing": "Minimum acceptable physical clearance between independent timber bodies.",
                "same_station_tolerance": "Maximum longitudinal centre difference treated as the same timber position.",
                "maximum_advisory_skew_degrees": "Skew above this value is reported for ordinary single-road timbers.",
            }
            box.setToolTip(analysis_tips[key])
            layout.addRow(label, box)
            boxes[key] = box
        cache_box = QtWidgets.QCheckBox("Reuse cached results when geometry and tolerances are unchanged")
        cache_box.setChecked(bool(settings.get("cache_enabled", True)))
        layout.addRow("Analysis cache", cache_box)
        note = QtWidgets.QLabel(
            "These are configurable model-scale manufacturing assumptions. Prototype timber and protected-support positions remain source-derived."
        )
        note.setWordWrap(True)
        layout.addRow(note)
        button_box = QtWidgets.QDialogButtonBox(QtWidgets.QDialogButtonBox.Ok | QtWidgets.QDialogButtonBox.Cancel)
        button_box.accepted.connect(dialog.accept)
        button_box.rejected.connect(dialog.reject)
        layout.addRow(button_box)
        if dialog.exec_() != QtWidgets.QDialog.Accepted:
            return
        for key, box in boxes.items():
            settings[key] = float(box.value())
        settings["cache_enabled"] = bool(cache_box.isChecked())
        settings["show_conflict_markers"] = bool(self.show_conflict_markers_checkbox.isChecked())
        settings["show_support_markers"] = bool(self.show_support_markers_checkbox.isChecked())
        self.timber_analysis_settings = normalise_crossover_timber_analysis_settings(settings)
        self.timber_analysis_status.setText("Tolerance changes will apply to the next analysis.")

    def analyse_selected_timbering(self):
        config = self.current_config()
        if config is None:
            return
        identifier = str(config.get("crossover_id") or "")
        settings = normalise_crossover_timber_analysis_settings(self.timber_analysis_settings)
        settings["show_conflict_markers"] = bool(self.show_conflict_markers_checkbox.isChecked())
        settings["show_support_markers"] = bool(self.show_support_markers_checkbox.isChecked())
        self.analyse_timber_button.setEnabled(False)
        cursor_active = False
        try:
            QtWidgets.QApplication.setOverrideCursor(QtCore.Qt.WaitCursor)
            cursor_active = True
            QtWidgets.QApplication.processEvents()
        except Exception:
            pass
        try:
            result = analyse_rea_c10_crossover_timbering(self.doc, identifier, settings)
            self.timber_analysis_settings = normalise_crossover_timber_analysis_settings(result.get("settings"))
            self.refresh_crossovers(identifier)
            summary = crossover_timber_analysis_summary(result, include_findings=False)
            self.diagnostics.setPlainText(summary)
            self.timber_analysis_status.setText(str(result.get("analysis_status") or ""))
        except Exception as error:
            QtWidgets.QMessageBox.critical(
                self,
                crossover_dialog_title("Timber analysis error"),
                str(error),
            )
        finally:
            self.analyse_timber_button.setEnabled(self.current_config() is not None)
            if cursor_active:
                try:
                    QtWidgets.QApplication.restoreOverrideCursor()
                except Exception:
                    pass

    def set_conflict_marker_visibility(self, visible):
        config = self.current_config()
        if config is None:
            return
        self.timber_analysis_settings["show_conflict_markers"] = bool(visible)
        set_crossover_timber_analysis_visibility(
            self.doc, config.get("crossover_id"), conflicts=bool(visible)
        )

    def set_support_marker_visibility(self, visible):
        config = self.current_config()
        if config is None:
            return
        self.timber_analysis_settings["show_support_markers"] = bool(visible)
        set_crossover_timber_analysis_visibility(
            self.doc, config.get("crossover_id"), supports=bool(visible)
        )

    def _selected_cached_timber_analysis(self):
        config = self.current_config()
        if config is None:
            return None
        return _cached_crossover_timber_analysis(self.doc, config.get("crossover_id"))

    def show_timber_analysis_details(self):
        result = self._selected_cached_timber_analysis()
        if result is None:
            QtWidgets.QMessageBox.information(
                self,
                crossover_dialog_title("Timber analysis details"),
                "This crossover has not yet been analysed.",
            )
            return
        dialog = QtWidgets.QDialog(self)
        dialog.setWindowTitle(crossover_dialog_title("Timber analysis details"))
        dialog.resize(900, 700)
        layout = QtWidgets.QVBoxLayout(dialog)
        details = QtWidgets.QPlainTextEdit()
        details.setReadOnly(True)
        config = self.current_config()
        status = crossover_timber_analysis_effective_status(self.doc, config) if config is not None else ""
        text = crossover_timber_analysis_summary(result, include_findings=True)
        if status == CROSSOVER_TIMBER_ANALYSIS_STATUS_STALE:
            text = "WARNING: Analysis stale — rerun the analyser before using these findings.\n\n" + text
        details.setPlainText(text)
        layout.addWidget(details)
        buttons = QtWidgets.QDialogButtonBox(QtWidgets.QDialogButtonBox.Close)
        buttons.rejected.connect(dialog.reject)
        buttons.clicked.connect(dialog.accept)
        layout.addWidget(buttons)
        dialog.exec_()

    def copy_timber_analysis_summary(self):
        result = self._selected_cached_timber_analysis()
        if result is None:
            QtWidgets.QMessageBox.information(
                self,
                crossover_dialog_title("Copy timber analysis summary"),
                "Analyse the selected crossover first.",
            )
            return
        text = crossover_timber_analysis_summary(result, include_findings=True)
        config = self.current_config()
        if config is not None and crossover_timber_analysis_effective_status(self.doc, config) == CROSSOVER_TIMBER_ANALYSIS_STATUS_STALE:
            text = "WARNING: Analysis stale — rerun the analyser before using these findings.\n\n" + text
        QtWidgets.QApplication.clipboard().setText(text)
        self.timber_analysis_status.setText("Readable timber analysis summary copied to the clipboard.")

    def clear_timber_analysis_display(self):
        config = self.current_config()
        if config is None:
            return
        try:
            removed = clear_crossover_timber_analysis_display(
                self.doc, config.get("crossover_id")
            )
            self.timber_analysis_status.setText(
                "Cleared {} temporary analysis object(s); cached analysis metadata remains available.".format(removed)
            )
        except Exception as error:
            QtWidgets.QMessageBox.critical(
                self,
                crossover_dialog_title("Clear timber analysis display error"),
                str(error),
            )


    def edit_shared_timber_settings(self):
        config = self.current_config()
        if config is None:
            return
        settings = normalise_crossover_shared_timber_settings(self.shared_timber_settings)
        dialog = QtWidgets.QDialog(self)
        dialog.setWindowTitle(crossover_dialog_title("Shared long-timber settings"))
        layout = QtWidgets.QFormLayout(dialog)
        specifications = (
            ("maximum_station_offset", "Maximum longitudinal timber-centre offset", 0.01, 20.0, 3, " mm"),
            ("maximum_angle_difference_degrees", "Maximum angular difference", 0.01, 15.0, 2, "°"),
            ("maximum_width_expansion", "Maximum width expansion", 0.0, 5.0, 3, " mm"),
            ("end_allowance", "Additional timber-end allowance", 0.0, 20.0, 3, " mm"),
            ("maximum_shared_timber_length", "Maximum shared timber length (0 = unlimited)", 0.0, 1000.0, 3, " mm"),
            ("collision_tolerance", "Unaffected-timber collision tolerance", 0.0, 5.0, 3, " mm²"),
            ("envelope_spacing_prototype_inches", "Maximum connector sleeper spacing", 12.0, 36.0, 2, " prototype in"),
            ("envelope_clearance", "Minimum clearance between independent sleepers", 0.0, 5.0, 3, " mm"),
            ("long_timber_envelope_allowance", "Long-timber envelope allowance", 0.0, 10.0, 3, " mm"),
            ("maximum_envelope_skew_degrees", "Maximum shared-envelope skew", 0.25, 30.0, 2, "°"),
        )
        boxes = {}
        for key, label, minimum, maximum, decimals, suffix in specifications:
            box = QtWidgets.QDoubleSpinBox()
            box.setDecimals(decimals)
            box.setRange(minimum, maximum)
            box.setValue(float(settings[key]))
            box.setSuffix(suffix)
            shared_tips = {
                "maximum_station_offset": "Largest longitudinal centre offset permitted when matching inherited timbers for a shared long timber.",
                "maximum_angle_difference_degrees": "Largest angular difference permitted between inherited timber candidates.",
                "maximum_width_expansion": "Maximum permitted increase in timber width when forming a shared candidate.",
                "end_allowance": "Additional length added beyond the outermost required support at each timber end.",
                "maximum_shared_timber_length": "Rejects a shared timber longer than this value; zero leaves the length unlimited.",
                "collision_tolerance": "Small polygon-overlap area ignored when checking unaffected neighbouring timbers.",
                "envelope_spacing_prototype_inches": "Maximum prototype spacing used when fitting connector timbers through the envelope.",
                "envelope_clearance": "Physical clearance required before two normal-width sleepers count as independent.",
                "long_timber_envelope_allowance": "Extends a timber into the long-timber envelope when its normal footprint lies within this extra margin of the interference boundary.",
                "maximum_envelope_skew_degrees": "Maximum accepted orientation difference for a timber supporting more than one road.",
            }
            box.setToolTip(shared_tips[key])
            layout.addRow(label, box)
            boxes[key] = box
        confirmation_box = QtWidgets.QSpinBox()
        confirmation_box.setRange(1, 10)
        confirmation_box.setValue(int(settings["envelope_return_confirmation_count"]))
        confirmation_box.setToolTip("Number of consecutive clear sleeper positions required before the envelope returns to ordinary Main template width.")
        layout.addRow("Consecutive clear sleeper positions before returning to plain track", confirmation_box)
        plain_connector_box = QtWidgets.QCheckBox("Generate nominal-width sleepers through any clear connector section")
        plain_connector_box.setChecked(bool(settings.get("generate_plain_connector_sleepers", True)))
        plain_connector_box.setToolTip("Creates normal-width sleepers in any connector section where both roads have safely left the shared long-timber envelope.")
        layout.addRow(plain_connector_box)
        note = QtWidgets.QLabel(
            "The minimum clearance is the physical separation rule. The long-timber envelope allowance adds a conservative margin, so borderline inherited timbers remain inside a continuous long-timber run. Nominal sleeper length comes from each host Main template width. Building the envelope never shoves, twists, shortens, omits or interlaces inherited timbering; use controlled timber adjustment afterwards where required."
        )
        note.setWordWrap(True)
        layout.addRow(note)
        buttons = QtWidgets.QDialogButtonBox(QtWidgets.QDialogButtonBox.Ok | QtWidgets.QDialogButtonBox.Cancel)
        buttons.accepted.connect(dialog.accept)
        buttons.rejected.connect(dialog.reject)
        layout.addRow(buttons)
        if dialog.exec_() != QtWidgets.QDialog.Accepted:
            return
        for key, box in boxes.items():
            settings[key] = float(box.value())
        settings["envelope_return_confirmation_count"] = int(confirmation_box.value())
        settings["generate_plain_connector_sleepers"] = bool(plain_connector_box.isChecked())
        settings["show_shared_timber_geometry"] = bool(self.show_shared_timbers_checkbox.isChecked())
        self.shared_timber_settings = normalise_crossover_shared_timber_settings(settings)
        self.timber_analysis_status.setText("Shared-timber setting changes will apply to the next resolution.")

    def apply_shared_long_timbers(self):
        config = self.current_config()
        if config is None:
            return
        identifier = str(config.get("crossover_id") or "")
        self.apply_shared_timbers_button.setEnabled(False)
        cursor_active = False
        try:
            QtWidgets.QApplication.setOverrideCursor(QtCore.Qt.WaitCursor)
            cursor_active = True
            QtWidgets.QApplication.processEvents()
        except Exception:
            pass
        try:
            settings = normalise_crossover_shared_timber_settings(self.shared_timber_settings)
            settings["show_shared_timber_geometry"] = bool(self.show_shared_timbers_checkbox.isChecked())
            result = apply_crossover_shared_long_timbers(self.doc, identifier, settings)
            if not result.get("generated_timber_count"):
                QtWidgets.QMessageBox.information(
                    self,
                    crossover_dialog_title("Shared timber envelope"),
                    "No safe inherited-pair or connector-envelope timber could be generated. The inherited geometry remains unchanged.\n\n" + crossover_shared_timber_summary(result, include_rejections=True),
                )
            self.shared_timber_settings = normalise_crossover_shared_timber_settings(result.get("settings"))
            self.refresh_crossovers(identifier)
            self.diagnostics.setPlainText(crossover_shared_timber_summary(result, include_rejections=True))
        except Exception as error:
            QtWidgets.QMessageBox.critical(self, crossover_dialog_title("Shared timber-envelope error"), str(error))
        finally:
            self.apply_shared_timbers_button.setEnabled(self.current_config() is not None)
            if cursor_active:
                try:
                    QtWidgets.QApplication.restoreOverrideCursor()
                except Exception:
                    pass

    def remove_shared_long_timbers(self):
        config = self.current_config()
        if config is None:
            return
        identifier = str(config.get("crossover_id") or "")
        answer = QtWidgets.QMessageBox.question(
            self,
            crossover_dialog_title("Remove shared timber envelope"),
            "Remove the shared long-timber envelope from {} and restore the red inherited reference display? Turnout and crossover rail geometry will not change.".format(identifier),
            QtWidgets.QMessageBox.Yes | QtWidgets.QMessageBox.No,
            QtWidgets.QMessageBox.No,
        )
        if answer != QtWidgets.QMessageBox.Yes:
            return
        try:
            clear_crossover_shared_long_timbers(self.doc, identifier)
            self.refresh_crossovers(identifier)
            self.diagnostics.setPlainText("Removed the shared long-timber envelope from {}. The inherited timber references are visible again.".format(identifier))
        except Exception as error:
            QtWidgets.QMessageBox.critical(self, crossover_dialog_title("Remove shared timber envelope error"), str(error))

    def show_shared_timber_details(self):
        config = self.current_config()
        if config is None:
            return
        result = config.get("shared_timber_result")
        if not isinstance(result, dict) or not result:
            QtWidgets.QMessageBox.information(self, crossover_dialog_title("Shared-timber envelope details"), "No shared-timber envelope result is stored for this crossover.")
            return
        dialog = QtWidgets.QDialog(self)
        dialog.setWindowTitle(crossover_dialog_title("Shared timber envelope details"))
        dialog.resize(900, 700)
        layout = QtWidgets.QVBoxLayout(dialog)
        details = QtWidgets.QPlainTextEdit()
        details.setReadOnly(True)
        details.setPlainText(crossover_shared_timber_summary(result, include_rejections=True))
        layout.addWidget(details)
        buttons = QtWidgets.QDialogButtonBox(QtWidgets.QDialogButtonBox.Close)
        buttons.rejected.connect(dialog.reject)
        buttons.clicked.connect(dialog.accept)
        layout.addWidget(buttons)
        dialog.exec_()

    def set_shared_timber_visibility(self, visible):
        config = self.current_config()
        if config is None:
            return
        self.shared_timber_settings["show_shared_timber_geometry"] = bool(visible)
        set_crossover_shared_timber_visibility(self.doc, config.get("crossover_id"), bool(visible))


    def edit_b3_settings(self):
        config = self.current_config()
        if config is None:
            return
        settings = normalise_crossover_b3_settings(self.b3_settings)
        dialog = QtWidgets.QDialog(self)
        dialog.setWindowTitle(crossover_dialog_title("Interlacing and timber-movement settings"))
        layout = QtWidgets.QFormLayout(dialog)
        specifications = (
            ("maximum_timber_movement", "Maximum longitudinal timber movement", 0.0, 10.0, 3, " mm"),
            ("movement_increment", "Movement search increment", 0.01, 2.0, 3, " mm"),
            ("minimum_clear_spacing", "Minimum clear spacing after movement", 0.0, 10.0, 3, " mm"),
            ("maximum_interlacing_separation", "Maximum total interlacing separation", 0.0, 20.0, 3, " mm"),
            ("maximum_angle_difference_degrees", "Maximum angular difference for interlacing", 0.1, 30.0, 2, "°"),
            ("protected_support_movement_allowance", "Protected support movement allowance", 0.0, 5.0, 3, " mm"),
            ("collision_tolerance", "Incidental overlap tolerance", 0.0, 5.0, 3, " mm²"),
        )
        boxes = {}
        for key, label, minimum, maximum, decimals, suffix in specifications:
            box = QtWidgets.QDoubleSpinBox()
            box.setDecimals(decimals)
            box.setRange(minimum, maximum)
            box.setValue(float(settings[key]))
            box.setSuffix(suffix)
            adjustment_tips = {
                "maximum_timber_movement": "Maximum longitudinal distance an ordinary eligible timber may move from its inherited position.",
                "movement_increment": "Search step used to find the smallest safe longitudinal movement.",
                "minimum_clear_spacing": "Minimum timber-body clearance required after interlacing or movement.",
                "maximum_interlacing_separation": "Maximum total longitudinal separation permitted when creating an interlaced arrangement.",
                "maximum_angle_difference_degrees": "Largest angular difference permitted between timber candidates for controlled adjustment.",
                "protected_support_movement_allowance": "Stricter movement limit for switch, crossing and rail-joint support positions.",
                "collision_tolerance": "Small overlap area ignored during neighbouring-timber collision checks.",
            }
            box.setToolTip(adjustment_tips[key])
            layout.addRow(label, box)
            boxes[key] = box
        advisory_box = QtWidgets.QCheckBox("Allow automatic movement for advisory same-position findings")
        advisory_box.setChecked(bool(settings.get("resolve_advisory_same_position", False)))
        advisory_box.setToolTip("Allows the resolver to adjust advisory-only same-position pairs; protected limits and collision checks still apply.")
        layout.addRow(advisory_box)
        note = QtWidgets.QLabel(
            "Controlled timber adjustment starts from the current shared long-timber envelope. It first accepts an already safe stagger, then tests symmetric interlacing and finally the smallest permitted single-timber longitudinal movement. Shared long timbers and connector sleepers remain fixed. Protected switch, crossing and rail-joint positions use the stricter allowance. No timber is shortened, omitted, twisted or widened."
        )
        note.setWordWrap(True)
        layout.addRow(note)
        buttons = QtWidgets.QDialogButtonBox(QtWidgets.QDialogButtonBox.Ok | QtWidgets.QDialogButtonBox.Cancel)
        buttons.accepted.connect(dialog.accept)
        buttons.rejected.connect(dialog.reject)
        layout.addRow(buttons)
        if dialog.exec_() != QtWidgets.QDialog.Accepted:
            return
        for key, box in boxes.items():
            settings[key] = float(box.value())
        settings["resolve_advisory_same_position"] = bool(advisory_box.isChecked())
        settings["show_b3_geometry"] = bool(self.show_b3_checkbox.isChecked())
        self.b3_settings = normalise_crossover_b3_settings(settings)
        self.timber_analysis_status.setText("Interlacing and movement setting changes will apply to the next resolution.")

    def apply_b3_timbering(self):
        config = self.current_config()
        if config is None:
            return
        identifier = str(config.get("crossover_id") or "")
        self.apply_b3_button.setEnabled(False)
        cursor_active = False
        try:
            QtWidgets.QApplication.setOverrideCursor(QtCore.Qt.WaitCursor)
            cursor_active = True
            QtWidgets.QApplication.processEvents()
        except Exception:
            pass
        try:
            settings = normalise_crossover_b3_settings(self.b3_settings)
            settings["show_b3_geometry"] = bool(self.show_b3_checkbox.isChecked())
            result = apply_crossover_b3_timbering(self.doc, identifier, settings)
            self.b3_settings = normalise_crossover_b3_settings(result.get("settings"))
            self.refresh_crossovers(identifier)
            self.diagnostics.setPlainText(crossover_b3_summary(result, include_unresolved=True))
        except Exception as error:
            QtWidgets.QMessageBox.critical(self, crossover_dialog_title("Timber adjustment error"), str(error))
        finally:
            self.update_selection_buttons()
            if cursor_active:
                try:
                    QtWidgets.QApplication.restoreOverrideCursor()
                except Exception:
                    pass

    def remove_b3_timbering(self):
        config = self.current_config()
        if config is None:
            return
        identifier = str(config.get("crossover_id") or "")
        answer = QtWidgets.QMessageBox.question(
            self,
            crossover_dialog_title("Remove interlacing and timber movement"),
            "Remove the controlled interlacing and timber movements from {} and restore the shared long-timber envelope? Rail geometry and host tracks will not change.".format(identifier),
            QtWidgets.QMessageBox.Yes | QtWidgets.QMessageBox.No,
            QtWidgets.QMessageBox.No,
        )
        if answer != QtWidgets.QMessageBox.Yes:
            return
        try:
            clear_crossover_b3_timbering(self.doc, identifier)
            self.refresh_crossovers(identifier)
            self.diagnostics.setPlainText("Removed the controlled timber movements from {}. The validated shared long-timber envelope is visible again.".format(identifier))
        except Exception as error:
            QtWidgets.QMessageBox.critical(self, crossover_dialog_title("Remove timber adjustment error"), str(error))

    def show_b3_details(self):
        config = self.current_config()
        if config is None:
            return
        result = config.get("b3_result")
        if not isinstance(result, dict) or not result:
            QtWidgets.QMessageBox.information(self, crossover_dialog_title("Interlacing and timber-movement details"), "No interlacing or timber-movement result is stored for this crossover.")
            return
        dialog = QtWidgets.QDialog(self)
        dialog.setWindowTitle(crossover_dialog_title("Interlacing and timber-movement details"))
        dialog.resize(900, 700)
        layout = QtWidgets.QVBoxLayout(dialog)
        details = QtWidgets.QPlainTextEdit()
        details.setReadOnly(True)
        details.setPlainText(crossover_b3_summary(result, include_unresolved=True))
        layout.addWidget(details)
        buttons = QtWidgets.QDialogButtonBox(QtWidgets.QDialogButtonBox.Close)
        buttons.rejected.connect(dialog.reject)
        buttons.clicked.connect(dialog.accept)
        layout.addWidget(buttons)
        dialog.exec_()

    def set_b3_visibility(self, visible):
        config = self.current_config()
        if config is None:
            return
        self.b3_settings["show_b3_geometry"] = bool(visible)
        set_crossover_b3_visibility(self.doc, config.get("crossover_id"), bool(visible))

    def apply_b4_timbering(self):
        config = self.current_config()
        if config is None:
            return
        identifier = str(config.get("crossover_id") or "")
        self.apply_b4_button.setEnabled(False)
        cursor_active = False
        try:
            QtWidgets.QApplication.setOverrideCursor(QtCore.Qt.WaitCursor)
            cursor_active = True
            QtWidgets.QApplication.processEvents()
        except Exception:
            pass
        try:
            shared_settings = normalise_crossover_shared_timber_settings(self.shared_timber_settings)
            shared_settings["show_shared_timber_geometry"] = bool(self.show_shared_timbers_checkbox.isChecked())
            b3_settings = normalise_crossover_b3_settings(self.b3_settings)
            b3_settings["show_b3_geometry"] = bool(self.show_b3_checkbox.isChecked())
            b4_settings = normalise_crossover_b4_settings(self.b4_settings)
            b4_settings["show_b4_geometry"] = bool(self.show_b4_checkbox.isChecked())
            result = apply_crossover_b4_timbering(
                self.doc, identifier, shared_settings, b3_settings, b4_settings
            )
            self.b4_settings = normalise_crossover_b4_settings(result.get("settings"))
            self.refresh_crossovers(identifier)
            self.diagnostics.setPlainText(crossover_b4_summary(result, include_unresolved=True))
        except Exception as error:
            QtWidgets.QMessageBox.critical(self, crossover_dialog_title("Automatic timber-resolution error"), str(error))
        finally:
            self.update_selection_buttons()
            if cursor_active:
                try:
                    QtWidgets.QApplication.restoreOverrideCursor()
                except Exception:
                    pass

    def remove_b4_timbering(self):
        config = self.current_config()
        if config is None:
            return
        identifier = str(config.get("crossover_id") or "")
        answer = QtWidgets.QMessageBox.question(
            self,
            crossover_dialog_title("Remove automatic timbering result"),
            "Remove the automatic timbering preview from {}? Existing adjusted, shared-envelope or inherited reference geometry will be restored where available. Rail geometry and host tracks will not change.".format(identifier),
            QtWidgets.QMessageBox.Yes | QtWidgets.QMessageBox.No,
            QtWidgets.QMessageBox.No,
        )
        if answer != QtWidgets.QMessageBox.Yes:
            return
        try:
            clear_crossover_b4_timbering(self.doc, identifier)
            self.refresh_crossovers(identifier)
            self.diagnostics.setPlainText("Removed the automatic timbering preview from {}.".format(identifier))
        except Exception as error:
            QtWidgets.QMessageBox.critical(self, crossover_dialog_title("Remove automatic timbering error"), str(error))

    def show_b4_details(self):
        config = self.current_config()
        if config is None:
            return
        result = config.get("b4_result")
        if not isinstance(result, dict) or not result:
            QtWidgets.QMessageBox.information(self, crossover_dialog_title("Automatic timbering details"), "No automatic timber-resolution result is stored for this crossover.")
            return
        dialog = QtWidgets.QDialog(self)
        dialog.setWindowTitle(crossover_dialog_title("Automatic timbering details"))
        dialog.resize(900, 700)
        layout = QtWidgets.QVBoxLayout(dialog)
        details = QtWidgets.QPlainTextEdit()
        details.setReadOnly(True)
        details.setPlainText(crossover_b4_summary(result, include_unresolved=True))
        layout.addWidget(details)
        buttons = QtWidgets.QDialogButtonBox(QtWidgets.QDialogButtonBox.Close)
        buttons.rejected.connect(dialog.reject)
        buttons.clicked.connect(dialog.accept)
        layout.addWidget(buttons)
        dialog.exec_()

    def set_b4_visibility(self, visible):
        config = self.current_config()
        if config is None:
            return
        self.b4_settings["show_b4_geometry"] = bool(visible)
        set_crossover_b4_visibility(self.doc, config.get("crossover_id"), bool(visible))

    def integrate_selected_crossover(self):
        config = self.current_config()
        if config is None:
            return
        identifier = str(config.get("crossover_id") or "")
        answer = QtWidgets.QMessageBox.question(
            self, crossover_dialog_title("Integrate crossover with host templates"),
            "Replace the affected host-template production records with the resolved {} assembly? The operation is reversible and chair validation will remain outstanding.".format(identifier),
            QtWidgets.QMessageBox.Yes | QtWidgets.QMessageBox.No, QtWidgets.QMessageBox.No,
        )
        if answer != QtWidgets.QMessageBox.Yes:
            return
        try:
            result = create_crossover_host_integration(self.doc, identifier)
            self.refresh_crossovers(identifier)
            self.diagnostics.setPlainText(crossover_host_integration_summary(self.doc, result))
        except Exception as error:
            QtWidgets.QMessageBox.critical(self, crossover_dialog_title("Crossover host-integration error"), str(error))

    def remove_selected_integration(self):
        config = self.current_config()
        if config is None:
            return
        identifier = str(config.get("crossover_id") or "")
        answer = QtWidgets.QMessageBox.question(
            self, crossover_dialog_title("Remove crossover host integration"),
            "Restore the original Host A and Host B production records for {}? The resolved crossover geometry remains available as a separate managed assembly.".format(identifier),
            QtWidgets.QMessageBox.Yes | QtWidgets.QMessageBox.No, QtWidgets.QMessageBox.No,
        )
        if answer != QtWidgets.QMessageBox.Yes:
            return
        try:
            result = remove_crossover_host_integration(self.doc, identifier)
            self.refresh_crossovers(identifier)
            self.diagnostics.setPlainText(crossover_host_integration_summary(self.doc, result))
        except Exception as error:
            QtWidgets.QMessageBox.critical(self, crossover_dialog_title("Remove host integration error"), str(error))

    def show_integration_details(self):
        config = self.current_config()
        if config is None:
            return
        dialog = QtWidgets.QDialog(self)
        dialog.setWindowTitle(crossover_dialog_title("Crossover host-integration details"))
        layout = QtWidgets.QVBoxLayout(dialog)
        details = QtWidgets.QPlainTextEdit()
        details.setReadOnly(True)
        details.setPlainText(crossover_host_integration_summary(self.doc, config))
        layout.addWidget(details)
        buttons = QtWidgets.QDialogButtonBox(QtWidgets.QDialogButtonBox.Close)
        buttons.rejected.connect(dialog.reject)
        layout.addWidget(buttons)
        dialog.resize(760, 480)
        dialog.exec_()

    def show_details(self):
        config = self.current_config()
        if config is None:
            return
        QtWidgets.QMessageBox.information(
            self,
            crossover_dialog_title("Crossover details"),
            json.dumps(config, indent=2, sort_keys=True),
        )


    def convert_crossover_to_turnout(self):
        config = self.current_config()
        if config is None:
            return
        identifier = str(config.get("crossover_id") or "")
        source_turnout = str(config.get("extended_from_turnout_id") or "").strip()
        keep_side = None
        if not source_turnout:
            choices = [
                "Host A - {}".format(config.get("host_a_track_name", config.get("host_a_label", "Host A"))),
                "Host B - {}".format(config.get("host_b_track_name", config.get("host_b_label", "Host B"))),
            ]
            choice, accepted = QtWidgets.QInputDialog.getItem(
                self,
                crossover_dialog_title("Choose turnout to retain"),
                "This crossover was created independently. Which constituent turnout should remain?",
                choices,
                0,
                False,
            )
            if not accepted:
                return
            keep_side = (
                CROSSOVER_REVERSION_SIDE_A
                if str(choice).startswith("Host A")
                else CROSSOVER_REVERSION_SIDE_B
            )

        self.revert_button.setEnabled(False)
        cursor_active = False
        try:
            QtWidgets.QApplication.setOverrideCursor(QtCore.Qt.WaitCursor)
            cursor_active = True
            QtWidgets.QApplication.processEvents()
        except Exception:
            pass
        try:
            resolved = resolve_crossover_to_turnout_conversion(
                self.doc, identifier, keep_side
            )
            if cursor_active:
                try:
                    QtWidgets.QApplication.restoreOverrideCursor()
                    cursor_active = False
                except Exception:
                    pass
            answer = QtWidgets.QMessageBox.question(
                self,
                crossover_dialog_title("Convert crossover to turnout"),
                (
                    "Convert {crossover} back into standalone turnout {turnout}?\n\n"
                    "Retained side: Host {side}\n"
                    "Host track: {host}\n"
                    "Identity: {identity}\n"
                    "Restoration source: {fidelity}\n\n"
                    "The turnout has already been rebuilt and validated in memory. Any active host integration will be restored inside the same transaction, and the crossover remains untouched if any FreeCAD object or production-record step fails."
                ).format(
                    crossover=identifier,
                    turnout=resolved["turnout_id"],
                    side=resolved["keep_side"],
                    host=resolved["host_label"],
                    identity=(
                        "original stable identity preserved"
                        if resolved["identity_preserved"]
                        else "new standalone turnout identity"
                    ),
                    fidelity=resolved["source_fidelity"],
                ),
                QtWidgets.QMessageBox.Yes | QtWidgets.QMessageBox.No,
                QtWidgets.QMessageBox.No,
            )
            if answer != QtWidgets.QMessageBox.Yes:
                return
            try:
                QtWidgets.QApplication.setOverrideCursor(QtCore.Qt.WaitCursor)
                cursor_active = True
                QtWidgets.QApplication.processEvents()
            except Exception:
                pass
            turnout_config = convert_rea_c10_crossover_to_turnout(
                self.doc,
                identifier,
                resolved["keep_side"],
                pre_resolved=resolved,
            )
            self.refresh_crossovers()
            self.refresh_hosts()
            callback = getattr(self, "turnout_refresh_callback", None)
            if callable(callback):
                callback(turnout_config.get("turnout_id"))
            tabs = self.parentWidget()
            if isinstance(tabs, QtWidgets.QTabWidget):
                tabs.setCurrentIndex(0)
            if cursor_active:
                try:
                    QtWidgets.QApplication.restoreOverrideCursor()
                    cursor_active = False
                except Exception:
                    pass
            if Gui is not None:
                try:
                    Gui.activeDocument().activeView().viewTop()
                    Gui.activeDocument().activeView().fitAll()
                except Exception:
                    pass
            QtWidgets.QMessageBox.information(
                self,
                crossover_dialog_title("Crossover converted to turnout"),
                "Converted {} into {} on Host {} in one transaction.".format(
                    identifier,
                    turnout_config.get("turnout_id", "the restored turnout"),
                    resolved["keep_side"],
                ),
            )
        except Exception as error:
            QtWidgets.QMessageBox.critical(
                self,
                crossover_dialog_title("Crossover-to-turnout conversion error"),
                str(error),
            )
        finally:
            self.revert_button.setEnabled(self.current_config() is not None)
            if cursor_active:
                try:
                    QtWidgets.QApplication.restoreOverrideCursor()
                except Exception:
                    pass

    def remove_crossover(self):
        config = self.current_config()
        if config is None:
            return
        identifier = str(config.get("crossover_id") or "")
        answer = QtWidgets.QMessageBox.question(
            self,
            crossover_dialog_title("Remove crossover"),
            "Remove {} and all of its crossover production records? If host integration is active, both original host templates and their production records will be restored inside the same transaction.".format(identifier),
            QtWidgets.QMessageBox.Yes | QtWidgets.QMessageBox.No,
            QtWidgets.QMessageBox.No,
        )
        if answer != QtWidgets.QMessageBox.Yes:
            return
        try:
            remove_rea_c10_crossover(self.doc, identifier)
            self.refresh_crossovers()
        except Exception as error:
            QtWidgets.QMessageBox.critical(self, crossover_dialog_title("Crossover removal error"), str(error))


# Backwards-compatible class name for existing tests and integrations.  It now
# resolves to the safe QWidget panel rather than a nested modal QDialog.
CrossoverManagerDialog = CrossoverManagerPanel


class TurnoutManagerDialog(QtWidgets.QDialog):
    def __init__(self, doc, parent=None):
        super(TurnoutManagerDialog, self).__init__(parent)
        self.doc = doc
        self.hosts = []
        self.turnouts = []
        self.editing_turnout_id = None
        self.editing_original_config = None
        self.setWindowTitle(versioned_dialog_title("REA C10 turnout and crossover manager"))
        self.resize(1180, 850)

        root_layout = QtWidgets.QVBoxLayout(self)
        self.mode_tabs = QtWidgets.QTabWidget()
        root_layout.addWidget(self.mode_tabs, 1)
        self.turnout_scroll_area = QtWidgets.QScrollArea()
        self.turnout_scroll_area.setWidgetResizable(True)
        self.turnout_scroll_area.setToolTip(
            "Scroll to reach all turnout controls when the manager is smaller than its full content."
        )
        turnout_tab = QtWidgets.QWidget()
        layout = QtWidgets.QVBoxLayout(turnout_tab)
        self.turnout_scroll_area.setWidget(turnout_tab)
        self.mode_tabs.addTab(self.turnout_scroll_area, "Turnouts")
        introduction = QtWidgets.QLabel(
            "Place or edit an REA bullhead C10 turnout by switch-toe chainage on a generated track centreline. "
            "Every rail component is mapped through the actual host alignment, so the result inherits "
            "straight, constant-radius and Euler-transition curvature continuously. The engraving includes "
            "stock, switch, closure, wing, vee and check-rail construction geometry. Editing builds and validates "
            "the complete replacement in memory before one transaction updates the existing turnout. Stage 8A5 can also "
            "create a derived integrated host template or an independent reference copy without changing the original source objects."
        )
        introduction.setWordWrap(True)
        layout.addWidget(introduction)

        source_note = QtWidgets.QLabel(
            "Geometry source: REA C semi-curved switch and Templot5 regular 1:10 common-crossing calculations. "
            "Stage 8A4 adds source-driven switch, closure, crossing-chair and exit timbering, including timber "
            "outlines, stepped lengths, identities and construction datums. Stage 8A5 replaces only the affected host-production "
            "records with derived integrated records; the original objects remain available for safe restoration. C10 remains fixed in this stage."
        )
        source_note.setWordWrap(True)
        layout.addWidget(source_note)

        self.workflow_panel = GuidedTrackworkWorkflowPanel(
            "Guided turnout workflow",
            (
                "Place, create or edit turnout geometry",
                "Confirm the REA timbering",
                "Analyse chair positions",
                "Adjust model timber support",
                "Build and validate the 2D chair layout",
                "Integrate with the host template",
                "Finish, export or convert to a crossover",
            ),
            self,
        )
        layout.addWidget(self.workflow_panel)

        host_group = QtWidgets.QGroupBox("Host track and placement")
        self.turnout_host_group = host_group
        host_grid = QtWidgets.QGridLayout(host_group)
        self.host_combo = QtWidgets.QComboBox()
        self.refresh_hosts_button = QtWidgets.QPushButton("Refresh hosts")
        self.use_selection_button = QtWidgets.QPushButton("Use selected centreline / picked point")
        self.chainage_box = QtWidgets.QDoubleSpinBox()
        self.chainage_box.setDecimals(3)
        self.chainage_box.setSingleStep(1.0)
        self.orientation_combo = QtWidgets.QComboBox()
        self.orientation_combo.addItems([TURNOUT_ORIENTATION_FACING, TURNOUT_ORIENTATION_TRAILING])
        self.handing_combo = QtWidgets.QComboBox()
        self.handing_combo.addItems([TURNOUT_HAND_LEFT, TURNOUT_HAND_RIGHT])
        self.host_summary = QtWidgets.QLabel("")
        self.host_summary.setWordWrap(True)
        host_grid.addWidget(QtWidgets.QLabel("Generated host centreline"), 0, 0)
        host_grid.addWidget(self.host_combo, 0, 1, 1, 3)
        host_grid.addWidget(self.refresh_hosts_button, 1, 1)
        host_grid.addWidget(self.use_selection_button, 1, 2, 1, 2)
        host_grid.addWidget(QtWidgets.QLabel("Switch-toe chainage (mm)"), 2, 0)
        host_grid.addWidget(self.chainage_box, 2, 1)

        nudge_layout = QtWidgets.QHBoxLayout()
        self.nudge_buttons = []
        for delta in (-100.0, -10.0, -1.0, 1.0, 10.0, 100.0):
            label = "{:+g}".format(delta)
            button = QtWidgets.QPushButton(label)
            button.setToolTip("Move the switch toe {} mm along the chosen host line.".format(label))
            button.clicked.connect(lambda _checked=False, amount=delta: self.nudge_chainage(amount))
            nudge_layout.addWidget(button)
            self.nudge_buttons.append(button)
        host_grid.addLayout(nudge_layout, 2, 2, 1, 2)

        host_grid.addWidget(QtWidgets.QLabel("Orientation"), 3, 0)
        host_grid.addWidget(self.orientation_combo, 3, 1, 1, 2)
        host_grid.addWidget(QtWidgets.QLabel("Handing"), 4, 0)
        host_grid.addWidget(self.handing_combo, 4, 1)
        host_grid.addWidget(self.host_summary, 5, 0, 1, 4)
        layout.addWidget(host_group)

        geometry_group = QtWidgets.QGroupBox("OO and production geometry")
        self.turnout_geometry_group = geometry_group
        geometry_grid = QtWidgets.QGridLayout(geometry_group)
        self.gauge_box = QtWidgets.QDoubleSpinBox()
        self.gauge_box.setRange(TURNOUT_MIN_GAUGE, TURNOUT_MAX_GAUGE)
        self.gauge_box.setDecimals(3)
        self.gauge_box.setValue(TURNOUT_DEFAULT_GAUGE)
        self.flangeway_box = QtWidgets.QDoubleSpinBox()
        self.flangeway_box.setRange(TURNOUT_MIN_FLANGEWAY, TURNOUT_MAX_FLANGEWAY)
        self.flangeway_box.setDecimals(3)
        self.flangeway_box.setValue(TURNOUT_DEFAULT_FLANGEWAY)
        self.timber_outline_box = QtWidgets.QCheckBox("Create full REA timber outlines")
        self.timber_outline_box.setChecked(True)
        self.timber_centre_box = QtWidgets.QCheckBox("Create timber centre lines")
        self.timber_centre_box.setChecked(False)
        self.timber_number_box = QtWidgets.QCheckBox("Engrave timber identities")
        self.timber_number_box.setChecked(True)
        self.timber_length_box = QtWidgets.QCheckBox("Engrave rounded timber lengths")
        self.timber_length_box.setChecked(False)
        self.datum_box = QtWidgets.QCheckBox("Create TOE, HEEL, FP, BN, A and VJ datums")
        self.datum_box.setChecked(True)
        # Backward-compatible alias retained for older dialogue integrations.
        self.timber_box = self.timber_outline_box
        geometry_grid.addWidget(QtWidgets.QLabel("Track gauge (mm)"), 0, 0)
        geometry_grid.addWidget(self.gauge_box, 0, 1)
        geometry_grid.addWidget(QtWidgets.QLabel("Design flangeway (mm)"), 0, 2)
        geometry_grid.addWidget(self.flangeway_box, 0, 3)
        geometry_grid.addWidget(self.timber_outline_box, 1, 0, 1, 2)
        geometry_grid.addWidget(self.timber_centre_box, 1, 2, 1, 2)
        geometry_grid.addWidget(self.timber_number_box, 2, 0, 1, 2)
        geometry_grid.addWidget(self.timber_length_box, 2, 2, 1, 2)
        geometry_grid.addWidget(self.datum_box, 3, 0, 1, 4)
        note = QtWidgets.QLabel(
            "The template width and thickness are inherited from the selected host track. Timber centres follow "
            "the published C-switch intervals, an equally divided closure region, and the fixed REA crossing-chair "
            "spacings used by Templot. Timber lengths increase in 6-inch prototype steps and remain separately "
            "exportable from rails, labels and construction datums."
        )
        note.setWordWrap(True)
        geometry_grid.addWidget(note, 4, 0, 1, 4)
        layout.addWidget(geometry_group)

        self.preview_label = QtWidgets.QLabel("")
        self.preview_label.setWordWrap(True)
        layout.addWidget(self.preview_label)
        self.edit_status_label = QtWidgets.QLabel("Create mode: choose a host and chainage, or select an existing turnout and choose Edit selected turnout.")
        self.edit_status_label.setWordWrap(True)
        layout.addWidget(self.edit_status_label)

        existing_group = QtWidgets.QGroupBox("Existing Stage 8A turnouts (older rail or timber geometry can be upgraded by Edit and Apply)")
        existing_layout = QtWidgets.QVBoxLayout(existing_group)
        self.table = QtWidgets.QTableWidget(0, 8)
        self.table.setHorizontalHeaderLabels(["ID", "Set", "Route", "Track", "Toe mm", "Hand", "Orientation", "Host template"])
        self.table.setSelectionBehavior(QtWidgets.QAbstractItemView.SelectRows)
        self.table.setSelectionMode(QtWidgets.QAbstractItemView.SingleSelection)
        try:
            self.table.horizontalHeader().setStretchLastSection(True)
        except Exception:
            pass
        existing_layout.addWidget(self.table)
        layout.addWidget(existing_group)
        self.chair_analysis_panel = ChairAnalysisPanel(self.doc, "turnout", self.current_turnout_config, self.refresh_turnouts, self)
        layout.addWidget(self.chair_analysis_panel)

        button_row = QtWidgets.QHBoxLayout()
        self.create_button = QtWidgets.QPushButton("Create curve-inheriting C10 turnout")
        self.edit_button = QtWidgets.QPushButton("Edit selected turnout")
        self.apply_edit_button = QtWidgets.QPushButton("Apply turnout changes")
        self.cancel_edit_button = QtWidgets.QPushButton("Cancel edit")
        self.extend_crossover_button = QtWidgets.QPushButton("Convert selected turnout to crossover")
        self.extend_crossover_button.setToolTip(
            "Automatically find the nearest valid neighbouring track, solve the complete crossover, "
            "and replace the selected standalone turnout in one transaction."
        )
        self.integrate_button = QtWidgets.QPushButton("Integrate selected turnout")
        self.remove_integration_button = QtWidgets.QPushButton("Remove host integration")
        self.reference_button = QtWidgets.QPushButton("Create reference copy")
        self.remove_button = QtWidgets.QPushButton("Remove selected turnout")
        self.close_button = QtWidgets.QPushButton("Close")
        button_row.addWidget(self.create_button)
        button_row.addWidget(self.edit_button)
        button_row.addWidget(self.apply_edit_button)
        button_row.addWidget(self.cancel_edit_button)
        button_row.addWidget(self.remove_button)
        button_row.addStretch(1)
        button_row.addWidget(self.close_button)
        integration_row = QtWidgets.QHBoxLayout()
        integration_row.addWidget(self.extend_crossover_button)
        integration_row.addWidget(self.integrate_button)
        integration_row.addWidget(self.remove_integration_button)
        integration_row.addWidget(self.reference_button)
        integration_row.addStretch(1)
        layout.addLayout(integration_row)
        layout.addLayout(button_row)

        self.refresh_hosts_button.clicked.connect(self.refresh_hosts)
        self.use_selection_button.clicked.connect(self.use_selected_host)
        self.host_combo.currentIndexChanged.connect(self.update_host_summary)
        self.orientation_combo.currentIndexChanged.connect(self.update_host_summary)
        self.handing_combo.currentIndexChanged.connect(self.update_host_summary)
        self.chainage_box.valueChanged.connect(self.update_host_summary)
        self.gauge_box.valueChanged.connect(self.update_host_summary)
        self.flangeway_box.valueChanged.connect(self.update_host_summary)
        self.timber_outline_box.toggled.connect(self.update_host_summary)
        self.timber_centre_box.toggled.connect(self.update_host_summary)
        self.timber_number_box.toggled.connect(self.update_host_summary)
        self.timber_length_box.toggled.connect(self.update_host_summary)
        self.datum_box.toggled.connect(self.update_host_summary)
        self.create_button.clicked.connect(self.create_turnout)
        self.edit_button.clicked.connect(self.begin_edit_turnout)
        self.apply_edit_button.clicked.connect(self.apply_turnout_edit)
        self.cancel_edit_button.clicked.connect(self.cancel_turnout_edit)
        self.extend_crossover_button.clicked.connect(self.begin_selected_turnout_extension)
        self.integrate_button.clicked.connect(self.integrate_selected_turnout)
        self.remove_integration_button.clicked.connect(self.remove_selected_integration)
        self.reference_button.clicked.connect(self.extract_selected_reference)
        self.remove_button.clicked.connect(self.remove_turnout)
        self.close_button.clicked.connect(self.close_manager)
        self.table.itemSelectionChanged.connect(self.update_selection_buttons)
        self.workflow_panel.run_next_button.clicked.connect(self.run_next_guided_step)
        self.workflow_panel.advanced_checkbox.toggled.connect(self.set_guided_advanced_visibility)
        self.workflow_panel.primary_button(0).clicked.connect(self.guided_turnout_geometry_primary)
        self.workflow_panel.secondary_button(0).clicked.connect(self.guided_turnout_geometry_secondary)
        self.workflow_panel.primary_button(1).clicked.connect(self.guided_turnout_timber_primary)
        self.workflow_panel.secondary_button(1).clicked.connect(self.guided_turnout_timber_secondary)
        self.workflow_panel.primary_button(2).clicked.connect(self.guided_turnout_chair_primary)
        self.workflow_panel.secondary_button(2).clicked.connect(self.guided_turnout_chair_secondary)
        self.workflow_panel.primary_button(3).clicked.connect(self.guided_turnout_model_support_primary)
        self.workflow_panel.secondary_button(3).clicked.connect(self.guided_turnout_model_support_secondary)
        self.workflow_panel.primary_button(4).clicked.connect(self.guided_turnout_2d_layout_primary)
        self.workflow_panel.secondary_button(4).clicked.connect(self.guided_turnout_2d_layout_secondary)
        self.workflow_panel.primary_button(5).clicked.connect(self.guided_turnout_integration_primary)
        self.workflow_panel.secondary_button(5).clicked.connect(self.guided_turnout_integration_secondary)
        self.workflow_panel.primary_button(6).clicked.connect(self.guided_turnout_export_chairs_primary)
        self.workflow_panel.secondary_button(6).clicked.connect(self.guided_turnout_finish_primary)
        self.turnout_legacy_action_buttons = (
            self.create_button, self.edit_button, self.apply_edit_button, self.cancel_edit_button,
            self.extend_crossover_button, self.integrate_button, self.remove_integration_button,
            self.reference_button, self.remove_button,
        )

        self.refresh_hosts()
        self.refresh_turnouts()
        self._set_edit_mode(False)
        self.set_guided_advanced_visibility(False)
        self.update_guided_workflow()

        # Embed a plain QWidget panel.  Never place a QDialog inside this modal
        # QDialog or mutate native window flags after construction.
        self.crossover_scroll_area = QtWidgets.QScrollArea()
        self.crossover_scroll_area.setWidgetResizable(True)
        self.crossover_scroll_area.setToolTip(
            "Scroll to reach all crossover geometry, timbering and integration controls."
        )
        self.crossover_panel = CrossoverManagerPanel(doc, self.crossover_scroll_area)
        self.crossover_panel.turnout_refresh_callback = self.refresh_turnouts
        try:
            self.crossover_panel.close_button.hide()
        except Exception:
            pass
        self.crossover_scroll_area.setWidget(self.crossover_panel)
        self.mode_tabs.addTab(self.crossover_scroll_area, "Crossovers")
        self.mode_tabs.currentChanged.connect(self._manager_tab_changed)

    def set_guided_advanced_visibility(self, visible):
        show = bool(visible)
        if hasattr(self, "chair_analysis_panel"):
            self.chair_analysis_panel.setVisible(show)
        editing = bool(getattr(self, "editing_turnout_id", None))
        normal_buttons = (
            self.create_button, self.edit_button, self.extend_crossover_button,
            self.integrate_button, self.remove_integration_button,
            self.reference_button, self.remove_button,
        )
        edit_buttons = (self.apply_edit_button, self.cancel_edit_button)
        for button in normal_buttons:
            button.setVisible(show and not editing)
        for button in edit_buttons:
            button.setVisible(show and editing)
        try:
            self.workflow_panel.advanced_checkbox.blockSignals(True)
            self.workflow_panel.advanced_checkbox.setChecked(show)
            self.workflow_panel.advanced_checkbox.blockSignals(False)
        except Exception:
            pass

    def guided_turnout_geometry_primary(self):
        if self.editing_turnout_id:
            self.apply_turnout_edit()
        else:
            self.create_turnout()
        self.update_guided_workflow()

    def guided_turnout_geometry_secondary(self):
        if self.editing_turnout_id:
            self.cancel_turnout_edit()
        else:
            self.begin_edit_turnout()
        self.update_guided_workflow()

    def guided_turnout_timber_primary(self):
        config = self.current_turnout_config()
        if config is not None and not self.editing_turnout_id:
            self.begin_edit_turnout()
        try:
            self.turnout_scroll_area.ensureWidgetVisible(self.turnout_geometry_group)
        except Exception:
            pass
        self.update_guided_workflow()

    def guided_turnout_timber_secondary(self):
        self.set_guided_advanced_visibility(True)
        try:
            self.turnout_scroll_area.ensureWidgetVisible(self.turnout_geometry_group)
        except Exception:
            pass

    def guided_turnout_chair_primary(self):
        self.chair_analysis_panel.run_analysis()
        self.update_guided_workflow()

    def guided_turnout_chair_secondary(self):
        config = self.current_turnout_config()
        if config is None:
            return
        identifier = str(config.get("turnout_id") or "")
        if _chair_read_cached_result(self.doc, "turnout", identifier) is not None:
            self.chair_analysis_panel.show_details()
        else:
            self.chair_analysis_panel.edit_settings()
        self.update_guided_workflow()

    def guided_turnout_integration_primary(self):
        config = self.current_turnout_config()
        if config is None:
            return
        identifier = str(config.get("turnout_id") or "")
        if turnout_integration_by_id(self.doc, identifier) is not None:
            self.remove_selected_integration()
        else:
            self.integrate_selected_turnout()
        self.update_guided_workflow()

    def guided_turnout_integration_secondary(self):
        self.extract_selected_reference()
        self.update_guided_workflow()

    def guided_turnout_finish_primary(self):
        self.begin_selected_turnout_extension()
        self.update_guided_workflow()

    def guided_turnout_finish_secondary(self):
        self.set_guided_advanced_visibility(True)

    def run_next_guided_step(self):
        config = self.current_turnout_config()
        if self.editing_turnout_id:
            self.apply_turnout_edit()
            self.update_guided_workflow()
            return
        if config is None:
            self.create_turnout()
            self.update_guided_workflow()
            return
        revision = int(config.get("timber_geometry_revision") or 0)
        timber_outlines = bool(config.get("timber_outlines", config.get("timber_references", True)))
        if revision < TURNOUT_TIMBER_GEOMETRY_REVISION or not timber_outlines:
            self.begin_edit_turnout()
            self.update_guided_workflow()
            return
        chair_status = chair_analysis_effective_status(self.doc, "turnout", config)
        if chair_status in (CHAIR_STATUS_NOT_ANALYSED, CHAIR_STATUS_STALE):
            self.chair_analysis_panel.run_analysis()
            self.update_guided_workflow()
            return
        if chair_status in (CHAIR_STATUS_INCOMPLETE, CHAIR_STATUS_CONFLICTS, CHAIR_STATUS_CRITICAL):
            QtWidgets.QMessageBox.information(
                self, versioned_dialog_title("Guided turnout workflow stopped"),
                "Chair-position analysis needs review before host integration. No turnout geometry, timbering or integration record has been changed.",
            )
            return
        identifier = str(config.get("turnout_id") or "")
        if turnout_integration_by_id(self.doc, identifier) is None and self.integrate_button.isEnabled():
            self.integrate_selected_turnout()
            self.update_guided_workflow()
            return
        QtWidgets.QMessageBox.information(
            self, versioned_dialog_title("Guided turnout workflow"),
            "The selected turnout has completed every currently available guided stage. Conversion to a crossover remains an optional final action.",
        )

    def update_guided_workflow(self):
        panel = getattr(self, "workflow_panel", None)
        if panel is None:
            return
        config = self.current_turnout_config()
        editing = bool(self.editing_turnout_id)
        if config is None and not editing:
            panel.set_step(0, "Choose a host centreline, switch-toe chainage, orientation, handing and production options.", "ready",
                           "Create turnout", self.create_button.isEnabled(), "", False)
            panel.set_step(1, "REA timbering will be built as part of the validated turnout geometry.", "waiting", "Timber options", True, "Show all controls", True)
            panel.set_step(2, "Create a turnout before analysing chair positions.", "waiting", "Analyse chairs", False, "", False)
            panel.set_step(3, "Create and review the turnout before integrating it with the host template.", "waiting", "Integrate host", False, "", False)
            panel.set_step(4, "A completed standalone turnout can be converted into a managed crossover.", "waiting", "Convert to crossover", False, "Show all controls", True)
            panel.set_summary("The turnout workflow keeps placement, REA timbering, chair-position analysis and host integration in one sequence while retaining the original specialist controls.")
            panel.run_next_button.setText("Run next safe step")
            return

        selected = config or self.editing_original_config or {}
        identifier = str(selected.get("turnout_id") or self.editing_turnout_id or "the selected turnout")
        if editing:
            panel.set_step(0, "Editing {} transactionally. Review the controls, then apply or cancel.".format(identifier), "ready",
                           "Apply turnout changes", self.apply_edit_button.isEnabled(), "Cancel edit", True)
        else:
            panel.set_step(0, "{} has validated turnout geometry on its host alignment.".format(identifier), "complete",
                           "Create another turnout", self.create_button.isEnabled(), "Edit selected turnout", self.edit_button.isEnabled())

        revision = int(selected.get("timber_geometry_revision") or 0)
        timber_outlines = bool(selected.get("timber_outlines", selected.get("timber_references", True)))
        if revision >= TURNOUT_TIMBER_GEOMETRY_REVISION and timber_outlines:
            panel.set_step(1, "Current source-driven REA timber outlines are included.", "complete",
                           "Review timber options", not editing, "Show all controls", True)
        elif not timber_outlines:
            panel.set_step(1, "Timber outlines are disabled for this turnout. Edit the turnout to enable production timbering.", "attention",
                           "Edit timber options", not editing, "Show all controls", True)
        else:
            panel.set_step(1, "Older timber geometry can be upgraded transactionally without moving the turnout.", "attention",
                           "Upgrade timbering", not editing, "Show all controls", True)

        chair_status = chair_analysis_effective_status(self.doc, "turnout", selected)
        chair_state = "ready" if chair_status in (CHAIR_STATUS_NOT_ANALYSED, CHAIR_STATUS_STALE) else (
            "attention" if chair_status in (CHAIR_STATUS_INCOMPLETE, CHAIR_STATUS_CONFLICTS, CHAIR_STATUS_CRITICAL) else "complete"
        )
        chair_cached = _chair_read_cached_result(self.doc, "turnout", identifier) is not None
        panel.set_step(2, chair_status, chair_state, "Analyse chair positions", not editing,
                       "Show chair details" if chair_cached else "Chair settings", not editing)

        integrated = turnout_integration_by_id(self.doc, identifier) is not None
        if integrated:
            panel.set_step(3, "The turnout is integrated reversibly with its host template.", "complete",
                           "Remove integration", not editing, "Create reference copy", not editing)
        else:
            panel.set_step(3, "The turnout remains a separate managed module.", "ready",
                           "Integrate with host", self.integrate_button.isEnabled(), "Create reference copy", self.reference_button.isEnabled())

        panel.set_step(4, "Keep the standalone turnout or extend it automatically to the nearest valid neighbouring host.", "ready",
                       "Convert to crossover", self.extend_crossover_button.isEnabled(), "Show all controls", True)
        panel.set_summary("Selected {}. The numbered actions call the existing turnout builder, chair analyser and reversible integration functions without duplicating their calculations.".format(identifier))
        panel.run_next_button.setText("Run next safe step")

    def _manager_tab_changed(self, index):
        if int(index) == 1:
            self.crossover_panel.refresh_hosts()
            self.crossover_panel.refresh_crossovers()

    def current_host(self):
        index = self.host_combo.currentIndex()
        return self.hosts[index] if 0 <= index < len(self.hosts) else None

    def current_turnout_config(self):
        row = self.table.currentRow()
        return self.turnouts[row] if 0 <= row < len(self.turnouts) else None

    def _set_combo_text(self, combo, value):
        index = combo.findText(str(value))
        if index >= 0:
            combo.setCurrentIndex(index)

    def _set_edit_mode(self, enabled):
        editing = bool(enabled)
        self.host_combo.setEnabled(not editing)
        self.refresh_hosts_button.setEnabled(not editing)
        self.create_button.setVisible(not editing)
        self.edit_button.setVisible(not editing)
        self.extend_crossover_button.setVisible(not editing)
        self.integrate_button.setVisible(not editing)
        self.remove_integration_button.setVisible(not editing)
        self.reference_button.setVisible(not editing)
        self.remove_button.setVisible(not editing)
        self.apply_edit_button.setVisible(editing)
        self.cancel_edit_button.setVisible(editing)
        self.table.setEnabled(not editing)
        self.update_selection_buttons()
        self.update_host_summary()
        if hasattr(self, "workflow_panel"):
            self.set_guided_advanced_visibility(self.workflow_panel.advanced_checkbox.isChecked())
            self.update_guided_workflow()

    def refresh_hosts(self):
        current_name = str(getattr(self.current_host(), "Name", "")) if self.current_host() is not None else ""
        self.hosts = turnout_host_objects(self.doc)
        self.host_combo.blockSignals(True)
        self.host_combo.clear()
        selected_index = 0
        for index, host in enumerate(self.hosts):
            self.host_combo.addItem(turnout_host_label(host))
            if str(host.Name) == current_name:
                selected_index = index
        self.host_combo.setCurrentIndex(selected_index if self.hosts else -1)
        self.host_combo.blockSignals(False)
        self.update_host_summary()

    def nudge_chainage(self, amount):
        value = float(self.chainage_box.value()) + float(amount)
        value = min(max(value, float(self.chainage_box.minimum())), float(self.chainage_box.maximum()))
        self.chainage_box.setValue(value)

    def use_selected_host(self):
        if Gui is None:
            return
        try:
            selection_ex = list(Gui.Selection.getSelectionEx())
        except Exception:
            selection_ex = []
        current_edit_host = str(self.editing_original_config.get("host_object") or "") if self.editing_original_config else ""
        for selected_ex in reversed(selection_ex):
            selected = getattr(selected_ex, "Object", None)
            for index, host in enumerate(self.hosts):
                if str(host.Name) != str(getattr(selected, "Name", "")):
                    continue
                if current_edit_host and str(host.Name) != current_edit_host:
                    QtWidgets.QMessageBox.information(
                        self,
                        versioned_dialog_title("Turnout edit host"),
                        "This turnout remains tied to its original host centreline. Click that line to move the toe by picked point, or cancel the edit first.",
                    )
                    return
                self.host_combo.setCurrentIndex(index)
                picked_points = list(getattr(selected_ex, "PickedPoints", []) or [])
                if picked_points:
                    try:
                        host_data = turnout_host_alignment(host)
                        projected = nearest_alignment_station(host_data, picked_points[-1])
                        projected = min(max(projected, self.chainage_box.minimum()), self.chainage_box.maximum())
                        self.chainage_box.setValue(projected)
                    except Exception:
                        pass
                return
        QtWidgets.QMessageBox.information(
            self,
            versioned_dialog_title("Turnout host selection"),
            "Select or click one generated track centreline in the FreeCAD tree or 3D view, then try again. "
            "A picked point also sets the nearest valid switch-toe chainage.",
        )

    def proposed_config(self):
        host = self.current_host()
        if host is None:
            return None
        return {
            "host_object": str(host.Name),
            "toe_chainage": float(self.chainage_box.value()),
            "handing": str(self.handing_combo.currentText()),
            "orientation": str(self.orientation_combo.currentText()),
            "track_gauge": float(self.gauge_box.value()),
            "flangeway": float(self.flangeway_box.value()),
            "timber_references": bool(self.timber_outline_box.isChecked()),
            "timber_outlines": bool(self.timber_outline_box.isChecked()),
            "timber_centres": bool(self.timber_centre_box.isChecked()),
            "timber_numbers": bool(self.timber_number_box.isChecked()),
            "timber_length_labels": bool(self.timber_length_box.isChecked()),
            "construction_marks": bool(self.datum_box.isChecked()),
            "rail_geometry_revision": TURNOUT_RAIL_GEOMETRY_REVISION,
            "timber_geometry_revision": TURNOUT_TIMBER_GEOMETRY_REVISION,
        }

    def update_host_summary(self):
        host = self.current_host()
        if host is None:
            self.host_summary.setText("No recognised generated centreline is available.")
            self.preview_label.setText("")
            self.create_button.setEnabled(False)
            self.apply_edit_button.setEnabled(False)
            return
        try:
            host_data = turnout_host_alignment(host)
            dimensions = rea_c10_dimensions(self.gauge_box.value(), self.flangeway_box.value())
            orientation = str(self.orientation_combo.currentText())
            minimum, maximum = turnout_valid_toe_range(host_data["total"], dimensions, orientation)
            valid = maximum >= minimum - GEOMETRY_TOLERANCE
            if valid:
                previous = float(self.chainage_box.value())
                self.chainage_box.blockSignals(True)
                self.chainage_box.setRange(minimum, maximum)
                if previous < minimum or previous > maximum:
                    self.chainage_box.setValue(min(max(previous, minimum), maximum))
                self.chainage_box.blockSignals(False)
            else:
                self.chainage_box.blockSignals(True)
                self.chainage_box.setRange(0.0, max(0.0, host_data["total"]))
                self.chainage_box.blockSignals(False)

            width, thickness = turnout_host_template_dimensions(self.doc, host)
            overlap_text = ""
            if valid:
                overlap_config, overlap_length = _turnout_find_overlap(
                    self.doc,
                    host,
                    self.chainage_box.value(),
                    dimensions,
                    orientation,
                    ignored_turnout_id=self.editing_turnout_id,
                )
                if overlap_config is not None:
                    valid = False
                    overlap_text = " Conflicts with {} by {:.3f} mm.".format(
                        overlap_config.get("turnout_id", "another turnout"), overlap_length
                    )
            self.host_summary.setText(
                "Host length {:.3f} mm. Valid switch-toe chainage for this orientation: {}. "
                "Inherited template: {:.3f} mm wide x {:.3f} mm thick.{}".format(
                    host_data["total"],
                    "{:.3f} to {:.3f} mm".format(minimum, maximum) if maximum >= minimum - GEOMETRY_TOLERANCE else "no complete C10 fits",
                    width,
                    thickness,
                    overlap_text,
                )
            )
            if maximum >= minimum - GEOMETRY_TOLERANCE:
                mapping = turnout_mapping_metrics(
                    host_data,
                    self.chainage_box.value(),
                    orientation,
                    str(self.handing_combo.currentText()),
                    dimensions,
                )
                host_radius = mapping["host_minimum_radius"]
                turnout_radius = mapping["turnout_minimum_radius"]
                radius_text = "sampled host minimum {}; sampled turnout-road minimum {}".format(
                    "{:.3f} mm".format(host_radius) if host_radius is not None else "straight",
                    "{:.3f} mm".format(turnout_radius) if turnout_radius is not None else "straight",
                )
            else:
                radius_text = "no complete C10 fits"
            timber_layout = rea_c10_timber_layout(dimensions, width)
            timber_total = sum(float(item["length"]) for item in timber_layout)
            outside_count = len([item for item in timber_layout if float(item["outside_template_by"]) > 0.05])
            void_count = len([item for item in timber_layout if float(item["internal_template_void"]) > 0.05])
            timber_status = (
                "all outlines remain in the combined template envelope"
                if outside_count == 0 and void_count == 0
                else "{} outline(s) exceed the envelope and {} cross a strip void".format(outside_count, void_count)
            )
            self.preview_label.setText(
                "Prototype-natural C10 reference: switch radius {:.3f} mm; straight-reference turnout radius {:.3f} mm; "
                "module length {:.3f} mm. At the selected chainage: {}. Timbering: {} pieces, {:.1f} mm combined model "
                "length; {}. The complete turnout is mapped through the host alignment, including straight, constant-radius, "
                "Euler and segment-boundary changes.".format(
                    dimensions["switch_radius"], dimensions["turnout_radius"],
                    dimensions["module_end_x"] - dimensions["module_start_x"], radius_text,
                    len(timber_layout), timber_total, timber_status,
                )
            )
            editing = self.editing_turnout_id is not None
            self.create_button.setEnabled(valid and not editing)
            proposed = self.proposed_config() or {}
            changes = turnout_configuration_change_summary(self.editing_original_config, proposed) if editing else []
            self.apply_edit_button.setEnabled(valid and editing and bool(changes))
            for button in self.nudge_buttons:
                button.setEnabled(maximum >= minimum - GEOMETRY_TOLERANCE)
            if editing:
                self.edit_status_label.setText(
                    "Editing {} transactionally. {}".format(
                        self.editing_turnout_id,
                        "; ".join(changes) if changes else "No settings have changed.",
                    )
                )
        except Exception as error:
            self.host_summary.setText("Turnout validation failed: {}".format(error))
            self.preview_label.setText("")
            self.create_button.setEnabled(False)
            self.apply_edit_button.setEnabled(False)

    def refresh_turnouts(self, selected_id=None):
        wanted = str(selected_id or "")
        self.turnouts = existing_turnout_configs(self.doc)
        self.table.setRowCount(len(self.turnouts))
        selected_row = -1
        for row, config in enumerate(self.turnouts):
            values = [
                config.get("turnout_id", ""),
                config.get("template_set_id", ""),
                config.get("route_name", "") or "Curve",
                config.get("track_name", ""),
                "{:.3f}".format(float(config.get("toe_chainage", 0.0))),
                config.get("handing", ""),
                config.get("orientation", ""),
                "Integrated" if turnout_integration_by_id(self.doc, config.get("turnout_id")) is not None else "Separate module",
            ]
            for column, value in enumerate(values):
                self.table.setItem(row, column, QtWidgets.QTableWidgetItem(str(value)))
            if wanted and str(config.get("turnout_id") or "") == wanted:
                selected_row = row
        if selected_row >= 0:
            self.table.selectRow(selected_row)
        self.update_selection_buttons()
        if hasattr(self, "chair_analysis_panel"):
            self.chair_analysis_panel.refresh()

    def update_selection_buttons(self):
        config = self.current_turnout_config()
        selected = config is not None
        editing = self.editing_turnout_id is not None
        integrated = bool(selected and turnout_integration_by_id(self.doc, config.get("turnout_id")) is not None)
        self.edit_button.setEnabled(selected and not editing and not integrated)
        self.extend_crossover_button.setEnabled(selected and not editing and not integrated)
        self.integrate_button.setEnabled(selected and not editing and not integrated)
        self.remove_integration_button.setEnabled(selected and not editing and integrated)
        self.reference_button.setEnabled(selected and not editing)
        self.remove_button.setEnabled(selected and not editing and not integrated)
        if hasattr(self, "chair_analysis_panel"):
            self.chair_analysis_panel.refresh()
        if hasattr(self, "workflow_panel"):
            self.update_guided_workflow()

    def begin_edit_turnout(self):
        config = self.current_turnout_config()
        if config is None:
            return
        if turnout_integration_by_id(self.doc, config.get("turnout_id")) is not None:
            QtWidgets.QMessageBox.information(
                self,
                versioned_dialog_title("Integrated turnout edit"),
                "Remove the host-template integration before editing this turnout. The manager will restore the original host production records first, after which the turnout can be moved or changed safely.",
            )
            return
        host_name = str(config.get("host_object") or "")
        host_index = next((index for index, host in enumerate(self.hosts) if str(host.Name) == host_name), -1)
        if host_index < 0:
            QtWidgets.QMessageBox.critical(
                self,
                versioned_dialog_title("Turnout edit error"),
                "The original host centreline for {} is no longer available.".format(config.get("turnout_id", "the selected turnout")),
            )
            return
        self.editing_turnout_id = str(config.get("turnout_id") or "")
        self.editing_original_config = dict(config)
        self.host_combo.setCurrentIndex(host_index)
        self._set_combo_text(self.orientation_combo, config.get("orientation", TURNOUT_ORIENTATION_FACING))
        self._set_combo_text(self.handing_combo, config.get("handing", TURNOUT_HAND_LEFT))
        self.gauge_box.setValue(float(config.get("track_gauge", TURNOUT_DEFAULT_GAUGE)))
        self.flangeway_box.setValue(float(config.get("flangeway", TURNOUT_DEFAULT_FLANGEWAY)))
        self.timber_outline_box.setChecked(bool(config.get("timber_outlines", config.get("timber_references", True))))
        self.timber_centre_box.setChecked(bool(config.get("timber_centres", False)))
        self.timber_number_box.setChecked(bool(config.get("timber_numbers", True)))
        self.timber_length_box.setChecked(bool(config.get("timber_length_labels", False)))
        self.datum_box.setChecked(bool(config.get("construction_marks", True)))
        self.update_host_summary()
        self.chainage_box.setValue(float(config.get("toe_chainage", 0.0)))
        self._set_edit_mode(True)
        upgrade_notes = []
        if int(config.get("rail_geometry_revision") or 0) < TURNOUT_RAIL_GEOMETRY_REVISION:
            upgrade_notes.append("complete common-crossing rail geometry")
        if int(config.get("timber_geometry_revision") or 0) < TURNOUT_TIMBER_GEOMETRY_REVISION:
            upgrade_notes.append("source-driven REA timber outlines and identities")
        if upgrade_notes:
            self.edit_status_label.setText(
                "{} can be upgraded transactionally to {}. Press Apply turnout changes; no placement change is required.".format(
                    self.editing_turnout_id, " and ".join(upgrade_notes)
                )
            )

    def cancel_turnout_edit(self):
        identifier = self.editing_turnout_id
        self.editing_turnout_id = None
        self.editing_original_config = None
        self.edit_status_label.setText("Edit cancelled. No turnout geometry or production records were changed.")
        self._set_edit_mode(False)
        if identifier:
            self.refresh_turnouts(selected_id=identifier)

    def apply_turnout_edit(self):
        identifier = self.editing_turnout_id
        old_config = self.editing_original_config
        host = self.current_host()
        if not identifier or old_config is None or host is None:
            return
        proposed = self.proposed_config() or {}
        changes = turnout_configuration_change_summary(old_config, proposed)
        if not changes:
            QtWidgets.QMessageBox.information(self, versioned_dialog_title("Turnout edit"), "No turnout settings have changed.")
            return
        answer = QtWidgets.QMessageBox.question(
            self,
            versioned_dialog_title("Apply turnout changes"),
            "Update {} with the following changes?\n\n{}\n\nThe complete replacement geometry will be validated first. Existing geometry and production records remain intact if any step fails.".format(
                identifier, "\n".join("- " + item for item in changes)
            ),
            QtWidgets.QMessageBox.Yes | QtWidgets.QMessageBox.No,
            QtWidgets.QMessageBox.No,
        )
        if answer != QtWidgets.QMessageBox.Yes:
            return
        try:
            config = edit_curve_inheriting_c10_turnout(
                self.doc,
                identifier,
                host,
                self.chainage_box.value(),
                str(self.handing_combo.currentText()),
                str(self.orientation_combo.currentText()),
                self.gauge_box.value(),
                self.flangeway_box.value(),
                self.timber_outline_box.isChecked(),
                self.timber_centre_box.isChecked(),
                self.timber_number_box.isChecked(),
                self.timber_length_box.isChecked(),
                self.datum_box.isChecked(),
            )
            self.editing_turnout_id = None
            self.editing_original_config = None
            self._set_edit_mode(False)
            self.refresh_turnouts(selected_id=identifier)
            if Gui is not None:
                try:
                    Gui.activeDocument().activeView().viewTop()
                    Gui.activeDocument().activeView().fitAll()
                except Exception:
                    pass
            self.edit_status_label.setText("{} updated successfully. Its identity and source-object names were retained.".format(identifier))
            QtWidgets.QMessageBox.information(
                self,
                versioned_dialog_title("REA C10 turnout updated"),
                "Updated {} at switch-toe chainage {:.3f} mm. The change was committed as one transaction; the host track and established railway geometry remain unchanged.".format(
                    identifier, float(config.get("toe_chainage", 0.0))
                ),
            )
        except Exception as error:
            QtWidgets.QMessageBox.critical(self, versioned_dialog_title("Turnout edit error"), str(error))

    def create_turnout(self):
        host = self.current_host()
        if host is None or self.editing_turnout_id is not None:
            return
        try:
            config = create_curve_inheriting_c10_turnout(
                self.doc,
                host,
                self.chainage_box.value(),
                str(self.handing_combo.currentText()),
                str(self.orientation_combo.currentText()),
                self.gauge_box.value(),
                self.flangeway_box.value(),
                self.timber_outline_box.isChecked(),
                self.timber_centre_box.isChecked(),
                self.timber_number_box.isChecked(),
                self.timber_length_box.isChecked(),
                self.datum_box.isChecked(),
            )
            self.refresh_turnouts(selected_id=config.get("turnout_id"))
            if Gui is not None:
                try:
                    Gui.activeDocument().activeView().viewTop()
                    Gui.activeDocument().activeView().fitAll()
                except Exception:
                    pass
            QtWidgets.QMessageBox.information(
                self,
                versioned_dialog_title("REA C10 turnout created"),
                (
                    "Created {turnout_id} on {track_name} at switch-toe chainage {toe_chainage:.3f} mm.\n\n"
                    "The turnout inherited the complete host alignment. Existing track, platform, formation, "
                    "section and numbering objects were not changed. Source-driven REA timbering was created as separate exportable geometry. Sampled turnout-road minimum radius: {sampled_radius}."
                ).format(
                    sampled_radius=(
                        "{:.3f} mm".format(config["turnout_minimum_radius_sampled"])
                        if config.get("turnout_minimum_radius_sampled") is not None else "straight"
                    ),
                    **config
                ),
            )
        except Exception as error:
            QtWidgets.QMessageBox.critical(self, versioned_dialog_title("Turnout creation error"), str(error))

    def begin_selected_turnout_extension(self):
        """Automatically convert the selected standalone turnout into a crossover."""
        config = self.current_turnout_config()
        if config is None or self.editing_turnout_id is not None:
            return
        identifier = str(config.get("turnout_id") or "")
        if turnout_integration_by_id(self.doc, identifier) is not None:
            QtWidgets.QMessageBox.information(
                self,
                versioned_dialog_title("Integrated turnout conversion"),
                "Remove the host-template integration before converting this turnout. That restores the exact original host and standalone-turnout production records first.",
            )
            return

        self.extend_crossover_button.setEnabled(False)
        cursor_active = False
        try:
            QtWidgets.QApplication.setOverrideCursor(QtCore.Qt.WaitCursor)
            cursor_active = True
            QtWidgets.QApplication.processEvents()
        except Exception:
            pass
        try:
            resolved = resolve_automatic_turnout_crossover_extension(
                self.doc,
                identifier,
                self.crossover_panel.minimum_radius_box.value(),
            )
            solved = resolved["solved"]
            connector = solved.get("connector") or {}
            connector_radius = connector.get("minimum_radius")
            radius_text = (
                "straight"
                if connector_radius is None
                else "{:.3f} mm".format(float(connector_radius))
            )
            if cursor_active:
                try:
                    QtWidgets.QApplication.restoreOverrideCursor()
                    cursor_active = False
                except Exception:
                    pass
            answer = QtWidgets.QMessageBox.question(
                self,
                versioned_dialog_title("Convert turnout to crossover"),
                (
                    "Convert {turnout_id} into a managed crossover using the automatically detected neighbouring track?\n\n"
                    "Neighbouring track: {host_b}\n"
                    "Track separation: {separation:.3f} mm\n"
                    "Host A toe: {toe_a:.3f} mm\n"
                    "Host B toe: {toe_b:.3f} mm\n"
                    "Arrangement: {arrangement}\n"
                    "Handing retained: {handing}\n"
                    "Connecting-road minimum radius: {radius}\n\n"
                    "The complete geometry has already passed the crossover solver. The original turnout remains untouched if FreeCAD cannot build or commit any part of the replacement."
                ).format(
                    turnout_id=identifier,
                    host_b=resolved["host_b_label"],
                    separation=resolved["track_separation"],
                    toe_a=resolved["toe_chainage_a"],
                    toe_b=resolved["toe_chainage_b"],
                    arrangement=resolved["arrangement"],
                    handing=resolved["handing"],
                    radius=radius_text,
                ),
                QtWidgets.QMessageBox.Yes | QtWidgets.QMessageBox.No,
                QtWidgets.QMessageBox.No,
            )
            if answer != QtWidgets.QMessageBox.Yes:
                return

            try:
                QtWidgets.QApplication.setOverrideCursor(QtCore.Qt.WaitCursor)
                cursor_active = True
                QtWidgets.QApplication.processEvents()
            except Exception:
                pass
            crossover_config = extend_turnout_to_rea_c10_crossover(
                self.doc,
                identifier,
                resolved["host_b"],
                resolved["minimum_radius"],
                pre_solved=solved,
            )
            self.refresh_turnouts()
            self.crossover_panel.refresh_hosts()
            self.crossover_panel.refresh_crossovers(crossover_config.get("crossover_id"))
            self.mode_tabs.setCurrentWidget(self.crossover_panel)
            if cursor_active:
                try:
                    QtWidgets.QApplication.restoreOverrideCursor()
                    cursor_active = False
                except Exception:
                    pass
            if Gui is not None:
                try:
                    Gui.activeDocument().activeView().viewTop()
                    Gui.activeDocument().activeView().fitAll()
                except Exception:
                    pass
            QtWidgets.QMessageBox.information(
                self,
                versioned_dialog_title("Turnout converted to crossover"),
                "Converted {} into {} using neighbouring track {}. Host selection, second-turnout placement and connecting geometry were resolved automatically and committed as one transaction.".format(
                    identifier,
                    crossover_config.get("crossover_id", "the managed crossover"),
                    resolved["host_b_label"],
                ),
            )
        except Exception as error:
            QtWidgets.QMessageBox.critical(
                self,
                versioned_dialog_title("Automatic crossover conversion error"),
                str(error),
            )
        finally:
            if cursor_active:
                try:
                    QtWidgets.QApplication.restoreOverrideCursor()
                except Exception:
                    pass
            self.update_selection_buttons()

    def integrate_selected_turnout(self):
        config = self.current_turnout_config()
        if config is None or self.editing_turnout_id is not None:
            return
        identifier = str(config.get("turnout_id") or "")
        answer = QtWidgets.QMessageBox.question(
            self,
            versioned_dialog_title("Integrate turnout into host template"),
            "Create a derived integrated host template for {}?\n\nThe affected host production records and the separate turnout-template records will be replaced in the production catalogue. Original FreeCAD objects remain in the document, hidden and available for exact restoration. Rail, timber and datum records remain separate.".format(identifier),
            QtWidgets.QMessageBox.Yes | QtWidgets.QMessageBox.No,
            QtWidgets.QMessageBox.No,
        )
        if answer != QtWidgets.QMessageBox.Yes:
            return
        try:
            integration = create_turnout_host_integration(self.doc, identifier)
            self.refresh_turnouts(selected_id=identifier)
            sections = integration.get("affected_sections") or []
            QtWidgets.QMessageBox.information(
                self,
                versioned_dialog_title("Turnout integrated"),
                "Integrated {} into its host template. {} Original source objects and production metadata were retained for transactional restoration.".format(
                    identifier,
                    "Affected sections: {}.".format(", ".join("{:02d}".format(int(item)) for item in sections)) if sections else "The complete unsplit host template was replaced.",
                ),
            )
        except Exception as error:
            QtWidgets.QMessageBox.critical(self, versioned_dialog_title("Turnout integration error"), str(error))

    def remove_selected_integration(self):
        config = self.current_turnout_config()
        if config is None or self.editing_turnout_id is not None:
            return
        identifier = str(config.get("turnout_id") or "")
        answer = QtWidgets.QMessageBox.question(
            self,
            versioned_dialog_title("Remove host integration"),
            "Remove the derived host integration for {} and restore the exact original host and separate-turnout production records?".format(identifier),
            QtWidgets.QMessageBox.Yes | QtWidgets.QMessageBox.No,
            QtWidgets.QMessageBox.No,
        )
        if answer != QtWidgets.QMessageBox.Yes:
            return
        try:
            remove_turnout_host_integration(self.doc, identifier)
            self.refresh_turnouts(selected_id=identifier)
            QtWidgets.QMessageBox.information(
                self,
                versioned_dialog_title("Host integration removed"),
                "The integrated copies were removed and the original host-template and separate turnout production records were restored.",
            )
        except Exception as error:
            QtWidgets.QMessageBox.critical(self, versioned_dialog_title("Integration removal error"), str(error))

    def extract_selected_reference(self):
        config = self.current_turnout_config()
        if config is None or self.editing_turnout_id is not None:
            return
        identifier = str(config.get("turnout_id") or "")
        try:
            result = create_turnout_reference_copy(self.doc, identifier)
            QtWidgets.QMessageBox.information(
                self,
                versioned_dialog_title("Turnout reference copy created"),
                "Created {} as an independent reference copy of {}. It contains copied turnout geometry only and is deliberately excluded from the production catalogue to prevent duplicate manufacturing outputs.".format(
                    result.get("reference_id", "the reference copy"), identifier
                ),
            )
        except Exception as error:
            QtWidgets.QMessageBox.critical(self, versioned_dialog_title("Reference-copy error"), str(error))

    def remove_turnout(self):
        config = self.current_turnout_config()
        if config is None or self.editing_turnout_id is not None:
            return
        turnout_id = str(config.get("turnout_id") or "")
        answer = QtWidgets.QMessageBox.question(
            self,
            versioned_dialog_title("Remove turnout"),
            "Remove {} and its separate production records? Any host integration must be removed first. The original host railway geometry will remain unchanged.".format(turnout_id),
            QtWidgets.QMessageBox.Yes | QtWidgets.QMessageBox.No,
            QtWidgets.QMessageBox.No,
        )
        if answer != QtWidgets.QMessageBox.Yes:
            return
        try:
            remove_curve_inheriting_turnout(self.doc, turnout_id)
            self.refresh_turnouts()
        except Exception as error:
            QtWidgets.QMessageBox.critical(self, versioned_dialog_title("Turnout removal error"), str(error))

    def close_manager(self):
        if self.crossover_panel.extending_turnout_id is not None:
            answer = QtWidgets.QMessageBox.question(
                self,
                versioned_dialog_title("Cancel turnout extension"),
                "Cancel the prepared turnout extension and close? No document objects have yet been changed.",
                QtWidgets.QMessageBox.Yes | QtWidgets.QMessageBox.No,
                QtWidgets.QMessageBox.No,
            )
            if answer != QtWidgets.QMessageBox.Yes:
                return
            self.crossover_panel.cancel_turnout_extension()
        if self.editing_turnout_id is not None:
            answer = QtWidgets.QMessageBox.question(
                self,
                versioned_dialog_title("Cancel turnout edit"),
                "Cancel the current edit and close? No turnout changes have yet been applied.",
                QtWidgets.QMessageBox.Yes | QtWidgets.QMessageBox.No,
                QtWidgets.QMessageBox.No,
            )
            if answer != QtWidgets.QMessageBox.Yes:
                return
        self.accept()

def run_macro():
    doc = App.ActiveDocument
    if doc is None:
        doc = App.newDocument("ModelRailwayCurve")

    settings_source = latest_generated_settings(doc)
    existing_template = latest_generated_template(doc)
    if settings_source is None:
        settings_source = existing_template
    assembly_label_config = read_assembly_label_config(settings_source)

    remembered_inputs = read_last_dialog_inputs(doc)
    if remembered_inputs is not None:
        transition_default = remembered_inputs["transition"]
        radius_default = remembered_inputs["radius"]
        angle_default = remembered_inputs["angle"]
        main_width_default = remembered_inputs["main_width"]
        track_configs_default = remembered_inputs["track_configs"]
        straight_configs_default = remembered_inputs["straight_configs"]
        selected_straight_index_default = remembered_inputs[
            "selected_straight_index"
        ]
        platform_configs_default = remembered_inputs["platform_configs"]
        selected_platform_id_default = remembered_inputs["selected_platform_id"]
        selected_platform_index_default = remembered_inputs["selected_platform_index"]
        formation_config_default = remembered_inputs["formation_config"]
        section_config_default = remembered_inputs["section_config"]
        registration_config_default = remembered_inputs["registration_config"]
        template_assembly_config_default = remembered_inputs["template_assembly_config"]
        production_export_config_default = remembered_inputs["production_export_config"]
    else:
        transition_default = quantity_value(
            settings_source,
            "TransitionLength",
            DEFAULT_TRANSITION_LENGTH,
        )
        radius_default = quantity_value(settings_source, "CurveRadius", DEFAULT_RADIUS)
        angle_default = quantity_value(settings_source, "TotalTurnAngle", DEFAULT_TURN_ANGLE)
        main_width_default = quantity_value(
            settings_source,
            "MainTemplateWidth",
            quantity_value(settings_source, "TemplateWidth", DEFAULT_MAIN_TEMPLATE_WIDTH),
        )
        track_configs_default = read_track_configs(settings_source, transition_default)
        straight_configs_default = read_straight_configs(settings_source)
        selected_straight_index_default = 0
        platform_configs_default = read_platform_configs(settings_source)
        selected_platform_id_default = ""
        selected_platform_index_default = 0
        formation_config_default = read_formation_config(settings_source)
        section_config_default = read_section_config(settings_source)
        registration_config_default = read_registration_config(settings_source)
        template_assembly_config_default = read_template_assembly_config(settings_source)
        production_export_config_default = read_production_export_config(settings_source)
    # Keep the selected set's material-report settings available to the main
    # dialogue and Stage 6 configuration utility without changing document
    # settings until the user deliberately accepts Generate.
    material_report_config_default = read_material_report_config(settings_source)
    exporter_capabilities = detect_exporter_capabilities()

    existing_set_total = generated_set_count(doc)
    dialog = CurveInputDialog(
        transition_default,
        radius_default,
        angle_default,
        main_width_default,
        track_configs_default,
        straight_configs_default,
        selected_straight_index_default,
        platform_configs_default,
        selected_platform_id_default,
        selected_platform_index_default,
        formation_config_default,
        section_config_default,
        registration_config_default,
        template_assembly_config_default,
        assembly_label_config,
        production_export_config_default,
        material_report_config_default,
        exporter_capabilities,
        existing_set_total,
    )
    if remembered_inputs is not None:
        dialog.output_mode_box.setCurrentIndex(
            1 if remembered_inputs["output_mode"] == OUTPUT_CREATE_NEW else 0
        )

    accepted_code = getattr(QtWidgets.QDialog, "Accepted", None)
    if accepted_code is None:
        accepted_code = QtWidgets.QDialog.DialogCode.Accepted
    if dialog_exec(dialog) != accepted_code:
        return

    (
        transition,
        radius,
        angle,
        main_width,
        track_configs,
        straight_configs,
        selected_straight_index,
        platform_configs,
        selected_platform_id,
        selected_platform_index,
        formation_config,
        section_config,
        registration_config,
        template_assembly_config,
        assembly_label_config,
        production_export_config,
        material_report_config,
        output_mode,
    ) = dialog.values()

    # Persist the accepted dialogue state before validation or geometry work.
    # A later validation failure or FreeCAD kernel failure will not force the
    # user to re-enter every value on the next run.
    remember_last_material_report_config(material_report_config)
    remember_last_dialog_inputs(
        doc,
        transition,
        radius,
        angle,
        main_width,
        track_configs,
        straight_configs,
        selected_straight_index,
        platform_configs,
        selected_platform_id,
        selected_platform_index,
        formation_config,
        section_config,
        registration_config,
        template_assembly_config,
        production_export_config,
        output_mode,
    )

    if output_mode == OUTPUT_REPLACE and existing_set_total > 0:
        try:
            yes_button = QtWidgets.QMessageBox.Yes
            no_button = QtWidgets.QMessageBox.No
        except AttributeError:
            yes_button = QtWidgets.QMessageBox.StandardButton.Yes
            no_button = QtWidgets.QMessageBox.StandardButton.No
        answer = QtWidgets.QMessageBox.question(
            None,
            versioned_dialog_title("Replace generated templates"),
            (
                "This will remove {} existing macro-generated template set{} "
                "from the active document and create one clean replacement.\n\n"
                "All objects carrying this macro's generator identity, plus "
                "recognised legacy templates and centrelines, will be removed. "
                "Unrelated FreeCAD objects will be preserved. No object is removed "
                "until all requested geometry has passed validation. Continue?"
            ).format(
                existing_set_total,
                "" if existing_set_total == 1 else "s",
            ),
            yes_button | no_button,
            no_button,
        )
        if answer != yes_button:
            return

    try:
        if radius <= 0.0:
            raise ValueError("The main curve radius must be greater than zero.")
        if transition < 0.0:
            raise ValueError("The main transition length cannot be negative.")
        if main_width <= 0.0:
            raise ValueError("The main template width must be greater than zero.")
        if radius <= main_width / 2.0:
            raise ValueError("The main radius must exceed half the main template width.")
        if abs(angle) <= 1.0e-9:
            raise ValueError("The total turn angle cannot be zero.")
        validate_platform_configurations(platform_configs)
        validate_production_export_request(
            production_export_config,
            exporter_capabilities,
        )

        turn_sign = 1.0 if angle > 0.0 else -1.0
        total_angle = math.radians(abs(angle))
        circle_centre = main_circle_centre(transition, radius)

        main_alignment = build_concentric_core(
            circle_centre,
            radius,
            transition,
            transition,
            total_angle,
            "Main Track",
        )
        main_alignment.update(
            {
                "name": "Main Track",
                "side": "Main",
                "alignment_mode": "Main alignment",
                "start_spacing": 0.0,
                "curve_spacing": 0.0,
                "finish_spacing": 0.0,
                "width": main_width,
                "create_template": True,
                "show_centreline": True,
                "minimum_radius": radius,
            }
        )

        track_alignments = []
        for config in track_configs:
            track_alignments.append(
                prepare_track_alignment(
                    config,
                    circle_centre,
                    radius,
                    total_angle,
                    main_alignment,
                )
            )

        all_alignments = [main_alignment] + track_alignments
        add_common_straight_extensions(all_alignments, total_angle)

        # Version 7.4 exact straight-spacing verification remains unchanged.
        for alignment in track_alignments:
            start_difference = alignment["extended_start"][1] - main_alignment["extended_start"][1]
            end_normal_x, end_normal_y = left_normal(total_angle)
            end_difference_x = alignment["extended_end"][0] - main_alignment["extended_end"][0]
            end_difference_y = alignment["extended_end"][1] - main_alignment["extended_end"][1]
            finish_difference = dot_xy(
                end_difference_x,
                end_difference_y,
                end_normal_x,
                end_normal_y,
            )
            side_factor = signed_side_factor(alignment["side"])
            calculated_entry = abs(start_difference)
            calculated_exit = abs(finish_difference)

            if start_difference * side_factor <= 0.0 or finish_difference * side_factor <= 0.0:
                raise ValueError(
                    "Internal alignment check failed for '{}': a straight ended on "
                    "the wrong side of the main track.".format(alignment["name"])
                )
            if abs(calculated_entry - alignment["start_spacing"]) > 0.01:
                raise ValueError(
                    "Internal entry-spacing check failed for '{}': expected {:.3f} "
                    "mm, calculated {:.3f} mm.".format(
                        alignment["name"],
                        alignment["start_spacing"],
                        calculated_entry,
                    )
                )
            if abs(calculated_exit - alignment["finish_spacing"]) > 0.01:
                raise ValueError(
                    "Internal exit-spacing check failed for '{}': expected {:.3f} "
                    "mm, calculated {:.3f} mm.".format(
                        alignment["name"],
                        alignment["finish_spacing"],
                        calculated_exit,
                    )
                )

        tight_platform_tracks = [
            alignment
            for alignment in track_alignments
            if alignment["alignment_mode"] == MODE_PLATFORM
            and alignment["minimum_radius"] < (radius - 0.01)
        ]
        if tight_platform_tracks:
            warning_lines = [
                "{}: constant radius {:.3f} mm, peak minimum radius {:.3f} mm".format(
                    alignment["name"],
                    alignment["radius"],
                    alignment["minimum_radius"],
                )
                for alignment in tight_platform_tracks
            ]
            try:
                yes_button = QtWidgets.QMessageBox.Yes
                no_button = QtWidgets.QMessageBox.No
            except AttributeError:
                yes_button = QtWidgets.QMessageBox.StandardButton.Yes
                no_button = QtWidgets.QMessageBox.StandardButton.No
            answer = QtWidgets.QMessageBox.question(
                None,
                versioned_dialog_title("Confirm platform minimum radius"),
                (
                    "The platform transition remains in the correct turn direction, "
                    "but its curvature briefly becomes tighter than the main "
                    "constant radius. This is how the track reaches the wider "
                    "concentric platform curve without a reverse curve.\n\n"
                    "{}\n\n"
                    "No existing generated template has been removed. Continue?"
                ).format("\n".join(warning_lines)),
                yes_button | no_button,
                no_button,
            )
            if answer != yes_button:
                return

        for alignment in all_alignments:
            mirror_alignment_for_turn(alignment, turn_sign)
            alignment["total_length"] = polyline_length(alignment["points"])

        straight_route_results = build_straight_routes(
            straight_configs,
            all_alignments,
        )
        validate_connected_straight_routes(
            straight_route_results,
            all_alignments,
        )

        straight_production_results = prepare_straight_routes_production(
            straight_route_results,
            formation_config,
            section_config,
            registration_config,
            template_assembly_config,
        )

        platform_results = []
        for platform_index, stored_config in enumerate(platform_configs):
            platform_config = clone_platform_config(stored_config)
            platform_configs[platform_index] = platform_config
            if not platform_config["enabled"]:
                continue
            platform_number = platform_index + 1
            platform_geometry = calculate_platform_boundaries(
                platform_config,
                all_alignments,
                turn_sign,
            )
            if platform_geometry is None:
                continue
            platform_config["platform_length"] = platform_geometry["length"]
            platform_config["centre_offset"] = platform_geometry["centre_offset"]
            platform_config["start_inset"] = platform_geometry["start_inset"]
            platform_config["finish_inset"] = platform_geometry["finish_inset"]
            platform_shapes = create_platform_shapes(
                platform_geometry, platform_config
            )
            platform_plan_face = create_platform_plan_face(platform_geometry)
            platform_results.append({
                "platform_number": platform_number,
                "config": platform_config,
                "geometry": platform_geometry,
                "shapes": platform_shapes,
                "plan_face": platform_plan_face,
                "sections": [],
                "section_plan_faces": [],
                "create_unsplit": False,
            })
        validate_platform_relationships(platform_results, all_alignments)

        template_solids = []
        template_sources = []
        template_plan_faces = []
        track_protection_faces = []
        centreline_data = []
        for alignment_index, alignment in enumerate(all_alignments):
            protection_face = create_template_plan_face(
                alignment["points"],
                alignment["headings"],
                alignment["width"],
            )
            track_protection_faces.append(protection_face)
            if alignment["create_template"]:
                solid = create_template_shape(
                    alignment["points"],
                    alignment["headings"],
                    alignment["width"],
                )
                template_solids.append(solid)
                template_plan_faces.append(protection_face)
                template_sources.append({
                    "alignment": alignment,
                    "solid": solid,
                    "plan_face": protection_face,
                    "track_number": alignment_index + 1,
                })
            centreline_data.append(
                {
                    "name": alignment["name"],
                    "points": alignment["points"],
                    "show": alignment["show_centreline"],
                }
            )

        if not template_solids:
            raise ValueError("At least one printable template strip is required.")
        compound_template = Part.makeCompound(template_solids)

        straight_template_outputs = []
        straight_centreline_outputs = []
        for route_index, bundle in enumerate(straight_production_results):
            route = bundle["route"]
            if bundle["create_unsplit_template"]:
                for source in bundle["template_sources"]:
                    alignment = source["alignment"]
                    straight_template_outputs.append({
                        "route_index": route_index,
                        "track_index": int(source["track_number"]) - 1,
                        "alignment": alignment,
                        "shape": source["solid"],
                        "route_id": route["route_id"],
                        "route_name": route["name"],
                        "section_hidden": bool(bundle["section_track_templates"]),
                    })
            for track_index, alignment in enumerate(route["alignments"]):
                if alignment["show_centreline"]:
                    straight_centreline_outputs.append({
                        "route_index": route_index,
                        "track_index": track_index,
                        "alignment": alignment,
                        "shape": create_centreline_wire(
                            alignment["points"],
                            alignment["template_thickness"],
                        ),
                        "route_id": route["route_id"],
                        "route_name": route["name"],
                    })

        platform_geometries = [
            result["geometry"] for result in platform_results
        ]
        platform_plan_faces = [
            result["plan_face"] for result in platform_results
        ]

        curve_formation_config = formation_config_for_curve_connections(
            formation_config,
            straight_route_results,
        )
        formation_geometry = create_formation_geometry_multi(
            curve_formation_config,
            all_alignments,
            track_protection_faces,
            platform_geometries,
            platform_plan_faces,
        )

        section_plan = calculate_section_plan(main_alignment["total_length"], section_config)
        section_active = bool(section_plan["enabled"])
        if section_active:
            selected_count = sum(
                1
                for selected in (
                    section_config["section_track_templates"],
                    section_config["section_platform"],
                    section_config["section_formation"],
                )
                if selected
            )
            if selected_count == 0:
                raise ValueError("Enable at least one output layer for sectioning.")
            if section_config["section_platform"]:
                body_platform_results = [
                    result for result in platform_results
                    if result["shapes"] is not None
                    and result["shapes"].get("body_shape") is not None
                ]
                if not body_platform_results:
                    raise ValueError(
                        "Platform sectioning requires at least one enabled 2D platform face or 3D platform body."
                    )
            if section_config["section_formation"] and formation_geometry is None:
                raise ValueError("Formation-board sectioning requires formation-board output.")
            # Registration features belong only to sectioned formation boards.
            # When formation-board sectioning is not selected, the disabled
            # registration controls are intentionally ignored.

        template_assembly_active = bool(
            section_active
            and section_config["section_track_templates"]
            and template_assembly_config["enabled"]
        )
        if (
            template_assembly_active
            and template_assembly_config["matching_formation_holes"]
            and not formation_config["enabled"]
        ):
            raise ValueError(
                "Matching formation-board fixing holes require formation-board output."
            )

        track_engraving_shape = None
        platform_engraving_shape = None
        if formation_config["enabled"] and formation_config["create_track_engraving"]:
            engraving_alignments = list(all_alignments)
            for bundle in straight_production_results:
                engraving_alignments.extend(bundle["alignments"])
            track_engraving_shape = create_track_engraving_shape(
                engraving_alignments
            )
        if (
            formation_config["enabled"]
            and formation_config["create_platform_engraving"]
            and platform_results
        ):
            platform_engraving_shape = create_platforms_engraving_shape(
                platform_geometries
            )

        section_masks = []
        template_sections = []
        template_sections_by_track = []
        template_section_stations = []
        template_joint_shapes = []
        template_hole_profile_shapes = []
        template_hole_faces = []
        formation_matching_hole_shape = None
        effective_template_hole_clearance = 0.0
        formation_section_faces = []
        formation_section_outlines = []
        formation_section_solids = []
        registration_shapes = []
        alignment_hole_shapes = []
        section_number_shapes = []

        if section_active:
            source_shapes = [compound_template]


            for result in platform_results:
                body_shape = (
                    result["shapes"].get("body_shape")
                    if result["shapes"] is not None
                    else None
                )
                if body_shape is not None:
                    source_shapes.append(body_shape)
            if formation_geometry is not None:
                source_shapes.append(formation_geometry["body"])
            z_min = -max(
                formation_config["board_thickness"] if formation_geometry is not None else 0.0,
                1.0,
            ) - 10.0
            platform_z_values = [
                result["config"]["platform_height"]
                for result in platform_results
                if result["config"]["body_output"] == PLATFORM_SOLID
            ]
            z_max = max(
                platform_z_values + [TEMPLATE_THICKNESS]
            ) + 10.0
            section_masks = create_section_masks(
                main_alignment,
                section_plan,
                source_shapes,
                z_min,
                z_max,
            )

            if section_config["section_track_templates"]:
                for source in template_sources:
                    pieces = section_solid_shape(source["solid"], section_masks)
                    validate_section_partition(
                        source["solid"],
                        pieces,
                        "'{}' track-template".format(source["alignment"]["name"]),
                        require_every_section=True,
                    )
                    template_sections_by_track.append(pieces)
                template_section_stations = calculate_template_section_stations(
                    template_sources,
                    main_alignment,
                    section_plan,
                )
                if template_assembly_active:
                    (
                        template_sections_by_track,
                        template_joint_shapes,
                    ) = apply_track_template_joints(
                        template_sections_by_track,
                        template_sources,
                        main_alignment,
                        section_plan,
                        template_section_stations,
                        template_assembly_config,
                    )
                    if template_assembly_config["fixing_holes_enabled"]:
                        (
                            template_sections_by_track,
                            template_hole_profile_shapes,
                            template_hole_faces,
                            effective_template_hole_clearance,
                        ) = create_track_template_fixing_holes(
                            template_sections_by_track,
                            template_sources,
                            template_section_stations,
                            template_assembly_config,
                        )
                        if template_assembly_config["matching_formation_holes"]:
                            (
                                formation_geometry,
                                formation_matching_hole_shape,
                            ) = cut_formation_matching_holes(
                                formation_geometry,
                                template_hole_faces,
                                formation_config["board_thickness"],
                            )
                template_sections = combine_track_template_sections(
                    template_sections_by_track
                )
                if any(shape is None for shape in template_sections):
                    raise ValueError("A combined track-template section is missing.")
            if section_config["section_platform"]:
                for result in platform_results:
                    body_shape = (
                        result["shapes"].get("body_shape")
                        if result["shapes"] is not None
                        else None
                    )
                    if body_shape is None:
                        continue
                    result["sections"] = section_solid_shape(
                        body_shape,
                        section_masks,
                    )
                    validate_section_partition(
                        body_shape,
                        result["sections"],
                        "Platform {:02d} '{}'".format(
                            result["platform_number"],
                            result["config"]["name"],
                        ),
                        require_every_section=False,
                    )
                    result["section_plan_faces"] = section_plan_face(
                        result["plan_face"],
                        section_masks,
                    )
                    validate_section_partition(
                        result["plan_face"],
                        result["section_plan_faces"],
                        "Platform {:02d} '{}' plan outline".format(
                            result["platform_number"],
                            result["config"]["name"],
                        ),
                        require_every_section=False,
                    )
            if section_config["section_formation"]:
                formation_section_faces = section_plan_face(
                    formation_geometry["face"],
                    section_masks,
                )
                validate_section_partition(
                    formation_geometry["face"],
                    formation_section_faces,
                    "formation-board",
                    require_every_section=True,
                )
                (
                    formation_section_faces,
                    registration_shapes,
                    alignment_hole_shapes,
                ) = apply_registration_features(
                    formation_section_faces,
                    main_alignment,
                    section_plan,
                    formation_geometry["face"],
                    formation_geometry["protected_face"],
                    registration_config,
                )
                for face_shape in formation_section_faces:
                    if face_shape is None:
                        formation_section_outlines.append(None)
                        formation_section_solids.append(None)
                        continue
                    formation_section_outlines.append(
                        _outline_shape_from_face(face_shape)
                    )
                    formation_section_solids.append(
                        extrude_plan_shape_down(
                            face_shape,
                            formation_config["board_thickness"],
                        )
                    )

            if section_config["number_in_travel_order"]:
                for index, (start_station, finish_station) in enumerate(section_plan["ranges"]):
                    if formation_geometry is not None:
                        placement_face = formation_geometry["face"]
                        if (
                            section_config["section_formation"]
                            and index < len(formation_section_faces)
                            and formation_section_faces[index] is not None
                        ):
                            placement_face = formation_section_faces[index]
                        origin, heading = find_section_number_origin(
                            placement_face,
                            formation_geometry["protected_face"],
                            main_alignment,
                            start_station,
                            finish_station,
                        )
                    else:
                        data = alignment_station_data(main_alignment)
                        origin, heading = interpolate_alignment_station(
                            data,
                            0.5 * (start_station + finish_station),
                        )
                    section_number_shapes.append(
                        create_section_number_shape(index + 1, origin, heading)
                    )

        preserve_unsplit = bool(section_config["preserve_unsplit"] or not section_active)
        create_unsplit_template = bool(
            preserve_unsplit or not section_config["section_track_templates"]
        )
        for result in platform_results:
            body_shape = (
                result["shapes"].get("body_shape")
                if result["shapes"] is not None
                else None
            )
            result["create_unsplit"] = bool(
                body_shape is not None
                and (preserve_unsplit or not section_config["section_platform"])
            )
        create_unsplit_formation = bool(
            formation_geometry is not None
            and (preserve_unsplit or not section_config["section_formation"])
        )

        planned_set_id = planned_template_set_id(doc, output_mode)
        catalogue_config = complete_production_record_config(
            production_export_config
        )
        production_schedule_records = build_production_export_records_multi(
            catalogue_config,
            all_alignments,
            template_sources,
            compound_template,
            template_plan_faces,
            template_sections_by_track,
            template_section_stations,
            template_hole_faces,
            template_joint_shapes,
            platform_results,
            formation_config,
            formation_geometry,
            formation_section_outlines,
            formation_section_solids,
            registration_shapes,
            alignment_hole_shapes,
            formation_matching_hole_shape,
            section_number_shapes,
            section_plan,
            track_engraving_shape,
            platform_engraving_shape,
            create_unsplit_template,
            create_unsplit_formation,
            template_assembly_config,
        )
        production_schedule_records.extend(
            build_straight_production_export_records(
                catalogue_config,
                straight_production_results,
                template_assembly_config,
            )
        )
        populate_production_record_track_names(
            production_schedule_records,
            all_alignments,
            straight_production_results,
        )
        assign_production_record_ids(
            production_schedule_records, planned_set_id
        )
        production_schedule_records, assembly_label_diagnostics = apply_assembly_labels_to_records(
            production_schedule_records,
            assembly_label_config,
            planned_set_id,
        )
        assign_production_record_ids(
            production_schedule_records, planned_set_id
        )

        production_export_records = []
        production_export_plan = None
        production_preflight_issues = []
        production_preflight_summary = None
        if production_export_config.get("enabled", False):
            production_export_records = filter_records_for_export_config(
                production_schedule_records, production_export_config
            )
            if not production_export_records:
                raise ValueError(
                    "None of the selected production-export groups exists in the current configuration."
                )
            production_export_plan = plan_production_export(
                production_export_records,
                production_export_config,
                planned_set_id,
            )
            if not production_export_plan["tasks"]:
                skipped_lines = []
                for item in production_export_plan.get("skipped", []):
                    skipped_lines.append(
                        "- {}: {}".format(
                            _export_record_report_name(item.get("record") or {}),
                            item.get("reason") or "No skip reason was recorded.",
                        )
                    )
                raise ValueError(
                    "No production files can be exported from the selected geometry and formats."
                    + (
                        "\n\nSkipped outputs:\n{}".format("\n".join(skipped_lines))
                        if skipped_lines
                        else " Review the export selections."
                    )
                )
            production_preflight_issues = run_production_preflight(
                doc,
                production_schedule_records,
                production_export_records,
                production_export_config,
                planned_set_id,
                section_config,
                registration_config,
                template_assembly_config,
                settings_obj=None,
                assembly_label_config=assembly_label_config,
                plan=production_export_plan,
                include_export_checks=True,
                probe_export_bounds=True,
            )
            production_preflight_summary = summarise_preflight(
                production_preflight_issues
            )
            blocking_report = preflight_blocking_report(
                production_preflight_issues
            )
            if blocking_report:
                raise ValueError(blocking_report)
            if not confirm_preflight_warnings(production_preflight_issues):
                raise ValueError(
                    "Production export was cancelled because its preflight warnings were not confirmed. "
                    "No generated object or existing export file has been changed."
                )
            ensure_production_export_directory(production_export_config)

        transaction_open = False
        removed_outputs = []
        settings_object = None
        template_object = None
        try:
            doc.openTransaction("Generate Version {} curve and straight production templates".format(MACRO_VERSION_NUMBER))
            transaction_open = True

            if output_mode == OUTPUT_REPLACE:
                removed_outputs = remove_all_generated_outputs(doc)
                set_id = planned_set_id
                suffix = "001"
                group_name = unique_internal_name(doc, GROUP_NAME)
            else:
                set_id = planned_set_id
                suffix = set_id.replace("SET-", "")
                group_name = unique_internal_name(doc, "{}_{}".format(GROUP_NAME, suffix))

            def set_name(base_name):
                if output_mode == OUTPUT_REPLACE:
                    return unique_internal_name(doc, base_name)
                return unique_internal_name(doc, "{}_{}".format(base_name, suffix))

            group = doc.addObject("App::DocumentObjectGroup", group_name)
            group.Label = "Model Railway Curve and Straight Tracks [{}]".format(set_id)
            tag_generated_object(group, "Group", set_id)

            straight_track_group = None
            straight_template_group = None
            straight_formation_group = None
            if straight_route_results:
                straight_track_group = doc.addObject(
                    "App::DocumentObjectGroup",
                    set_name(STRAIGHT_TRACK_GROUP_NAME),
                )
                straight_track_group.Label = "Straight Tracks [{}]".format(set_id)
                tag_generated_object(straight_track_group, "Group", set_id)
                group.addObject(straight_track_group)

                straight_template_group = doc.addObject(
                    "App::DocumentObjectGroup",
                    set_name(STRAIGHT_TEMPLATE_GROUP_NAME),
                )
                straight_template_group.Label = "Straight Track Templates [{}]".format(set_id)
                tag_generated_object(straight_template_group, "Group", set_id)
                group.addObject(straight_template_group)

                if any(
                    bundle.get("formation_geometry") is not None
                    for bundle in straight_production_results
                ):
                    straight_formation_group = doc.addObject(
                        "App::DocumentObjectGroup",
                        set_name(STRAIGHT_FORMATION_GROUP_NAME),
                    )
                    straight_formation_group.Label = "Straight Formation [{}]".format(set_id)
                    tag_generated_object(straight_formation_group, "Group", set_id)
                    group.addObject(straight_formation_group)

            # Part::Feature is used deliberately because it is supported by the same
            # FreeCAD builds that create the other output objects. A null Shape is
            # valid and lets this object act as the persistent settings container.
            settings_object = doc.addObject("Part::Feature", set_name(SETTINGS_NAME))
            settings_object.Label = "Railway Curve and Straight Settings [{}]".format(set_id)
            tag_generated_object(settings_object, "Settings", set_id)
            group.addObject(settings_object)

            if create_unsplit_template:
                template_object = doc.addObject("Part::Feature", set_name(TEMPLATE_NAME))
                template_object.Label = "Multi-Track Curve Template [{}]".format(set_id)
                template_object.Shape = compound_template
                tag_generated_object(template_object, "Template", set_id)
                tag_export_metadata(
                    template_object,
                    "TrackTemplateCompound",
                    EXPORT_CATEGORY_SOLID,
                )
                group.addObject(template_object)
                if Gui is not None:
                    template_object.ViewObject.ShapeColor = (0.82, 0.82, 0.82)
                    template_object.ViewObject.LineColor = (0.25, 0.25, 0.25)
                    template_object.ViewObject.Visibility = not bool(
                        section_active and section_config["section_track_templates"]
                    )

            centreline_base = CENTRELINE_PREFIX if output_mode == OUTPUT_REPLACE else "{}{}_".format(CENTRELINE_PREFIX, suffix)
            for index, data in enumerate(centreline_data):
                if not data["show"]:
                    continue
                object_name = unique_internal_name(doc, "{}{:02d}".format(centreline_base, index))
                centreline = doc.addObject("Part::Feature", object_name)
                centreline.Label = "{} Centreline [{}]".format(data["name"], set_id)
                centreline.Shape = create_centreline_wire(data["points"])
                tag_generated_object(centreline, "Centreline", set_id)
                tag_export_metadata(
                    centreline,
                    "TrackCentreline",
                    EXPORT_CATEGORY_ENGRAVING,
                    track_number=index + 1,
                )
                group.addObject(centreline)
                if Gui is not None:
                    centreline.ViewObject.LineColor = CENTRELINE_COLOURS[index % len(CENTRELINE_COLOURS)]
                    centreline.ViewObject.LineWidth = 3.0

            for output_index, output in enumerate(straight_template_outputs):
                alignment = output["alignment"]
                object_name = set_name(
                    "{}R{:02d}_T{:02d}".format(
                        STRAIGHT_TEMPLATE_PREFIX,
                        output["route_index"] + 1,
                        output["track_index"] + 1,
                    )
                )
                straight_template = doc.addObject("Part::Feature", object_name)
                straight_template.Label = "{} Template [{}]".format(
                    alignment["name"], set_id
                )
                straight_template.Shape = output["shape"]
                tag_generated_object(
                    straight_template, "StraightTrackTemplate", set_id
                )
                tag_route_metadata(
                    straight_template, output["route_id"], output["route_name"]
                )
                tag_export_metadata(
                    straight_template,
                    "TrackTemplateCompound",
                    EXPORT_CATEGORY_SOLID,
                    track_number=output["track_index"] + 1,
                )
                if straight_template_group is not None:
                    straight_template_group.addObject(straight_template)
                else:
                    group.addObject(straight_template)
                if Gui is not None:
                    straight_template.ViewObject.ShapeColor = (0.72, 0.78, 0.86)
                    straight_template.ViewObject.LineColor = (0.20, 0.30, 0.45)
                    straight_template.ViewObject.Visibility = not output["section_hidden"]

            for output_index, output in enumerate(straight_centreline_outputs):
                alignment = output["alignment"]
                object_name = set_name(
                    "{}R{:02d}_T{:02d}".format(
                        STRAIGHT_CENTRELINE_PREFIX,
                        output["route_index"] + 1,
                        output["track_index"] + 1,
                    )
                )
                straight_centreline = doc.addObject("Part::Feature", object_name)
                straight_centreline.Label = "{} Centreline [{}]".format(
                    alignment["name"], set_id
                )
                straight_centreline.Shape = output["shape"]
                tag_generated_object(
                    straight_centreline, "StraightTrackCentreline", set_id
                )
                tag_route_metadata(
                    straight_centreline, output["route_id"], output["route_name"]
                )
                tag_export_metadata(
                    straight_centreline,
                    "TrackCentreline",
                    EXPORT_CATEGORY_ENGRAVING,
                    track_number=output["track_index"] + 1,
                )
                if straight_track_group is not None:
                    straight_track_group.addObject(straight_centreline)
                else:
                    group.addObject(straight_centreline)
                if Gui is not None:
                    straight_centreline.ViewObject.LineColor = CENTRELINE_COLOURS[
                        output_index % len(CENTRELINE_COLOURS)
                    ]
                    straight_centreline.ViewObject.LineWidth = 3.0

            for route_index, bundle in enumerate(straight_production_results):
                route = bundle["route"]
                route_id = bundle["route_id"]
                route_name = bundle["route_name"]
                route_token = "R{:02d}".format(route_index + 1)
                formation_geometry_for_route = bundle["formation_geometry"]
                formation_config_for_route = bundle["formation_config"]

                if (
                    formation_geometry_for_route is not None
                    and bundle["create_unsplit_formation"]
                ):
                    output_type = formation_config_for_route["output_type"]
                    if output_type in (FORMATION_OUTLINE_ONLY, FORMATION_BOTH):
                        obj = doc.addObject(
                            "Part::Feature",
                            set_name("{}{}".format(
                                STRAIGHT_FORMATION_OUTLINE_PREFIX, route_token
                            )),
                        )
                        obj.Label = "{} Formation Board Perimeter [{}]".format(
                            route_name, set_id
                        )
                        obj.Shape = formation_geometry_for_route["outline"]
                        tag_generated_object(obj, "StraightFormationOutline", set_id)
                        tag_route_metadata(obj, route_id, route_name)
                        tag_export_metadata(
                            obj, "FormationPerimeter", EXPORT_CATEGORY_CUTTING
                        )
                        (straight_formation_group if straight_formation_group is not None else group).addObject(obj)
                        if Gui is not None:
                            obj.ViewObject.LineColor = (0.10, 0.55, 0.85)
                            obj.ViewObject.LineWidth = 3.0
                            obj.ViewObject.Visibility = bool(
                                formation_config_for_route["show_outline"]
                            )
                    if output_type in (FORMATION_SOLID_ONLY, FORMATION_BOTH):
                        obj = doc.addObject(
                            "Part::Feature",
                            set_name("{}{}".format(
                                STRAIGHT_FORMATION_BODY_PREFIX, route_token
                            )),
                        )
                        obj.Label = "{} Formation Board [{}]".format(route_name, set_id)
                        obj.Shape = formation_geometry_for_route["body"]
                        tag_generated_object(obj, "StraightFormationBody", set_id)
                        tag_route_metadata(obj, route_id, route_name)
                        tag_export_metadata(
                            obj, "FormationBody", EXPORT_CATEGORY_SOLID
                        )
                        (straight_formation_group if straight_formation_group is not None else group).addObject(obj)
                        if Gui is not None:
                            obj.ViewObject.ShapeColor = (0.62, 0.68, 0.76)
                            obj.ViewObject.LineColor = (0.20, 0.30, 0.45)
                            obj.ViewObject.Visibility = bool(
                                formation_config_for_route["show_solid"]
                            )

                if bundle["formation_matching_hole_shape"] is not None:
                    obj = doc.addObject(
                        "Part::Feature",
                        set_name("{}{}".format(
                            STRAIGHT_FORMATION_MATCHING_HOLES_PREFIX, route_token
                        )),
                    )
                    obj.Label = "{} Formation Matching Fixing Holes [{}]".format(
                        route_name, set_id
                    )
                    obj.Shape = bundle["formation_matching_hole_shape"]
                    tag_generated_object(
                        obj, "StraightFormationMatchingHole", set_id
                    )
                    tag_route_metadata(obj, route_id, route_name)
                    tag_export_metadata(
                        obj,
                        "FormationMatchingFixingHole",
                        EXPORT_CATEGORY_HOLES,
                    )
                    (straight_formation_group if straight_formation_group is not None else group).addObject(obj)
                    if Gui is not None:
                        obj.ViewObject.LineColor = (0.15, 0.45, 0.85)
                        obj.ViewObject.LineWidth = 3.0
                        obj.ViewObject.Visibility = bool(
                            template_assembly_config["show_hole_geometry"]
                        )

                if bundle["section_active"]:
                    for section_index, section_range in enumerate(
                        bundle["section_plan"]["ranges"]
                    ):
                        local_section = section_index + 1
                        section_length = float(
                            section_range[1] - section_range[0]
                        )
                        section_label = "{} - Section {:02d}".format(
                            route_name, local_section
                        )
                        if (
                            bundle["section_track_templates"]
                            and section_index < len(bundle["template_sections"])
                        ):
                            shape = bundle["template_sections"][section_index]
                            if shape is not None:
                                obj = doc.addObject(
                                    "Part::Feature",
                                    set_name("{}{}_S{:02d}".format(
                                        STRAIGHT_TEMPLATE_SECTION_PREFIX,
                                        route_token,
                                        local_section,
                                    )),
                                )
                                obj.Label = "{} - Track Templates [{}]".format(
                                    section_label, set_id
                                )
                                obj.Shape = shape
                                tag_generated_object(
                                    obj, "StraightTrackTemplateSection", set_id
                                )
                                tag_route_metadata(obj, route_id, route_name)
                                tag_export_metadata(
                                    obj,
                                    "TrackTemplateSectionCombined",
                                    EXPORT_CATEGORY_SOLID,
                                    section_number=local_section,
                                    travel_order_number=local_section,
                                    section_length=section_length,
                                )
                                (straight_template_group if straight_template_group is not None else group).addObject(obj)
                                if Gui is not None:
                                    obj.ViewObject.ShapeColor = (0.72, 0.78, 0.86)

                        if section_index < len(bundle["template_hole_profile_shapes"]):
                            shape = bundle["template_hole_profile_shapes"][section_index]
                            if shape is not None:
                                obj = doc.addObject(
                                    "Part::Feature",
                                    set_name("{}{}_S{:02d}".format(
                                        STRAIGHT_TEMPLATE_HOLE_PREFIX,
                                        route_token,
                                        local_section,
                                    )),
                                )
                                obj.Label = "{} - Template Fixing Holes [{}]".format(
                                    section_label, set_id
                                )
                                obj.Shape = shape
                                tag_generated_object(
                                    obj, "StraightTrackTemplateFixingHole", set_id
                                )
                                tag_route_metadata(obj, route_id, route_name)
                                tag_export_metadata(
                                    obj,
                                    "TrackTemplateFixingHole",
                                    EXPORT_CATEGORY_HOLES,
                                    section_number=local_section,
                                    travel_order_number=local_section,
                                    section_length=section_length,
                                )
                                (straight_template_group if straight_template_group is not None else group).addObject(obj)
                                if Gui is not None:
                                    obj.ViewObject.LineColor = (0.10, 0.35, 0.85)
                                    obj.ViewObject.LineWidth = 3.0
                                    obj.ViewObject.Visibility = bool(
                                        template_assembly_config["show_hole_geometry"]
                                    )

                        if (
                            bundle["section_formation"]
                            and section_index < len(bundle["formation_section_faces"])
                        ):
                            output_type = formation_config_for_route["output_type"]
                            if (
                                output_type in (FORMATION_OUTLINE_ONLY, FORMATION_BOTH)
                                and section_index < len(bundle["formation_section_outlines"])
                                and bundle["formation_section_outlines"][section_index] is not None
                            ):
                                obj = doc.addObject(
                                    "Part::Feature",
                                    set_name("{}{}_S{:02d}_Profile".format(
                                        STRAIGHT_FORMATION_SECTION_PREFIX,
                                        route_token,
                                        local_section,
                                    )),
                                )
                                obj.Label = "{} - Formation Perimeter [{}]".format(
                                    section_label, set_id
                                )
                                obj.Shape = bundle["formation_section_outlines"][section_index]
                                tag_generated_object(
                                    obj, "StraightFormationSection", set_id
                                )
                                tag_route_metadata(obj, route_id, route_name)
                                tag_export_metadata(
                                    obj,
                                    "FormationSectionPerimeter",
                                    EXPORT_CATEGORY_CUTTING,
                                    section_number=local_section,
                                    travel_order_number=local_section,
                                    section_length=section_length,
                                )
                                (straight_formation_group if straight_formation_group is not None else group).addObject(obj)
                                if Gui is not None:
                                    obj.ViewObject.LineColor = (0.10, 0.55, 0.85)
                                    obj.ViewObject.LineWidth = 3.0
                            if (
                                output_type in (FORMATION_SOLID_ONLY, FORMATION_BOTH)
                                and section_index < len(bundle["formation_section_solids"])
                                and bundle["formation_section_solids"][section_index] is not None
                            ):
                                obj = doc.addObject(
                                    "Part::Feature",
                                    set_name("{}{}_S{:02d}_Body".format(
                                        STRAIGHT_FORMATION_SECTION_PREFIX,
                                        route_token,
                                        local_section,
                                    )),
                                )
                                obj.Label = "{} - Formation Board [{}]".format(
                                    section_label, set_id
                                )
                                obj.Shape = bundle["formation_section_solids"][section_index]
                                tag_generated_object(
                                    obj, "StraightFormationSection", set_id
                                )
                                tag_route_metadata(obj, route_id, route_name)
                                tag_export_metadata(
                                    obj,
                                    "FormationSectionBody",
                                    EXPORT_CATEGORY_SOLID,
                                    section_number=local_section,
                                    travel_order_number=local_section,
                                    section_length=section_length,
                                )
                                (straight_formation_group if straight_formation_group is not None else group).addObject(obj)
                                if Gui is not None:
                                    obj.ViewObject.ShapeColor = (0.62, 0.68, 0.76)

                        if section_index < len(bundle["section_number_shapes"]):
                            obj = doc.addObject(
                                "Part::Feature",
                                set_name("{}{}_S{:02d}".format(
                                    STRAIGHT_SECTION_ENGRAVING_PREFIX,
                                    route_token,
                                    local_section,
                                )),
                            )
                            obj.Label = "{} - Number Engraving [{}]".format(
                                section_label, set_id
                            )
                            obj.Shape = bundle["section_number_shapes"][section_index]
                            tag_generated_object(
                                obj, "StraightEngravingGeometry", set_id
                            )
                            tag_route_metadata(obj, route_id, route_name)
                            tag_export_metadata(
                                obj,
                                "SectionNumberEngraving",
                                EXPORT_CATEGORY_ENGRAVING,
                                section_number=local_section,
                                travel_order_number=local_section,
                                section_length=section_length,
                            )
                            (straight_track_group if straight_track_group is not None else group).addObject(obj)
                            if Gui is not None:
                                obj.ViewObject.LineColor = (0.20, 0.20, 0.20)
                                obj.ViewObject.LineWidth = 2.0

                    for joint_index, shape in enumerate(
                        bundle["template_joint_shapes"]
                    ):
                        obj = doc.addObject(
                            "Part::Feature",
                            set_name("{}{}_J{:02d}".format(
                                STRAIGHT_TEMPLATE_JOINT_PREFIX,
                                route_token,
                                joint_index + 1,
                            )),
                        )
                        obj.Label = "{} - Track Template Joint {:02d} - {} [{}]".format(
                            route_name,
                            joint_index + 1,
                            template_assembly_config["joint_type"],
                            set_id,
                        )
                        obj.Shape = shape
                        tag_generated_object(
                            obj, "StraightTrackTemplateJoint", set_id
                        )
                        tag_route_metadata(obj, route_id, route_name)
                        tag_export_metadata(
                            obj,
                            "TrackTemplateJoint",
                            EXPORT_CATEGORY_JOINTS,
                            travel_order_number=joint_index + 1,
                        )
                        (straight_template_group if straight_template_group is not None else group).addObject(obj)
                        if Gui is not None:
                            obj.ViewObject.LineColor = (0.15, 0.65, 0.25)
                            obj.ViewObject.LineWidth = 3.0

                    for joint_index, shape in enumerate(
                        bundle["registration_shapes"]
                    ):
                        obj = doc.addObject(
                            "Part::Feature",
                            set_name("{}{}_J{:02d}".format(
                                STRAIGHT_REGISTRATION_PREFIX,
                                route_token,
                                joint_index + 1,
                            )),
                        )
                        obj.Label = "{} - Formation Joint {:02d} - {} [{}]".format(
                            route_name,
                            joint_index + 1,
                            registration_config["joint_type"],
                            set_id,
                        )
                        obj.Shape = shape
                        tag_generated_object(
                            obj, "StraightRegistrationFeature", set_id
                        )
                        tag_route_metadata(obj, route_id, route_name)
                        tag_export_metadata(
                            obj,
                            "RegistrationJoint",
                            EXPORT_CATEGORY_JOINTS,
                            travel_order_number=joint_index + 1,
                        )
                        (straight_formation_group if straight_formation_group is not None else group).addObject(obj)
                        if Gui is not None:
                            obj.ViewObject.LineColor = (0.55, 0.15, 0.65)
                            obj.ViewObject.LineWidth = 3.0

                    for joint_index, shape in enumerate(
                        bundle["alignment_hole_shapes"]
                    ):
                        obj = doc.addObject(
                            "Part::Feature",
                            set_name("{}{}_J{:02d}".format(
                                STRAIGHT_ALIGNMENT_HOLE_PREFIX,
                                route_token,
                                joint_index + 1,
                            )),
                        )
                        obj.Label = "{} - Formation Alignment Holes {:02d} [{}]".format(
                            route_name, joint_index + 1, set_id
                        )
                        obj.Shape = shape
                        tag_generated_object(
                            obj, "StraightAlignmentHole", set_id
                        )
                        tag_route_metadata(obj, route_id, route_name)
                        tag_export_metadata(
                            obj,
                            "RegistrationHole",
                            EXPORT_CATEGORY_HOLES,
                            travel_order_number=joint_index + 1,
                        )
                        (straight_formation_group if straight_formation_group is not None else group).addObject(obj)
                        if Gui is not None:
                            obj.ViewObject.LineColor = (0.55, 0.15, 0.65)
                            obj.ViewObject.LineWidth = 3.0

            for result in platform_results:
                platform_number = result["platform_number"]
                platform_config = result["config"]
                platform_shapes = result["shapes"]
                edge_labels = ("Track-side edge A", "Track-side edge B")
                for edge_index, edge_shape in enumerate(
                    platform_shapes.get("edge_shapes", [])
                ):
                    object_name = set_name(
                        "{}P{:02d}_E{:02d}".format(
                            PLATFORM_EDGE_PREFIX,
                            platform_number,
                            edge_index + 1,
                        )
                    )
                    platform_edge = doc.addObject("Part::Feature", object_name)
                    platform_edge.Label = "{} - {} [{}]".format(
                        platform_config["name"],
                        edge_labels[edge_index],
                        set_id,
                    )
                    platform_edge.Shape = edge_shape
                    tag_generated_object(platform_edge, "PlatformEdge", set_id)
                    tag_export_metadata(
                        platform_edge,
                        "PlatformEdge",
                        EXPORT_CATEGORY_ENGRAVING,
                        platform_number=platform_number,
                        platform_name=platform_config["name"],
                        feature_number=edge_index + 1,
                    )
                    group.addObject(platform_edge)
                    if Gui is not None:
                        platform_edge.ViewObject.LineColor = (0.95, 0.65, 0.10)
                        platform_edge.ViewObject.LineWidth = 3.0
                        platform_edge.ViewObject.Visibility = bool(
                            platform_config["show_edges"]
                        )

                body_shape = platform_shapes.get("body_shape")
                if result["create_unsplit"] and body_shape is not None:
                    platform_body_object = doc.addObject(
                        "Part::Feature",
                        set_name(
                            "{}{:02d}".format(
                                PLATFORM_BODY_NAME, platform_number
                            )
                        ),
                    )
                    platform_body_object.Label = "{} [{}]".format(
                        platform_config["name"], set_id
                    )
                    platform_body_object.Shape = body_shape
                    tag_generated_object(
                        platform_body_object, "PlatformBody", set_id
                    )
                    tag_export_metadata(
                        platform_body_object,
                        "PlatformBody",
                        (
                            EXPORT_CATEGORY_SOLID
                            if platform_shapes.get("body_is_solid", False)
                            else EXPORT_CATEGORY_CUTTING
                        ),
                        platform_number=platform_number,
                        platform_name=platform_config["name"],
                    )
                    group.addObject(platform_body_object)
                    if Gui is not None:
                        platform_body_object.ViewObject.ShapeColor = (
                            0.62, 0.58, 0.48
                        )
                        platform_body_object.ViewObject.LineColor = (
                            0.30, 0.28, 0.24
                        )
                        platform_body_object.ViewObject.Visibility = bool(
                            platform_config["show_body"]
                        )

            if formation_geometry is not None and create_unsplit_formation:
                output_type = formation_config["output_type"]
                if output_type in (FORMATION_OUTLINE_ONLY, FORMATION_BOTH):
                    outline_object = doc.addObject("Part::Feature", set_name(FORMATION_OUTLINE_NAME))
                    outline_object.Label = "Formation Board Perimeter Profile [{}]".format(set_id)
                    outline_object.Shape = formation_geometry["outline"]
                    tag_generated_object(outline_object, "FormationOutline", set_id)
                    tag_export_metadata(
                        outline_object,
                        "FormationPerimeter",
                        EXPORT_CATEGORY_CUTTING,
                    )
                    group.addObject(outline_object)
                    if Gui is not None:
                        outline_object.ViewObject.LineColor = (0.10, 0.55, 0.85)
                        outline_object.ViewObject.LineWidth = 3.0
                        outline_object.ViewObject.Visibility = bool(formation_config["show_outline"])
                if output_type in (FORMATION_SOLID_ONLY, FORMATION_BOTH):
                    formation_body_object = doc.addObject("Part::Feature", set_name(FORMATION_BODY_NAME))
                    formation_body_object.Label = "Formation Board {:.3f} mm [{}]".format(
                        formation_config["board_thickness"], set_id
                    )
                    formation_body_object.Shape = formation_geometry["body"]
                    tag_generated_object(formation_body_object, "FormationBody", set_id)
                    tag_export_metadata(
                        formation_body_object,
                        "FormationBody",
                        EXPORT_CATEGORY_SOLID,
                    )
                    group.addObject(formation_body_object)
                    if Gui is not None:
                        formation_body_object.ViewObject.ShapeColor = (0.72, 0.58, 0.38)
                        formation_body_object.ViewObject.LineColor = (0.30, 0.20, 0.10)
                        formation_body_object.ViewObject.Visibility = bool(formation_config["show_solid"])

            if track_engraving_shape is not None:
                engraving = doc.addObject("Part::Feature", set_name(TRACK_ENGRAVING_NAME))
                engraving.Label = "Track Centreline Engraving [{}]".format(set_id)
                engraving.Shape = track_engraving_shape
                tag_generated_object(engraving, "EngravingGeometry", set_id)
                tag_export_metadata(
                    engraving,
                    "TrackCentrelineEngraving",
                    EXPORT_CATEGORY_ENGRAVING,
                )
                group.addObject(engraving)
                if Gui is not None:
                    engraving.ViewObject.LineColor = (0.80, 0.10, 0.10)
                    engraving.ViewObject.LineWidth = 2.0

            if platform_engraving_shape is not None:
                engraving = doc.addObject("Part::Feature", set_name(PLATFORM_ENGRAVING_NAME))
                engraving.Label = "Platform Edge Engraving [{}]".format(set_id)
                engraving.Shape = platform_engraving_shape
                tag_generated_object(engraving, "EngravingGeometry", set_id)
                tag_export_metadata(
                    engraving,
                    "PlatformEdgeEngraving",
                    EXPORT_CATEGORY_ENGRAVING,
                )
                group.addObject(engraving)
                if Gui is not None:
                    engraving.ViewObject.LineColor = (0.95, 0.55, 0.05)
                    engraving.ViewObject.LineWidth = 2.0

            if formation_matching_hole_shape is not None:
                obj = doc.addObject("Part::Feature", set_name(FORMATION_MATCHING_HOLES_NAME))
                obj.Label = "Formation Board Matching Fixing Holes [{}]".format(set_id)
                obj.Shape = formation_matching_hole_shape
                tag_generated_object(obj, "FormationMatchingHole", set_id)
                tag_export_metadata(
                    obj,
                    "FormationMatchingFixingHole",
                    EXPORT_CATEGORY_HOLES,
                )
                group.addObject(obj)
                if Gui is not None:
                    obj.ViewObject.LineColor = (0.15, 0.45, 0.85)
                    obj.ViewObject.LineWidth = 3.0
                    obj.ViewObject.Visibility = bool(template_assembly_config["show_hole_geometry"])

            if section_active:
                for index, section_range in enumerate(section_plan["ranges"]):
                    section_number = index + 1
                    section_length = float(section_range[1] - section_range[0])
                    section_label = "Section {:02d}".format(section_number)

                    if section_config["section_track_templates"] and index < len(template_sections):
                        shape = template_sections[index]
                        if shape is not None:
                            obj = doc.addObject("Part::Feature", set_name("{}{:02d}".format(TEMPLATE_SECTION_PREFIX, section_number)))
                            obj.Label = "{} - Track Template [{}]".format(section_label, set_id)
                            obj.Shape = shape
                            tag_generated_object(obj, "TrackTemplateSection", set_id)
                            tag_export_metadata(
                                obj,
                                "TrackTemplateSectionCombined",
                                EXPORT_CATEGORY_SOLID,
                                section_number=section_number,
                                travel_order_number=section_number,
                                section_length=section_length,
                            )
                            group.addObject(obj)
                            if Gui is not None:
                                obj.ViewObject.ShapeColor = (0.82, 0.82, 0.82)

                    if index < len(template_hole_profile_shapes):
                        hole_shape = template_hole_profile_shapes[index]
                        if hole_shape is not None:
                            obj = doc.addObject("Part::Feature", set_name("{}{:02d}".format(TRACK_TEMPLATE_HOLE_PREFIX, section_number)))
                            obj.Label = "{} - Track Template Fixing Holes [{}]".format(section_label, set_id)
                            obj.Shape = hole_shape
                            tag_generated_object(obj, "TrackTemplateFixingHole", set_id)
                            tag_export_metadata(
                                obj,
                                "TrackTemplateFixingHole",
                                EXPORT_CATEGORY_HOLES,
                                section_number=section_number,
                                travel_order_number=section_number,
                                section_length=section_length,
                            )
                            group.addObject(obj)
                            if Gui is not None:
                                obj.ViewObject.LineColor = (0.10, 0.35, 0.85)
                                obj.ViewObject.LineWidth = 3.0
                                obj.ViewObject.Visibility = bool(template_assembly_config["show_hole_geometry"])

                    if section_config["section_platform"]:
                        for result in platform_results:
                            sections = result.get("sections", [])
                            if index >= len(sections):
                                continue
                            shape = sections[index]
                            if shape is None:
                                continue
                            platform_number = result["platform_number"]
                            platform_name = result["config"]["name"]
                            obj = doc.addObject(
                                "Part::Feature",
                                set_name(
                                    "{}P{:02d}_S{:02d}".format(
                                        PLATFORM_SECTION_PREFIX,
                                        platform_number,
                                        section_number,
                                    )
                                ),
                            )
                            obj.Label = "{} - {} [{}]".format(
                                section_label, platform_name, set_id
                            )
                            obj.Shape = shape
                            tag_generated_object(
                                obj, "PlatformSection", set_id
                            )
                            tag_export_metadata(
                                obj,
                                "PlatformSection",
                                (
                                    EXPORT_CATEGORY_SOLID
                                    if shape_has_solid_geometry(shape)
                                    else EXPORT_CATEGORY_CUTTING
                                ),
                                platform_number=platform_number,
                                platform_name=platform_name,
                                section_number=section_number,
                                travel_order_number=section_number,
                                section_length=section_length,
                            )
                            group.addObject(obj)
                            if Gui is not None:
                                obj.ViewObject.ShapeColor = (
                                    0.62, 0.58, 0.48
                                )

                    if section_config["section_formation"] and index < len(formation_section_faces):
                        output_type = formation_config["output_type"]
                        if (
                            output_type in (FORMATION_OUTLINE_ONLY, FORMATION_BOTH)
                            and index < len(formation_section_outlines)
                            and formation_section_outlines[index] is not None
                        ):
                            obj = doc.addObject("Part::Feature", set_name("{}{:02d}_Profile".format(FORMATION_SECTION_PREFIX, section_number)))
                            obj.Label = "{} - Formation Perimeter [{}]".format(section_label, set_id)
                            obj.Shape = formation_section_outlines[index]
                            tag_generated_object(obj, "FormationSection", set_id)
                            tag_export_metadata(
                                obj,
                                "FormationSectionPerimeter",
                                EXPORT_CATEGORY_CUTTING,
                                section_number=section_number,
                                travel_order_number=section_number,
                                section_length=section_length,
                            )
                            group.addObject(obj)
                            if Gui is not None:
                                obj.ViewObject.LineColor = (0.10, 0.55, 0.85)
                                obj.ViewObject.LineWidth = 3.0
                        if (
                            output_type in (FORMATION_SOLID_ONLY, FORMATION_BOTH)
                            and index < len(formation_section_solids)
                            and formation_section_solids[index] is not None
                        ):
                            obj = doc.addObject("Part::Feature", set_name("{}{:02d}_Body".format(FORMATION_SECTION_PREFIX, section_number)))
                            obj.Label = "{} - Formation Board [{}]".format(section_label, set_id)
                            obj.Shape = formation_section_solids[index]
                            tag_generated_object(obj, "FormationSection", set_id)
                            tag_export_metadata(
                                obj,
                                "FormationSectionBody",
                                EXPORT_CATEGORY_SOLID,
                                section_number=section_number,
                                travel_order_number=section_number,
                                section_length=section_length,
                            )
                            group.addObject(obj)
                            if Gui is not None:
                                obj.ViewObject.ShapeColor = (0.72, 0.58, 0.38)

                    if index < len(section_number_shapes):
                        obj = doc.addObject("Part::Feature", set_name("{}{:02d}".format(SECTION_ENGRAVING_PREFIX, section_number)))
                        obj.Label = "{} - Number Engraving [{}]".format(section_label, set_id)
                        obj.Shape = section_number_shapes[index]
                        tag_generated_object(obj, "EngravingGeometry", set_id)
                        tag_export_metadata(
                            obj,
                            "SectionNumberEngraving",
                            EXPORT_CATEGORY_ENGRAVING,
                            section_number=section_number,
                            travel_order_number=section_number,
                            section_length=section_length,
                        )
                        group.addObject(obj)
                        if Gui is not None:
                            obj.ViewObject.LineColor = (0.20, 0.20, 0.20)
                            obj.ViewObject.LineWidth = 2.0

                for index, shape in enumerate(template_joint_shapes):
                    obj = doc.addObject("Part::Feature", set_name("{}{:02d}".format(TRACK_TEMPLATE_JOINT_PREFIX, index + 1)))
                    obj.Label = "Track Template Joint {:02d} - {} [{}]".format(
                        index + 1,
                        template_assembly_config["joint_type"],
                        set_id,
                    )
                    obj.Shape = shape
                    tag_generated_object(obj, "TrackTemplateJoint", set_id)
                    tag_export_metadata(
                        obj,
                        "TrackTemplateJoint",
                        EXPORT_CATEGORY_JOINTS,
                        travel_order_number=index + 1,
                    )
                    group.addObject(obj)
                    if Gui is not None:
                        obj.ViewObject.LineColor = (0.15, 0.65, 0.25)
                        obj.ViewObject.LineWidth = 3.0

                for index, shape in enumerate(registration_shapes):
                    obj = doc.addObject("Part::Feature", set_name("{}{:02d}".format(REGISTRATION_PREFIX, index + 1)))
                    obj.Label = "Section Joint {:02d} - {} Profile [{}]".format(
                        index + 1,
                        registration_config["joint_type"],
                        set_id,
                    )
                    obj.Shape = shape
                    tag_generated_object(obj, "RegistrationFeature", set_id)
                    tag_export_metadata(
                        obj,
                        "RegistrationJoint",
                        EXPORT_CATEGORY_JOINTS,
                        travel_order_number=index + 1,
                    )
                    group.addObject(obj)
                    if Gui is not None:
                        obj.ViewObject.LineColor = (0.55, 0.15, 0.65)
                        obj.ViewObject.LineWidth = 3.0

                for index, shape in enumerate(alignment_hole_shapes):
                    obj = doc.addObject("Part::Feature", set_name("{}{:02d}".format(ALIGNMENT_HOLE_PREFIX, index + 1)))
                    obj.Label = "Section Joint {:02d} - Internal Alignment Holes [{}]".format(index + 1, set_id)
                    obj.Shape = shape
                    tag_generated_object(obj, "AlignmentHole", set_id)
                    tag_export_metadata(
                        obj,
                        "RegistrationHole",
                        EXPORT_CATEGORY_HOLES,
                        travel_order_number=index + 1,
                    )
                    group.addObject(obj)
                    if Gui is not None:
                        obj.ViewObject.LineColor = (0.55, 0.15, 0.65)
                        obj.ViewObject.LineWidth = 3.0

            straight_assembly_routes = [
                bundle for bundle in straight_production_results
                if bundle["template_assembly_active"]
            ]
            if not template_assembly_active and not straight_assembly_routes:
                template_assembly_summary = "Track-template assembly features disabled"
            else:
                hole_summary = "fixing holes disabled"
                if template_assembly_config["fixing_holes_enabled"]:
                    total_holes = len(template_hole_faces)
                    hole_summary = (
                        "{} centreline holes; {} per strip per section; effective end clearance "
                        "{:.3f} mm{}"
                    ).format(
                        total_holes,
                        template_assembly_config["holes_per_section"],
                        effective_template_hole_clearance,
                        "; matching formation holes"
                        if template_assembly_config["matching_formation_holes"]
                        else "",
                    )
                straight_hole_total = sum(
                    len(bundle["template_hole_faces"])
                    for bundle in straight_assembly_routes
                )
                straight_route_text = (
                    "; straight routes {} with {} fixing holes".format(
                        len(straight_assembly_routes), straight_hole_total
                    )
                    if straight_assembly_routes
                    else ""
                )
                template_assembly_summary = "{}; {}{}".format(
                    template_assembly_config["joint_type"],
                    hole_summary,
                    straight_route_text,
                )

            bind_export_records_to_current_set(
                doc,
                set_id,
                production_schedule_records,
            )
            assign_production_record_ids(
                production_schedule_records, set_id
            )
            capture_assembly_label_base_sources(production_schedule_records)
            materialise_assembly_label_base_sources(
                doc, group, set_id, production_schedule_records
            )
            materialise_production_source_objects(
                doc, group, set_id, production_schedule_records
            )
            capture_assembly_label_base_sources(production_schedule_records)
            tag_production_record_bindings(
                doc, set_id, production_schedule_records
            )
            production_record_index = build_production_record_index(
                production_schedule_records, set_id
            )

            store_parameters(
                settings_object,
                transition,
                radius,
                angle,
                main_width,
                track_configs,
                straight_configs,
                straight_route_results,
                turn_sign,
                main_alignment,
                track_alignments,
                platform_configs,
                platform_results,
                formation_config,
                formation_geometry,
                section_config,
                section_plan,
                registration_config,
                template_assembly_config,
                production_export_config,
                template_assembly_summary,
                output_mode,
                production_record_index=production_record_index,
            )
            store_assembly_label_config(settings_object, assembly_label_config)
            if template_object is not None:
                store_parameters(
                    template_object,
                    transition,
                    radius,
                    angle,
                    main_width,
                    track_configs,
                    straight_configs,
                    straight_route_results,
                    turn_sign,
                    main_alignment,
                    track_alignments,
                    platform_configs,
                    platform_results,
                    formation_config,
                    formation_geometry,
                    section_config,
                    section_plan,
                    registration_config,
                    template_assembly_config,
                    production_export_config,
                    template_assembly_summary,
                    output_mode,
                )
                store_assembly_label_config(template_object, assembly_label_config)

            _document_recompute(doc)
            doc.commitTransaction()
            transaction_open = False
        except Exception:
            if transaction_open:
                try:
                    doc.abortTransaction()
                except Exception:
                    pass
            raise

        production_schedule_result = "Not created"
        production_export_summary = None
        if production_export_config.get("enabled", False):
            try:
                bind_export_records_to_current_set(
                    doc,
                    set_id,
                    production_export_records,
                )
                production_export_summary = run_production_export(
                    doc,
                    production_export_plan,
                    production_export_config,
                    set_id,
                    platform_configs[0] if platform_configs else default_platform_config(),
                    formation_config,
                    registration_config,
                    template_assembly_config,
                )
            except Exception as export_error:
                failure_message = "Production export system: {}".format(export_error)
                production_export_summary = {
                    "output_directory": production_export_config.get("output_directory", ""),
                    "successful_files": 0,
                    "failed_files": 1,
                    "skipped_objects": 0,
                    "formats": [],
                    "manifest_path": "",
                    "manifest_requested": bool(production_export_config.get("create_manifest", True)),
                    "failures": [failure_message],
                    "failure_details": [failure_message],
                    "skipped_outputs": [],
                    "skipped_details": [],
                }
            show_production_export_summary(production_export_summary)
            if production_export_config.get("open_output_directory", False):
                open_export_directory(
                    production_export_summary.get("output_directory", "")
                )

        try:
            production_schedule_rows = build_production_schedule_rows(
                production_record_index,
                production_export_config,
                set_id,
            )
            create_or_replace_production_schedule(
                doc, set_id, production_schedule_rows
            )
            production_schedule_result = "{} records".format(
                len(production_schedule_rows)
            )
            App.Console.PrintMessage(
                "Production schedule [{}]: {} records.\n".format(
                    set_id, len(production_schedule_rows)
                )
            )
        except Exception as schedule_error:
            production_schedule_result = "Failed: {}".format(schedule_error)
            App.Console.PrintWarning(
                "Production schedule was not created: {}\n".format(
                    schedule_error
                )
            )

        material_report_result = "Not created"
        try:
            material_report_config = read_material_report_config(settings_object)
            material_report_rows, material_report_diagnostics = build_material_report_rows(
                doc,
                production_record_index,
                settings_object,
                material_report_config,
                set_id,
            )
            create_or_replace_material_report(
                doc,
                set_id,
                material_report_rows,
                material_report_config,
                material_report_diagnostics,
            )
            material_report_result = "{} rows; {} physical parts".format(
                len(material_report_rows),
                material_report_diagnostics.get("physical_part_count", 0),
            )
            App.Console.PrintMessage(
                "Material and length report [{}]: {} rows.\n".format(
                    set_id, len(material_report_rows)
                )
            )
        except Exception as material_error:
            material_report_result = "Failed: {}".format(material_error)
            App.Console.PrintWarning(
                "Material and length report was not created: {}\n".format(
                    material_error
                )
            )

        _document_recompute(doc)
        if Gui is not None:
            Gui.activeDocument().activeView().viewTop()
            Gui.activeDocument().activeView().fitAll()

        created_strips = sum(1 for item in all_alignments if item["create_template"])
        created_straight_strips = sum(
            len(bundle["template_sources"])
            for bundle in straight_production_results
        )
        straight_result_lines = [
            "{}: {}; {:.3f} mm; {} track(s); {} section(s); formation {}".format(
                bundle["route_name"],
                bundle["route"]["connection_mode"],
                bundle["route"]["length"],
                len(bundle["alignments"]),
                len(bundle["section_plan"]["ranges"])
                if bundle["section_active"] else 1,
                "yes" if bundle["formation_geometry"] is not None else "no",
            )
            for bundle in straight_production_results
        ]
        result_lines = []
        for alignment in track_alignments:
            result_lines.append(
                "{}: {}, constant R {:.3f} mm, minimum R {:.3f} mm, "
                "entry/exit transitions {:.3f}/{:.3f} mm".format(
                    alignment["name"],
                    alignment["alignment_mode"],
                    alignment["radius"],
                    alignment["minimum_radius"],
                    alignment["entry_transition"],
                    alignment["exit_transition"],
                )
            )

        straight_formation_count = sum(
            1
            for bundle in straight_production_results
            if bundle["formation_geometry"] is not None
        )
        formation_result = "Disabled"
        if formation_geometry is not None:
            formation_result = "{}; {:.3f} mm thick; {:.3f} mm2 curve plan area".format(
                formation_config["output_type"],
                formation_config["board_thickness"],
                formation_geometry["area"],
            )
        if straight_formation_count:
            formation_result += "; {} straight extension board(s)".format(
                straight_formation_count
            )

        straight_sectioned_routes = [
            bundle
            for bundle in straight_production_results
            if bundle["section_active"]
        ]
        section_result = "Disabled"
        if section_active or straight_sectioned_routes:
            parts = []
            if section_active:
                if section_config["section_formation"]:
                    registration_result = registration_config["joint_type"]
                else:
                    registration_result = "formation board retained unsplit"
                parts.append(
                    "curve {} matched pieces; {}".format(
                        len(section_plan["ranges"]), registration_result
                    )
                )
            for bundle in straight_sectioned_routes:
                parts.append(
                    "{} {} route-local pieces".format(
                        bundle["route_name"],
                        len(bundle["section_plan"]["ranges"]),
                    )
                )
            section_result = "; ".join(parts)

        production_result = "Disabled"
        if production_export_summary is not None:
            production_result = (
                "{} successful files; {} failed; {} skipped; {}"
            ).format(
                production_export_summary.get("successful_files", 0),
                production_export_summary.get("failed_files", 0),
                production_export_summary.get("skipped_objects", 0),
                production_export_summary.get("output_directory", ""),
            )

        production_preflight_result = "Not run because production export was disabled"
        if production_preflight_summary is not None:
            production_preflight_result = (
                "{} error(s); {} warning(s); {} information item(s)"
            ).format(
                production_preflight_summary.get(
                    PRODUCTION_PREFLIGHT_SEVERITY_ERROR, 0
                ),
                production_preflight_summary.get(
                    PRODUCTION_PREFLIGHT_SEVERITY_WARNING, 0
                ),
                production_preflight_summary.get(
                    PRODUCTION_PREFLIGHT_SEVERITY_INFORMATION, 0
                ),
            )

        assembly_label_result = "Disabled"
        if assembly_label_config.get("enabled", False):
            placed_labels = sum(
                1 for item in assembly_label_diagnostics
                if item.get("status") == "Placed"
            )
            skipped_labels = sum(
                1 for item in assembly_label_diagnostics
                if item.get("status") == "Skipped"
            )
            assembly_label_result = "{} placed; {} safely skipped".format(
                placed_labels, skipped_labels
            )

        platform_result = "Disabled"
        if platform_results:
            platform_descriptions = [
                "{:02d} {} ({})".format(
                    result["platform_number"],
                    result["config"]["name"],
                    result["config"]["body_output"],
                )
                for result in platform_results
            ]
            platform_result = "{} enabled: {}".format(
                len(platform_results),
                "; ".join(platform_descriptions),
            )

        QtWidgets.QMessageBox.information(
            None,
            versioned_dialog_title("Railway production outputs created"),
            (
                "Curve and straight-track outputs created successfully with {}.\n\n"
                "Output behaviour: {}\n"
                "Template set: {}\n"
                "Previous generated objects removed: {}\n"
                "Direction: {}\n"
                "Main constant radius: {:.3f} mm\n"
                "Additional tracks: {}\n"
                "Curve printable strips: {}\n"
                "Straight routes: {}\n"
                "Straight printable strips: {}\n"
                "Platforms: {}\n"
                "Formation-board swept envelope: {}\n"
                "Universal sectioning: {}\n"
                "Track-template assembly: {}\n"
                "Assembly labels: {}\n"
                "Production preflight: {}\n"
                "Production export: {}\n"
                "Production schedule: {}\n"
                "Material and length report: {}\n"
                "Main circular arc angle: {:.3f} deg\n"
                "Main minimum radius: {:.3f} mm\n\n"
                "Curve tracks:\n{}\n\n"
                "Straight routes:\n{}\n\n"
                "Version 9.13 curve, easement and curved-platform geometry remains unchanged. "
                "Version 10.2A4 retains Version 10.0B3 route-local sectioning, template joints, fixing holes, "
                "straight formation-board extensions and established production exporters unchanged. It retains the stable "
                "production schedule, material report, read-only production preflight and selected-item export. "
                "Version 10.2A5 adds optional compact assembly labels as separate validated production geometry, with shallow 3D engraving applied only to hidden export copies. Version 10.2A6 adds readable atomic JSON configuration export, deterministic migration and all-or-nothing validated import into the open dialogue without automatic regeneration. Version 10.2A7 adds the explicit named-preset library. Version 10.2A8A1 adds a separate source-driven REA C10 turnout manager which maps turnout geometry through any generated host alignment without altering the established route engines. Version 10.2A8A2 adds exact chainage nudging and all-or-nothing editing of existing turnout handing, orientation and placement while retaining stable turnout identities and source-object names. Version 10.2A8A3 replaces the simplified turnout rail references with source-driven stock, switch, closure, knuckle, wing, vee and check-rail construction geometry while preserving the established host-curvature mapping and editor. Version 10.2A8A4 adds source-driven REA turnout timbering. Version 10.2A8A5 adds reversible derived host-template integration and independent reference-copy extraction without rewriting established route geometry. Version 10.2A8A6A adds a managed crossover geometry stage using two existing natural C10 turnout builds and an exact tangent-continuous biarc connector; unresolved independent turnout timbers are visibly marked and host integration remains blocked pending A8A6B. Version 10.2A8A6A1 unifies turnout and crossover controls in one tabbed manager and adds direct picked-position crossover placement with automatic nearest-host resolution and exact chainage nudging. Version 10.2A8A6A2 repairs the unified manager by embedding crossover controls as a normal QWidget rather than a nested QDialog, avoiding FreeCAD/PySide native ownership crashes. Version 10.2A8A6A3 repairs crossover creation by deriving turnout module lengths from the built C10 configurations, reuses validated preview solutions, removes repeated host-alignment scans, and omits non-production timber-number wires from the unresolved preview. Version 10.2A8A6A4 adds transactional extension of an existing standalone turnout into a managed crossover, preserving its host, exact toe chainage, orientation, handing, gauge, flangeway and internal turnout identity while selecting only the second host. Version 10.2A8A6A5 makes that conversion hands-off: it automatically ranks neighbouring managed hosts from the selected turnout, reuses the established crossover solver to reject unsuitable tracks, and replaces the turnout only after the nearest valid crossover has been solved completely. Version 10.2A8A6A6 adds the matching transactional reverse operation: a managed crossover can restore its original source turnout automatically, or retain either constituent turnout when the crossover was created independently. New conversions preserve a complete source-configuration snapshot for exact future restoration. Version 10.2A8A6B1 adds cached read-only timber conflict and protected-support analysis. Version 10.2A8A6B2A2 completes the shared-timber envelope through the crossover road, using each host Main template width as the nominal plain sleeper length. Version 10.2A8A6B3 adds controlled interlacing and minimum longitudinal timber movement for remaining eligible inherited A/B positions. Version 10.2A8A6B4 combines the validated B2A2 and B3 engines into one automatic final timbering preview, while retaining unsafe cases explicitly for engineering review. Version 10.2A8A6C adds transactional crossover editing and reversible host-template integration of the final resolved timber arrangement. Version 10.2A8A6C1 repairs crossover XY engraving hydration and format-aware export preflight. Version 10.2A8A6C2 repairs selected-export row selection, adds scrolling to the unified manager and projects turnout engraving copies safely to XY. Version 10.2A8A7B7 adds a shared numbered guided workflow for both turnout and crossover operations, with original specialist controls available on demand and no railway-calculation changes. "
                "Straight platforms remain staged "
                "for a later revision."
            ).format(
                MACRO_VERSION,
                output_mode,
                set_id,
                len(removed_outputs),
                "left" if turn_sign > 0.0 else "right",
                radius,
                len(track_alignments),
                created_strips,
                len(straight_route_results),
                created_straight_strips,
                platform_result,
                formation_result,
                section_result,
                template_assembly_summary,
                assembly_label_result,
                production_preflight_result,
                production_result,
                production_schedule_result,
                material_report_result,
                math.degrees(main_alignment["circular_angle"]),
                radius,
                "\n".join(result_lines) if result_lines else "No added curve tracks",
                "\n".join(straight_result_lines) if straight_result_lines else "Disabled",
            ),
        )

    except Exception as error:
        show_error(str(error))
        App.Console.PrintError("Railway template error: {}\n".format(error))



# ---------------------------------------------------------------------------
# A8A7B ordinary and turnout chair assignment.
#
# This controlled extension works from the A8A7A1 stable logical positions.
# It confirms ordinary S1/S1J and REA C-switch P/PLR assignments, resolves
# deterministic model key directions, and records model-scale timber support
# recommendations.  It remains read-only regarding production geometry.
# Crossing, check-rail, wing-rail and final bridge-chair selection remain
# staged for A8A7C.  Detailed solids remain staged for A8A7D/A8A7E.
# ---------------------------------------------------------------------------
_A8A7A1_VALIDATE_CHAIR_POSITIONS = validate_chair_positions
CHAIR_ANALYSIS_SCHEMA_VERSION = 3
CHAIR_STATUS_ASSIGNMENTS_VALIDATED = "Ordinary and turnout assignments validated"
CHAIR_ASSIGNMENT_CONFIRMED = "confirmed ordinary or turnout assignment"
CHAIR_ASSIGNMENT_OMITTED = "confirmed shared switch support"
CHAIR_ASSIGNMENT_DEFERRED_SPECIAL = "deferred to special-chair assignment"
CHAIR_ASSIGNMENT_UNRESOLVED = "ordinary or turnout assignment unresolved"

CHAIR_CODE_CATALOG = {
    1: {"label": "S1", "family": CHAIR_FAMILY_ORDINARY, "source": "REA ordinary chair"},
    2: {"label": "P", "family": CHAIR_FAMILY_SLIDE, "source": "REA slide chair"},
    5: {"label": "L1", "family": CHAIR_FAMILY_BRIDGE, "source": "REA bridge chair"},
    7: {"label": "S1J", "family": CHAIR_FAMILY_JOINT, "source": "REA joint chair"},
    11: {"label": "1P/2P", "family": CHAIR_FAMILY_SWITCH, "source": "REA block-slide chair"},
    12: {"label": "3P-11P", "family": CHAIR_FAMILY_SWITCH_HEEL, "source": "REA block-heel chair"},
    14: {"label": "CCW", "family": CHAIR_FAMILY_CHECK, "source": "REA check flare-in chair"},
    15: {"label": "CC", "family": CHAIR_FAMILY_CHECK, "source": "REA ordinary check chair"},
    16: {"label": "CCE", "family": CHAIR_FAMILY_CHECK, "source": "REA check flare-out chair"},
    21: {"label": "ZY", "family": CHAIR_FAMILY_CROSSING, "source": "REA crossing chair"},
    22: {"label": "XN", "family": CHAIR_FAMILY_KNUCKLE, "source": "REA knuckle chair"},
    23: {"label": "XA", "family": CHAIR_FAMILY_CROSSING, "source": "REA crossing-gap chair"},
    24: {"label": "AA", "family": CHAIR_FAMILY_NOSE, "source": "REA nose chair"},
    25: {"label": "AB", "family": CHAIR_FAMILY_SPLICE, "source": "REA splice chair"},
    26: {"label": "BB/BC", "family": CHAIR_FAMILY_VEE, "source": "REA vee chair"},
    27: {"label": "CD", "family": CHAIR_FAMILY_VEE, "source": "REA vee chair"},
    28: {"label": "EF", "family": CHAIR_FAMILY_VEE, "source": "REA exit vee chair"},
}


def default_chair_analysis_settings():
    """Return A8A7B analytical and model-support settings."""
    return {
        "schema_version": CHAIR_ANALYSIS_SCHEMA_VERSION,
        "position_tolerance": 0.20,
        "footprint_clearance": 0.15,
        "timber_end_clearance": 0.50,
        "maximum_advisory_skew_degrees": 5.0,
        "maximum_unsupported_span": 15.0,
        "markers_visible": True,
        "protected_markers_visible": False,
        "footprints_visible": False,
        "cache_enabled": True,
        "model_support_recommendations_enabled": True,
        "model_support_edge_margin": 0.15,
        "preferred_maximum_model_support_extension_per_side": 2.0,
        # Reserved for later solid stages. They are stored but not applied here.
        "future_chair_embed_depth": 0.20,
        "future_boolean_overlap_allowance": 0.05,
        "future_boolean_fuzzy_tolerance": 0.01,
    }


def normalise_chair_analysis_settings(settings=None):
    defaults = default_chair_analysis_settings()
    supplied = settings if isinstance(settings, dict) else {}
    result = dict(defaults)
    numeric_keys = (
        "position_tolerance", "footprint_clearance", "timber_end_clearance",
        "maximum_advisory_skew_degrees", "maximum_unsupported_span",
        "model_support_edge_margin", "preferred_maximum_model_support_extension_per_side",
        "future_chair_embed_depth", "future_boolean_overlap_allowance",
        "future_boolean_fuzzy_tolerance",
    )
    for key in numeric_keys:
        if key in supplied:
            try:
                result[key] = float(supplied[key])
            except Exception:
                raise ValueError("Chair setting {} must be numeric.".format(key.replace("_", " ")))
    limits = {
        "position_tolerance": (0.0, 5.0),
        "footprint_clearance": (0.0, 5.0),
        "timber_end_clearance": (0.0, 10.0),
        "maximum_advisory_skew_degrees": (0.0, 30.0),
        "maximum_unsupported_span": (1.0, 100.0),
        "model_support_edge_margin": (0.0, 3.0),
        "preferred_maximum_model_support_extension_per_side": (0.0, 10.0),
        "future_chair_embed_depth": (0.0, 5.0),
        "future_boolean_overlap_allowance": (0.0, 2.0),
        "future_boolean_fuzzy_tolerance": (0.0, 1.0),
    }
    for key, bounds in limits.items():
        value = float(result[key])
        if not math.isfinite(value) or value < bounds[0] or value > bounds[1]:
            raise ValueError(
                "Chair setting {} must be between {:.3f} and {:.3f}.".format(
                    key.replace("_", " "), bounds[0], bounds[1]
                )
            )
    for key in (
        "markers_visible", "protected_markers_visible", "footprints_visible",
        "cache_enabled", "model_support_recommendations_enabled",
    ):
        result[key] = bool(supplied.get(key, defaults[key]))
    result["schema_version"] = CHAIR_ANALYSIS_SCHEMA_VERSION
    return result


def _chair_matched_support_requirements(timber, rail, support=None):
    requirements = [dict(item) for item in (timber.get("support_requirements") or []) if isinstance(item, dict)]
    return [item for item in requirements if _chair_requirement_route_matches(item, rail, support)]


def _chair_parse_prototype_identifier(value):
    text = str(value or "").strip()
    matches = re.findall(r"(?:^|:)(J\d+|S\d+|T\d+|X\d+-[A-Z]+|R\d+)$", text, re.IGNORECASE)
    return matches[-1].upper() if matches else ""


def _chair_effective_prototype_identifier(timber, rail, support=None):
    direct = str(timber.get("identifier") or timber.get("prototype_reference") or "").strip().upper()
    if re.match(r"^(J\d+|S\d+|T\d+|X\d+-[A-Z]+|R\d+)$", direct):
        return direct
    candidates = []
    for requirement in _chair_matched_support_requirements(timber, rail, support):
        parsed = _chair_parse_prototype_identifier(
            requirement.get("source_timber_identity") or requirement.get("route_identity") or ""
        )
        if parsed:
            candidates.append(parsed)
    if candidates:
        # Route/zone matching should normally return one source timber.  A
        # deterministic first result keeps shared-edge contact stable.
        return sorted(set(candidates))[0]
    parsed = _chair_parse_prototype_identifier(timber.get("stable_identity") or "")
    return parsed or direct


def _chair_code_values(code):
    data = dict(CHAIR_CODE_CATALOG.get(int(code or 0), {}))
    return int(code or 0), str(data.get("label") or "")


def _chair_crossing_deferred_assignment(identifier, timber, rail):
    role = str(rail.get("rail_role") or "").lower()
    suffix = str((timber.get("source_configuration") or {}).get("crossing_suffix") or "").upper()
    if not suffix and "-" in identifier:
        suffix = identifier.rsplit("-", 1)[-1].upper()
    if role == "check rail":
        return CHAIR_FAMILY_CHECK, "REA check-chair subtype awaiting detailed special-chair assignment", 15
    if role == "wing rail knuckle":
        return CHAIR_FAMILY_KNUCKLE, "REA XN knuckle-chair assignment awaiting detailed special-chair assignment", 22
    if role == "wing rail":
        code = 21 if suffix == "Z" else (22 if suffix == "Y" else (23 if suffix == "X" else 25))
        return CHAIR_FAMILY_WING, "REA wing/crossing-chair subtype awaiting detailed special-chair assignment", code
    if role == "vee point rail":
        code = {"A": 24, "B": 26, "C": 26, "D": 27, "E": 28, "F": 28}.get(suffix, 26)
        family = CHAIR_FAMILY_NOSE if suffix == "A" else CHAIR_FAMILY_VEE
        return family, "REA vee/crossing-chair subtype awaiting detailed special-chair assignment", code
    if role == "vee splice rail":
        code = {"A": 24, "B": 25, "C": 26, "D": 27, "E": 28, "F": 28}.get(suffix, 25)
        family = CHAIR_FAMILY_NOSE if suffix == "A" else CHAIR_FAMILY_SPLICE
        return family, "REA splice/crossing-chair subtype awaiting detailed special-chair assignment", code
    code = {"Z": 21, "Y": 22, "X": 23, "A": 24, "B": 25, "C": 26, "D": 27, "E": 28, "F": 28}.get(suffix, 0)
    family = CHAIR_FAMILY_NOSE if suffix == "A" else CHAIR_FAMILY_CROSSING
    return family, "REA common-crossing subtype awaiting detailed special-chair assignment", code


def _chair_assignment(timber, rail, support=None):
    """Assign confirmed ordinary/C-switch chairs and stage special chairs."""
    identifier = _chair_effective_prototype_identifier(timber, rail, support)
    section = str(timber.get("section") or "").lower()
    role = str(rail.get("rail_role") or "").lower()
    digits = re.search(r"([0-9]+)", identifier)
    number = int(digits.group(1)) if digits else 0
    family = CHAIR_FAMILY_ORDINARY
    subtype = "REA S1 ordinary chair"
    chair_code = 1
    classification = CHAIR_CLASS_SOURCE
    assignment_status = CHAIR_ASSIGNMENT_CONFIRMED
    protected = []
    mandatory = False
    deliberate_omission = False

    if role == "crossover connecting rail":
        subtype = "REA S1 ordinary chair on the plain crossover connecting road"
        classification = CHAIR_CLASS_INFERENCE
    elif identifier.startswith("X") or role in (
        "check rail", "wing rail", "wing rail knuckle", "vee point rail", "vee splice rail"
    ):
        family, subtype, chair_code = _chair_crossing_deferred_assignment(identifier, timber, rail)
        assignment_status = CHAIR_ASSIGNMENT_DEFERRED_SPECIAL
        mandatory = True
        protected.append(str(rail.get("supported_feature") or "special crossing support"))
    elif identifier in ("J1", "J2"):
        family, subtype, chair_code = CHAIR_FAMILY_JOINT, "REA S1J switch-front joint chair", 7
        mandatory = True
        protected.append("switch-front rail joint")
    elif identifier == "R1" and role == "stock rail":
        family, subtype, chair_code = CHAIR_FAMILY_JOINT, "REA S1J exit joint chair", 7
        mandatory = True
        protected.append("exit rail joint")
    elif identifier.startswith("S") and number:
        if 1 <= number <= 7:
            if role == "stock rail":
                family, subtype, chair_code = CHAIR_FAMILY_SLIDE, "REA P slide chair", 2
                mandatory = True
                protected.extend(["slide-chair position", "switch blade support"])
                if number == 1:
                    protected.append("switch toe")
            elif "switch and closure" in role:
                family, subtype, chair_code = CHAIR_FAMILY_OMITTED, "switch blade supported by the adjacent P slide-chair table", 0
                assignment_status = CHAIR_ASSIGNMENT_OMITTED
                deliberate_omission = True
                mandatory = False
                protected.append("switch blade support shared with stock-rail slide chair")
        elif 8 <= number <= 9:
            if role == "stock rail":
                family, subtype, chair_code = CHAIR_FAMILY_SWITCH, "REA 1P/2P PLR block-slide chair", 11
                mandatory = True
                protected.append("switch blade block-slide support")
            elif "switch and closure" in role:
                family, subtype, chair_code = CHAIR_FAMILY_OMITTED, "switch blade supported by the adjacent 1P/2P block-slide chair", 0
                assignment_status = CHAIR_ASSIGNMENT_OMITTED
                deliberate_omission = True
                protected.append("switch blade support shared with block-slide chair")
        elif 10 <= number <= 12:
            if role == "stock rail":
                family, subtype, chair_code = CHAIR_FAMILY_SWITCH_HEEL, "REA 3P-5P PLR block-heel chair", 12
                mandatory = True
                protected.append("switch heel block support")
            elif "switch and closure" in role:
                family, subtype, chair_code = CHAIR_FAMILY_OMITTED, "switch rail supported by the adjacent PLR block-heel chair", 0
                assignment_status = CHAIR_ASSIGNMENT_OMITTED
                deliberate_omission = True
                protected.append("switch heel support shared with block-heel chair")
        else:
            subtype = "REA S1 ordinary chair beyond the C-switch block-chair zone"
    elif identifier.startswith("T") or section == "closure":
        subtype = "REA S1 ordinary closure-region chair; L1 clearance selection awaits detailed bridge-chair assignment"
    elif identifier.startswith("R"):
        subtype = "REA S1 ordinary exit chair"

    # Preserve route-specific protected metadata without allowing broad timber
    # labels to overwrite the exact C-switch assignment above.
    inherited = _chair_applicable_timber_features(timber, rail, support)
    for feature in inherited:
        if feature not in protected:
            protected.append(feature)
    if any(token in " ".join(protected).lower() for token in ("switch", "joint", "crossing", "wing", "check", "vee", "splice", "knuckle")):
        mandatory = mandatory or assignment_status == CHAIR_ASSIGNMENT_DEFERRED_SPECIAL

    length, width, dimension_class, dimension_note = _chair_base_dimensions(family, subtype)
    if classification == CHAIR_CLASS_SOURCE and dimension_class != CHAIR_CLASS_SOURCE:
        classification = dimension_class
    code, code_label = _chair_code_values(chair_code)
    return {
        "chair_family": family,
        "chair_subtype": subtype,
        "chair_code": code,
        "chair_code_label": code_label,
        "prototype_timber_identifier": identifier,
        "assignment_status": assignment_status,
        "assignment_complete_in_current_stage": assignment_status in (CHAIR_ASSIGNMENT_CONFIRMED, CHAIR_ASSIGNMENT_OMITTED),
        "special_assignment_deferred": assignment_status == CHAIR_ASSIGNMENT_DEFERRED_SPECIAL,
        "classification": classification,
        "mandatory": mandatory,
        "deliberate_omission": deliberate_omission,
        "protected_features": sorted(set(protected)),
        "footprint_length": length,
        "footprint_width": width,
        "footprint_dimension_classification": dimension_class,
        "footprint_dimension_note": dimension_note,
    }


def _chair_bridge_candidate_priority(position):
    name = str(position.get("rail_name") or "").lower()
    role = str(position.get("rail_role") or "").lower()
    if "main-side stock" in name:
        return 0
    if "straight switch" in name:
        return 1
    if "turnout-side stock" in name:
        return 2
    if "curved switch" in name:
        return 3
    if role == "stock rail":
        return 1
    return 2


def _chair_apply_bridge_candidate(position):
    length, width, dimension_class, dimension_note = _chair_base_dimensions(CHAIR_FAMILY_BRIDGE, "REA L1")
    position["chair_family"] = CHAIR_FAMILY_BRIDGE
    position["chair_subtype"] = "REA L1 bridge-chair candidate; final side and fit selection await detailed bridge-chair assignment"
    position["chair_code"] = 5
    position["chair_code_label"] = "L1"
    position["assignment_status"] = CHAIR_ASSIGNMENT_DEFERRED_SPECIAL
    position["assignment_complete_in_current_stage"] = True
    position["special_assignment_deferred"] = True
    position["key_orientation"] = "requires confirmation from the final bridge-chair subtype and keying arrangement"
    position["key_direction_sign"] = 0
    position["key_orientation_classification"] = CHAIR_CLASS_CONFIRM
    position["source_or_assumed_classification"] = CHAIR_CLASS_INFERENCE
    position["chair_footprint_parameters"].update({
        "length": float(length), "width": float(width),
        "dimension_classification": dimension_class,
        "dimension_note": dimension_note + "; candidate selected from analytical S1 clearance",
    })
    timber = position.get("_generation_timber")
    if isinstance(timber, dict):
        position["chair_footprint_parameters"]["polygon"] = _chair_footprint_polygon(
            position["centre_point"], timber, length, width
        )


def _chair_refine_bridge_candidates(positions, settings):
    """Identify only the tight ordinary-chair positions needing A8A7C review."""
    grouped = {}
    for position in positions:
        identifier = str(position.get("prototype_timber_identifier") or "")
        if position.get("chair_code") != 1 or not (identifier.startswith("T") or identifier == "S13"):
            continue
        grouped.setdefault(position.get("timber_identity"), []).append(position)
    tolerance_area = float(settings.get("position_tolerance") or 0.0) ** 2
    for values in grouped.values():
        changed = set()
        for first_index in range(len(values)):
            for second_index in range(first_index + 1, len(values)):
                first, second = values[first_index], values[second_index]
                polygon_a = first.get("chair_footprint_parameters", {}).get("polygon") or []
                polygon_b = second.get("chair_footprint_parameters", {}).get("polygon") or []
                if len(polygon_a) < 3 or len(polygon_b) < 3:
                    continue
                if not _chair_bbox_overlap(_chair_bbox_for_points(polygon_a), _chair_bbox_for_points(polygon_b)):
                    continue
                overlap = _timber_convex_intersection(polygon_a, polygon_b)
                area = abs(_timber_polygon_area(overlap)) if len(overlap) >= 3 else 0.0
                if area <= tolerance_area:
                    continue
                candidate = max((first, second), key=_chair_bridge_candidate_priority)
                changed.add(candidate["stable_chair_position_identity"])
        for position in values:
            if position["stable_chair_position_identity"] in changed:
                _chair_apply_bridge_candidate(position)
    for position in positions:
        position.pop("_generation_timber", None)


def _chair_orientation_metadata(config, rail, assignment, rail_station=None, rail_length=None):
    family = str(assignment.get("chair_family") or "")
    status = str(assignment.get("assignment_status") or "")
    if family in (CHAIR_FAMILY_ORDINARY, CHAIR_FAMILY_JOINT, CHAIR_FAMILY_BRIDGE, CHAIR_FAMILY_OMITTED):
        handedness = "not applicable"
    else:
        handedness = str((config or {}).get("handing") or "not applicable")
    if family == CHAIR_FAMILY_OMITTED:
        key_orientation = "not applicable"
        key_sign = 0
        key_classification = CHAIR_CLASS_SOURCE
    elif status == CHAIR_ASSIGNMENT_DEFERRED_SPECIAL:
        key_orientation = "requires confirmation from the final special-chair subtype and keying arrangement"
        key_sign = 0
        key_classification = CHAIR_CLASS_CONFIRM
    elif int(assignment.get("chair_code") or 0) == 7:
        key_orientation = "towards the adjacent rail joint; exact direction sign requires stored joint chainage"
        key_sign = 0
        key_classification = CHAIR_CLASS_SOURCE
    else:
        # Templot exposes random/towards-joint, forwards and backwards modes.
        # The FreeCAD macro does not yet store a key-direction policy, so do
        # not manufacture a direction from rail station or display order.
        key_orientation = "requires a configurable key-direction policy"
        key_sign = 0
        key_classification = CHAIR_CLASS_CONFIRM
    rail_source = dict((rail or {}).get("source_configuration") or {})
    gauge_face = str(rail_source.get("gauge_face") or "")
    outer_face = str(rail_source.get("outer_face") or "")
    rail_foot_orientation = (
        "seat orientation derived from named gauge face '{}' and outer face '{}'".format(gauge_face, outer_face)
        if gauge_face and outer_face
        else "derived from stable logical rail tangent; detailed foot seat requires later solid confirmation"
    )
    return {
        "handedness": handedness,
        "handedness_classification": CHAIR_CLASS_SOURCE if handedness != "not applicable" else CHAIR_CLASS_INFERENCE,
        "key_orientation": key_orientation,
        "key_direction_sign": key_sign,
        "key_orientation_classification": key_classification,
        "rail_foot_orientation": rail_foot_orientation,
        "rail_foot_orientation_classification": CHAIR_CLASS_SOURCE if gauge_face and outer_face else CHAIR_CLASS_CONFIRM,
    }


def _chair_footprint_fit_measurements(footprint, timber):
    polygon = list(footprint or [])
    if not polygon:
        return None
    centre = _chair_xy(timber.get("centre") or (0.0, 0.0))
    length_axis = tuple(float(value) for value in timber.get("length_axis", (0.0, 1.0)))
    width_axis = tuple(float(value) for value in timber.get("width_axis", (1.0, 0.0)))
    length_values, width_values = [], []
    for point in polygon:
        px, py = _chair_xy(point)
        dx, dy = px - centre[0], py - centre[1]
        length_values.append(dx * length_axis[0] + dy * length_axis[1])
        width_values.append(dx * width_axis[0] + dy * width_axis[1])
    half_length = 0.5 * float(timber.get("length") or 0.0)
    half_width = 0.5 * float(timber.get("width") or 0.0)
    near_end_clearance = min(length_values) + half_length
    far_end_clearance = half_length - max(length_values)
    approach_side_clearance = min(width_values) + half_width
    exit_side_clearance = half_width - max(width_values)
    end_clearance = min(near_end_clearance, far_end_clearance)
    side_clearance = min(approach_side_clearance, exit_side_clearance)
    return {
        "end_clearance": float(end_clearance),
        "side_clearance": float(side_clearance),
        "end_overhang": max(0.0, -float(end_clearance)),
        "side_overhang": max(0.0, -float(side_clearance)),
        "near_end_clearance": float(near_end_clearance),
        "far_end_clearance": float(far_end_clearance),
        "approach_side_clearance": float(approach_side_clearance),
        "exit_side_clearance": float(exit_side_clearance),
    }


def _chair_model_support_adjustment(
    footprint, timber, settings, deliberate_omission=False,
    assignment_status="", dimension_classification="",
):
    """Return a read-only model-support recommendation from confirmed data.

    A timber-width recommendation is meaningful only when both the chair
    assignment and its analytical footprint are established in the current
    stage.  Deferred special chairs and temporary envelopes remain visible to
    validation, but cannot silently drive a production-width recommendation.
    """
    result = {
        "required": False,
        "eligible_in_current_stage": False,
        "applied_to_production_geometry": False,
        "approach_side_extension": 0.0,
        "exit_side_extension": 0.0,
        "total_width_increase": 0.0,
        "model_support_edge_margin": float(settings.get("model_support_edge_margin") or 0.0),
        "classification": CHAIR_CLASS_ASSUMPTION,
        "reason": "no model-scale timber widening required",
    }
    if deliberate_omission or not settings.get("model_support_recommendations_enabled"):
        return result
    if str(assignment_status or "") != CHAIR_ASSIGNMENT_CONFIRMED:
        result["reason"] = "model support remains deferred until the special chair assignment is confirmed"
        return result
    if str(dimension_classification or "") != CHAIR_CLASS_SOURCE:
        result["reason"] = "model support remains deferred until the chair footprint dimension is confirmed"
        return result
    result["eligible_in_current_stage"] = True
    fit = _chair_footprint_fit_measurements(footprint, timber)
    if fit is None:
        return result
    margin = float(settings.get("model_support_edge_margin") or 0.0)
    approach = max(0.0, margin - float(fit["approach_side_clearance"]))
    exit_side = max(0.0, margin - float(fit["exit_side_clearance"]))
    result.update({
        "required": approach > 1.0e-9 or exit_side > 1.0e-9,
        "approach_side_extension": float(approach),
        "exit_side_extension": float(exit_side),
        "total_width_increase": float(approach + exit_side),
    })
    if result["required"]:
        result["reason"] = (
            "model-scale support allowance derived from a confirmed chair footprint; "
            "prototype timber width remains recorded separately"
        )
    return result


def generate_chair_positions(entity_kind, config, rail_records, timber_records, settings=None):
    settings = normalise_chair_analysis_settings(settings)
    entity_id = str(config.get("turnout_id") or config.get("crossover_id") or "")
    if not entity_id:
        raise ValueError("Chair analysis requires a stable turnout or crossover identity.")
    positions = []
    rail_supports = {rail["stable_identity"]: [] for rail in rail_records}
    padding = float(settings["position_tolerance"])
    prepared_rails = []
    rail_lengths = {}
    for rail in rail_records:
        points = list(rail.get("points") or [])
        prepared = _chair_prepare_polyline_projection(points)
        rail_id = str(rail["stable_identity"])
        rail_lengths[rail_id] = float(prepared.get("total_length") or 0.0)
        prepared_rails.append({
            "rail": rail,
            "points": points,
            "prepared": prepared,
            "bounding_box": _chair_bbox_for_points(points, padding) if points else (0.0, 0.0, 0.0, 0.0),
        })
    for timber in timber_records:
        polygon = list(timber.get("outline_polygon") or timber.get("collision_polygon") or [])
        if len(polygon) < 3:
            continue
        timber_bbox = _chair_bbox_for_points(polygon, padding)
        centre = timber.get("centre") or _timber_polygon_centroid(polygon)
        timber_id = str(timber.get("stable_identity") or timber.get("identifier") or "")
        for rail_data in prepared_rails:
            rail = rail_data["rail"]
            points = rail_data["points"]
            if len(points) < 2 or not _chair_bbox_overlap(timber_bbox, rail_data["bounding_box"]):
                continue
            projected = _chair_project_to_prepared_polyline(
                centre, rail_data["prepared"], timber_bbox
            )
            if projected is None:
                continue
            distance, rail_station, support, tangent, _segment_index = projected
            if not _chair_point_near_polygon(support, polygon, padding):
                continue
            assignment = _chair_assignment(timber, rail, support)
            footprint = _chair_footprint_polygon(
                support, timber, assignment["footprint_length"], assignment["footprint_width"]
            ) if not assignment["deliberate_omission"] else []
            timber_axis = tuple(float(value) for value in timber.get("width_axis", (1.0, 0.0)))
            dot = max(-1.0, min(1.0, abs(tangent[0] * timber_axis[0] + tangent[1] * timber_axis[1])))
            skew = math.degrees(math.acos(dot))
            position_id = _chair_position_identity(entity_id, timber_id, rail["stable_identity"])
            orientation_metadata = _chair_orientation_metadata(
                config, rail, assignment, rail_station, rail_lengths.get(rail["stable_identity"], 0.0)
            )
            support_zone = _chair_support_zone(
                timber, support, tangent, rail_station, settings,
                assignment["mandatory"] or assignment["deliberate_omission"],
            )
            support_adjustment = _chair_model_support_adjustment(
                footprint, timber, settings, assignment["deliberate_omission"],
                assignment["assignment_status"], assignment["footprint_dimension_classification"],
            )
            record = {
                "stable_chair_position_identity": position_id,
                "parent_template_set_identity": str(config.get("template_set_id") or ""),
                "parent_turnout_identity": str(rail.get("parent_turnout_identity") or ""),
                "parent_crossover_identity": str(rail.get("parent_crossover_identity") or ""),
                "timber_identity": timber_id,
                "timber_identifier": str(timber.get("identifier") or timber.get("prototype_reference") or ""),
                "prototype_timber_identifier": assignment["prototype_timber_identifier"],
                "rail_identity": str(rail.get("stable_identity") or ""),
                "rail_name": str(rail.get("name") or ""),
                "rail_role": str(rail.get("rail_role") or ""),
                "supported_feature": str(rail.get("supported_feature") or ""),
                "centre_point": [float(support[0]), float(support[1])],
                "rail_station": float(rail_station),
                "local_rail_tangent": [float(tangent[0]), float(tangent[1])],
                "timber_centre": [float(centre[0]), float(centre[1])],
                "timber_angle_radians": float(timber.get("angle_radians") or 0.0),
                "timber_angle_degrees": float(timber.get("angle_degrees") or 0.0),
                "local_support_direction": [float(timber.get("length_axis", [0.0, 1.0])[0]), float(timber.get("length_axis", [0.0, 1.0])[1])],
                "chair_family": assignment["chair_family"],
                "chair_subtype": assignment["chair_subtype"],
                "chair_code": int(assignment.get("chair_code") or 0),
                "chair_code_label": str(assignment.get("chair_code_label") or ""),
                "assignment_status": assignment["assignment_status"],
                "assignment_complete_in_current_stage": bool(assignment["assignment_complete_in_current_stage"]),
                "special_assignment_deferred": bool(assignment["special_assignment_deferred"]),
                "handedness": orientation_metadata["handedness"],
                "handedness_classification": orientation_metadata["handedness_classification"],
                "key_orientation": orientation_metadata["key_orientation"],
                "key_direction_sign": int(orientation_metadata["key_direction_sign"]),
                "key_orientation_classification": orientation_metadata["key_orientation_classification"],
                "rail_foot_orientation": orientation_metadata["rail_foot_orientation"],
                "rail_foot_orientation_classification": orientation_metadata["rail_foot_orientation_classification"],
                "protected_support_classification": "mandatory" if assignment["mandatory"] else ("deliberately omitted" if assignment["deliberate_omission"] else "ordinary"),
                "protected_features": list(assignment["protected_features"]),
                "protected_support_zone": support_zone,
                "source_configuration": {"rail": dict(rail.get("source_configuration") or {}), "timber": dict(timber.get("source_configuration") or {})},
                "chair_footprint_parameters": {
                    "length": float(assignment["footprint_length"]), "width": float(assignment["footprint_width"]),
                    "clearance": float(settings["footprint_clearance"]), "polygon": footprint,
                    "dimension_classification": assignment["footprint_dimension_classification"],
                    "dimension_note": assignment["footprint_dimension_note"],
                },
                "model_timber_support_adjustment": support_adjustment,
                "future_solid_generation_parameters": {
                    "embed_depth": float(settings["future_chair_embed_depth"]),
                    "boolean_overlap_allowance": float(settings["future_boolean_overlap_allowance"]),
                    "boolean_fuzzy_tolerance": float(settings["future_boolean_fuzzy_tolerance"]),
                    "active_in_this_stage": False,
                },
                "source_or_assumed_classification": assignment["classification"],
                "validation_status": "not yet validated", "stale_signature_state": False,
                "mandatory": bool(assignment["mandatory"]), "deliberate_omission": bool(assignment["deliberate_omission"]),
                "chair_skew_degrees": float(skew), "distance_from_timber_centre": float(distance),
                "_generation_timber": timber,
            }
            positions.append(record)
            rail_supports[rail["stable_identity"]].append(record)
    positions.sort(key=lambda item: (item["timber_identity"], item["rail_identity"], item["stable_chair_position_identity"]))
    identities = [item["stable_chair_position_identity"] for item in positions]
    if len(identities) != len(set(identities)):
        raise ValueError("Chair-position generation produced duplicate stable identities.")
    _chair_refine_bridge_candidates(positions, settings)
    timber_by_id = {str(item.get("stable_identity") or ""): item for item in timber_records}
    for position in positions:
        timber = timber_by_id.get(position["timber_identity"])
        if timber is not None:
            position["model_timber_support_adjustment"] = _chair_model_support_adjustment(
                position.get("chair_footprint_parameters", {}).get("polygon") or [], timber, settings,
                position.get("deliberate_omission", False), position.get("assignment_status", ""),
                position.get("chair_footprint_parameters", {}).get("dimension_classification", ""),
            )
    return positions, rail_supports


def _chair_model_support_plan(positions):
    grouped = {}
    for position in positions:
        adjustment = dict(position.get("model_timber_support_adjustment") or {})
        if not adjustment.get("required"):
            continue
        timber_id = str(position.get("timber_identity") or "")
        record = grouped.setdefault(timber_id, {
            "timber_identity": timber_id,
            "timber_identifier": str(position.get("timber_identifier") or ""),
            "approach_side_extension": 0.0,
            "exit_side_extension": 0.0,
            "total_width_increase": 0.0,
            "chair_position_identities": [],
            "applied_to_production_geometry": False,
        })
        record["approach_side_extension"] = max(record["approach_side_extension"], float(adjustment.get("approach_side_extension") or 0.0))
        record["exit_side_extension"] = max(record["exit_side_extension"], float(adjustment.get("exit_side_extension") or 0.0))
        record["chair_position_identities"].append(position["stable_chair_position_identity"])
    for record in grouped.values():
        record["total_width_increase"] = record["approach_side_extension"] + record["exit_side_extension"]
        record["chair_position_identities"] = sorted(set(record["chair_position_identities"]))
    return sorted(grouped.values(), key=lambda item: item["timber_identity"])


def _chair_recount_findings(findings, positions):
    severity_order = {
        CHAIR_SEVERITY_INFORMATION: 0, CHAIR_SEVERITY_ADVISORY: 1,
        CHAIR_SEVERITY_CONFLICT: 2, CHAIR_SEVERITY_CRITICAL: 3,
    }
    findings.sort(key=lambda item: (-severity_order.get(item["severity"], 0), item["code"], item["message"]))
    counts = {name: 0 for name in severity_order}
    for finding in findings:
        counts[finding["severity"]] = counts.get(finding["severity"], 0) + 1
    maximum_severity_by_chair = {}
    for finding in findings:
        rank = severity_order.get(finding["severity"], 0)
        for identity in finding.get("chair_position_identities", []) or []:
            current = maximum_severity_by_chair.get(identity)
            if current is None or rank > current[0]:
                maximum_severity_by_chair[identity] = (rank, finding["severity"])
    for item in positions:
        status = maximum_severity_by_chair.get(item["stable_chair_position_identity"])
        item["validation_status"] = status[1] if status is not None else "validated"
    return findings, counts


def validate_chair_positions(config, rail_records, timber_records, positions, rail_supports, settings=None):
    settings = normalise_chair_analysis_settings(settings)
    findings, _counts = _A8A7A1_VALIDATE_CHAIR_POSITIONS(
        config, rail_records, timber_records, positions, rail_supports, settings
    )
    positions_by_id = {item["stable_chair_position_identity"]: item for item in positions}
    transformed = []
    for finding in findings:
        code = str(finding.get("code") or "")
        linked = [positions_by_id.get(identity) for identity in finding.get("chair_position_identities") or []]
        linked = [item for item in linked if item is not None]
        if code == "PROTECTED_TIMBER_WITHOUT_MANDATORY_CHAIR":
            timber_ids = [str(value) for value in finding.get("timber_identities") or []]
            timber_positions = [item for item in positions if str(item.get("timber_identity") or "") in timber_ids]
            # A8A7A1's timber-level protection is intentionally broad.  S13
            # and closure timbers can be fully supported by ordinary S1 or
            # provisional L1 chairs without every support being marked
            # mandatory.  Exact rail-position validation supersedes the broad
            # timber flag at this stage.
            if timber_positions and all(
                item.get("chair_code") in (1, 5)
                or item.get("special_assignment_deferred")
                or item.get("deliberate_omission")
                for item in timber_positions
            ):
                continue
        if code == "CHAIR_FOOTPRINT_SIDE_OVERHANG":
            if linked:
                position = linked[0]
                adjustment = dict(position.get("model_timber_support_adjustment") or {})
                if adjustment.get("required"):
                    transformed.append(_chair_finding(
                        "MODEL_TIMBER_SUPPORT_WIDENING_RECOMMENDED", CHAIR_SEVERITY_ADVISORY,
                        "Chair {} requires a read-only model support recommendation of {:.3f} mm on the approach side and {:.3f} mm on the exit side of timber {}. No production timber has been changed.".format(
                            position["stable_chair_position_identity"],
                            adjustment.get("approach_side_extension", 0.0),
                            adjustment.get("exit_side_extension", 0.0),
                            position["timber_identity"],
                        ),
                        [position["stable_chair_position_identity"]], [position["timber_identity"]], [position["rail_identity"]],
                    ))
                else:
                    transformed.append(_chair_finding(
                        "CHAIR_FOOTPRINT_SUPPORT_REQUIRES_DIMENSION_CONFIRMATION", CHAIR_SEVERITY_ADVISORY,
                        "Chair {} has analytical side overhang, but its assignment or footprint dimension is not yet confirmed. No timber-width recommendation has been created.".format(
                            position["stable_chair_position_identity"]
                        ),
                        [position["stable_chair_position_identity"]], [position["timber_identity"]], [position["rail_identity"]],
                    ))
            continue
        if code in ("CHAIR_INTERFERENCE_ADJACENT_RAILS", "OVERLAPPING_CHAIR_FOOTPRINTS") and any(item.get("special_assignment_deferred") for item in linked):
            transformed.append(_chair_finding(
                "SPECIAL_CHAIR_CLEARANCE_REQUIRES_CONFIRMATION", CHAIR_SEVERITY_ADVISORY,
                "Analytical chair envelopes overlap at a position whose final bridge, crossing, wing or check-chair subtype remains awaiting detailed special-chair assignment.",
                finding.get("chair_position_identities"), finding.get("timber_identities"), finding.get("rail_identities"),
            ))
            continue
        transformed.append(finding)

    # Enforce the source-derived C-switch chair sequence per constituent turnout.
    by_turnout = {}
    for item in positions:
        turnout_id = str(item.get("parent_turnout_identity") or "")
        if turnout_id:
            by_turnout.setdefault(turnout_id, []).append(item)
        if item.get("assignment_status") == CHAIR_ASSIGNMENT_CONFIRMED and int(item.get("chair_code") or 0) not in (1, 2, 7, 11, 12):
            transformed.append(_chair_finding(
                "CONFIRMED_ASSIGNMENT_HAS_INVALID_CHAIR_CODE", CHAIR_SEVERITY_CONFLICT,
                "Confirmed ordinary/turnout chair {} has invalid chair code {}.".format(
                    item["stable_chair_position_identity"], item.get("chair_code")
                ), [item["stable_chair_position_identity"]], [item["timber_identity"]], [item["rail_identity"]],
            ))
    for turnout_id, values in by_turnout.items():
        expected = {2: 14, 11: 4, 12: 6}
        actual = {code: sum(1 for item in values if int(item.get("chair_code") or 0) == code) for code in expected}
        for code, count in expected.items():
            if actual[code] != count:
                transformed.append(_chair_finding(
                    "C_SWITCH_CHAIR_SEQUENCE_INCOMPLETE", CHAIR_SEVERITY_CRITICAL,
                    "Turnout {} has {} {} assignments; the REA C-switch sequence requires {}.".format(
                        turnout_id, actual[code], CHAIR_CODE_CATALOG[code]["label"], count
                    ), rail_ids=[turnout_id],
                ))
        omitted = sum(1 for item in values if item.get("assignment_status") == CHAIR_ASSIGNMENT_OMITTED and str(item.get("prototype_timber_identifier") or "").startswith("S"))
        if omitted != 24:
            transformed.append(_chair_finding(
                "C_SWITCH_SHARED_SUPPORT_SEQUENCE_INCOMPLETE", CHAIR_SEVERITY_CRITICAL,
                "Turnout {} has {} deliberately shared switch-rail positions; 24 are required across S1-S12.".format(turnout_id, omitted),
                rail_ids=[turnout_id],
            ))

    preferred = float(settings.get("preferred_maximum_model_support_extension_per_side") or 0.0)
    if preferred > 0.0:
        for item in positions:
            adjustment = dict(item.get("model_timber_support_adjustment") or {})
            maximum = max(float(adjustment.get("approach_side_extension") or 0.0), float(adjustment.get("exit_side_extension") or 0.0))
            if adjustment.get("required") and maximum > preferred + 1.0e-9:
                transformed.append(_chair_finding(
                    "MODEL_SUPPORT_EXTENSION_EXCEEDS_PREFERRED_LIMIT", CHAIR_SEVERITY_ADVISORY,
                    "Chair {} needs {:.3f} mm support extension on one timber side, above the preferred {:.3f} mm review limit.".format(
                        item["stable_chair_position_identity"], maximum, preferred
                    ), [item["stable_chair_position_identity"]], [item["timber_identity"]], [item["rail_identity"]],
                ))
    return _chair_recount_findings(transformed, positions)


def _chair_status_from_counts(position_count, positions, counts):
    if counts.get(CHAIR_SEVERITY_CRITICAL, 0):
        return CHAIR_STATUS_CRITICAL
    if counts.get(CHAIR_SEVERITY_CONFLICT, 0):
        return CHAIR_STATUS_CONFLICTS
    if any(item.get("assignment_status") == CHAIR_ASSIGNMENT_UNRESOLVED for item in positions):
        return CHAIR_STATUS_INCOMPLETE
    if position_count:
        return CHAIR_STATUS_ASSIGNMENTS_VALIDATED
    return CHAIR_STATUS_INCOMPLETE


def analyse_chair_position_records(entity_kind, config, rail_records, timber_records, settings=None):
    profile_start = time.perf_counter()
    profile_stage_start = profile_start
    settings = normalise_chair_analysis_settings(settings)
    profile_timings = {
        "settings_normalisation": (time.perf_counter() - profile_stage_start) * 1000.0,
    }

    profile_stage_start = time.perf_counter()
    positions, rail_supports = generate_chair_positions(entity_kind, config, rail_records, timber_records, settings)
    profile_timings["chair_position_generation"] = (time.perf_counter() - profile_stage_start) * 1000.0

    profile_stage_start = time.perf_counter()
    findings, counts = validate_chair_positions(config, rail_records, timber_records, positions, rail_supports, settings)
    profile_timings["chair_position_validation"] = (time.perf_counter() - profile_stage_start) * 1000.0

    profile_stage_start = time.perf_counter()
    status = _chair_status_from_counts(len(positions), positions, counts)
    families, chair_codes, assignment_counts = {}, {}, {}
    for item in positions:
        families[item["chair_family"]] = families.get(item["chair_family"], 0) + 1
        label = str(item.get("chair_code_label") or "shared/omitted")
        chair_codes[label] = chair_codes.get(label, 0) + 1
        assignment = str(item.get("assignment_status") or CHAIR_ASSIGNMENT_UNRESOLVED)
        assignment_counts[assignment] = assignment_counts.get(assignment, 0) + 1
    support_plan = _chair_model_support_plan(positions)
    profile_timings["result_summary_assembly"] = (time.perf_counter() - profile_stage_start) * 1000.0
    profile_timings["core_total"] = (time.perf_counter() - profile_start) * 1000.0
    return {
        "schema_version": CHAIR_ANALYSIS_SCHEMA_VERSION,
        "macro_version": MACRO_VERSION_NUMBER,
        "entity_kind": str(entity_kind),
        "entity_id": str(config.get("turnout_id") or config.get("crossover_id") or ""),
        "status": status,
        "settings": settings,
        "source_basis": list(CHAIR_ANALYSIS_SOURCE_BASIS) + [
            "Templot5 revision 556b switch_select.pas REA C-switch counts: 7 P, 2 PLR block-slide and 3 PLR block-heel chairs per stock-rail side",
            "Templot5 revision 556b math_unit.pas drawtimber default S1, S1J joint, P slide, PLR1 and PLR3 assignment sequence",
            "Model-scale support extensions are derived analytical recommendations and are not prototype dimensions",
        ],
        "positions": positions,
        "findings": findings,
        "model_timber_support_plan": support_plan,
        "summary": {
            "rail_count": len(rail_records), "timber_count": len(timber_records), "chair_position_count": len(positions),
            "family_counts": families, "chair_code_counts": chair_codes, "assignment_status_counts": assignment_counts,
            "severity_counts": counts,
            "deliberately_omitted_count": sum(1 for item in positions if item.get("deliberate_omission")),
            "mandatory_position_count": sum(1 for item in positions if item.get("mandatory")),
            "confirmed_ordinary_turnout_assignment_count": sum(1 for item in positions if item.get("assignment_status") == CHAIR_ASSIGNMENT_CONFIRMED),
            "special_assignment_deferred_count": sum(1 for item in positions if item.get("special_assignment_deferred")),
            "model_support_timber_count": len(support_plan),
            "maximum_model_support_extension_per_side": max([
                max(item["approach_side_extension"], item["exit_side_extension"]) for item in support_plan
            ] or [0.0]),
        },
        "cache_reused": False, "production_geometry_changed": False,
        "model_timber_support_changes_applied": False,
        "chair_solids_generated": False,
        "performance_timings_ms": profile_timings,
    }


def chair_analysis_summary(result, include_findings=True):
    if not isinstance(result, dict):
        return "No chair analysis has been stored."
    summary = dict(result.get("summary") or {})
    lines = [
        "Chair-position and assignment analysis — {}".format(result.get("entity_id") or "unknown"),
        "Status: {}".format(result.get("status") or CHAIR_STATUS_NOT_ANALYSED),
        "Rails analysed: {}".format(summary.get("rail_count", 0)),
        "Final effective timbers analysed: {}".format(summary.get("timber_count", 0)),
        "Logical chair positions: {}".format(summary.get("chair_position_count", 0)),
        "Confirmed ordinary and turnout assignments: {}".format(summary.get("confirmed_ordinary_turnout_assignment_count", 0)),
        "Special assignments awaiting detailed assignment: {}".format(summary.get("special_assignment_deferred_count", 0)),
        "Mandatory protected positions: {}".format(summary.get("mandatory_position_count", 0)),
        "Deliberately omitted/shared switch supports: {}".format(summary.get("deliberately_omitted_count", 0)),
        "Model-support timber recommendations: {}".format(summary.get("model_support_timber_count", 0)),
        "Maximum recommended extension on one timber side: {:.3f} mm".format(float(summary.get("maximum_model_support_extension_per_side") or 0.0)),
        "Cache reused: {}".format("Yes" if result.get("cache_reused") else "No"),
        "Production geometry changed: No",
        "Model timber widening applied: {}".format("Yes — effective physical-support envelope only; prototype timber references retained" if result.get("model_timber_support_changes_applied") else "No — recommendations only"),
        "Temporary diagnostic markers generated: {} — display objects only".format("Yes" if result.get("temporary_diagnostics_generated") else "No"),
        "Detailed chair solids generated: No — later solid-generation stage",
        "Measured run time: {:.1f} ms{}".format(
            float((result.get("performance_timings_ms") or {}).get("total") or (result.get("performance_timings_ms") or {}).get("before_display") or 0.0),
            " (calculation cache reused)" if result.get("cache_reused") else "",
        ),
        "Final solid/export validation complete: No — later validation stage",
        "",
        "Chair codes:",
    ]
    for name, count in sorted((summary.get("chair_code_counts") or {}).items()):
        lines.append("  - {}: {}".format(name, count))
    lines.extend(["", "Chair families:"])
    for name, count in sorted((summary.get("family_counts") or {}).items()):
        lines.append("  - {}: {}".format(name, count))
    severity_counts = summary.get("severity_counts") or {}
    lines.extend(["", "Validation findings:"])
    for severity in (CHAIR_SEVERITY_CRITICAL, CHAIR_SEVERITY_CONFLICT, CHAIR_SEVERITY_ADVISORY, CHAIR_SEVERITY_INFORMATION):
        lines.append("  - {}: {}".format(severity, severity_counts.get(severity, 0)))
    support_plan = list(result.get("model_timber_support_plan") or [])
    if support_plan:
        lines.extend(["", "Model timber support recommendations (read-only):"])
        for item in support_plan[:12]:
            lines.append(
                "  - {}: extend approach side {:.3f} mm; exit side {:.3f} mm; total width increase {:.3f} mm.".format(
                    item.get("timber_identifier") or item.get("timber_identity"),
                    item.get("approach_side_extension", 0.0), item.get("exit_side_extension", 0.0),
                    item.get("total_width_increase", 0.0),
                )
            )
        if len(support_plan) > 12:
            lines.append("  - {} further timber recommendation(s) remain stored in the metadata.".format(len(support_plan) - 12))
    timings = dict(result.get("performance_timings_ms") or {})
    if timings:
        lines.extend([
            "",
            "Live performance profile:",
            "- Record extraction: {:.1f} ms".format(float(timings.get("record_extraction") or 0.0)),
            "- Chair-position generation: {:.1f} ms".format(float(timings.get("core_chair_position_generation") or timings.get("chair_position_generation") or 0.0)),
            "- Chair validation: {:.1f} ms".format(float(timings.get("core_chair_position_validation") or timings.get("chair_position_validation") or 0.0)),
            "- Metadata updates: {:.1f} ms".format(float(timings.get("metadata_updates") or 0.0)),
            "- Diagnostic display construction: {:.1f} ms".format(float(timings.get("diagnostic_display_construction") or 0.0)),
            "- Document recompute: {:.1f} ms".format(float(timings.get("document_recompute") or 0.0)),
            "- Total operation: {:.1f} ms".format(float(timings.get("total") or timings.get("core_total") or 0.0)),
        ])
    if include_findings:
        findings = list(result.get("findings") or [])
        if not findings:
            lines.extend(["", "No validation findings."])
        else:
            grouped_codes = {
                "MODEL_TIMBER_SUPPORT_WIDENING_RECOMMENDED",
                "MODEL_SUPPORT_EXTENSION_EXCEEDS_PREFERRED_LIMIT",
                "CHAIR_FOOTPRINT_SUPPORT_REQUIRES_DIMENSION_CONFIRMATION",
                "SPECIAL_CHAIR_CLEARANCE_REQUIRES_CONFIRMATION",
                "EXCESSIVE_CHAIR_SKEW",
                "KEY_ORIENTATION_REQUIRES_CONFIRMATION",
            }
            direct = [item for item in findings if item.get("code") not in grouped_codes]
            grouped = {}
            for item in findings:
                if item.get("code") in grouped_codes:
                    grouped.setdefault((item.get("severity"), item.get("code")), []).append(item)
            if direct:
                lines.append("")
                for finding in direct:
                    lines.append("[{}] {}: {}".format(finding.get("severity"), finding.get("code"), finding.get("message")))
            if grouped:
                lines.extend(["", "Grouped advisory and informational findings:"])
                for (severity, code), items in sorted(grouped.items()):
                    if code == "EXCESSIVE_CHAIR_SKEW":
                        values = []
                        positions_by_id = {str(item.get("stable_chair_position_identity") or ""): item for item in result.get("positions") or []}
                        for finding in items:
                            for identity in finding.get("chair_position_identities") or []:
                                values.append(float((positions_by_id.get(identity) or {}).get("chair_skew_degrees") or 0.0))
                        detail = "Maximum reported analytical skew: {:.3f} degrees.".format(max(values) if values else 0.0)
                    else:
                        detail = str(items[0].get("message") or "")
                    lines.append("[{}] {}: {} position(s). {}".format(severity, code, len(items), detail))
                lines.append("Individual records remain stored in the chair-analysis metadata.")
    return "\n".join(lines)


class ChairAnalysisSettingsDialog(QtWidgets.QDialog):
    def __init__(self, settings, parent=None):
        super(ChairAnalysisSettingsDialog, self).__init__(parent)
        self.setWindowTitle(versioned_dialog_title("Chair tolerances and settings"))
        self._defaults = normalise_chair_analysis_settings(settings)
        layout = QtWidgets.QFormLayout(self)
        self.position = QtWidgets.QDoubleSpinBox(); self.position.setRange(0.0, 5.0); self.position.setDecimals(3); self.position.setSuffix(" mm"); self.position.setValue(self._defaults["position_tolerance"])
        self.position.setToolTip("Tolerance used to decide whether a rail support centre lies on a timber. It affects analysis only and never moves geometry.")
        self.footprint = QtWidgets.QDoubleSpinBox(); self.footprint.setRange(0.0, 5.0); self.footprint.setDecimals(3); self.footprint.setSuffix(" mm"); self.footprint.setValue(self._defaults["footprint_clearance"])
        self.footprint.setToolTip("Clearance added when analytical chair-footprint candidates are compared. It affects analysis only.")
        self.end_clearance = QtWidgets.QDoubleSpinBox(); self.end_clearance.setRange(0.0, 10.0); self.end_clearance.setDecimals(3); self.end_clearance.setSuffix(" mm"); self.end_clearance.setValue(self._defaults["timber_end_clearance"])
        self.end_clearance.setToolTip("Minimum desired model-scale clearance between the analytical chair footprint and a timber end.")
        self.skew = QtWidgets.QDoubleSpinBox(); self.skew.setRange(0.0, 30.0); self.skew.setDecimals(2); self.skew.setSuffix(" degrees"); self.skew.setValue(self._defaults["maximum_advisory_skew_degrees"])
        self.skew.setToolTip("Chair skew above this value is reported as advisory. It does not rotate rails or timbers.")
        self.span = QtWidgets.QDoubleSpinBox(); self.span.setRange(1.0, 100.0); self.span.setDecimals(3); self.span.setSuffix(" mm"); self.span.setValue(self._defaults["maximum_unsupported_span"])
        self.span.setToolTip("Largest permitted model-scale distance between adjacent logical rail supports before a production conflict is reported.")
        self.model_support = QtWidgets.QCheckBox("Create model timber support recommendations"); self.model_support.setChecked(self._defaults["model_support_recommendations_enabled"])
        self.model_support.setToolTip("Calculates fractional timber-width extensions needed to support complete analytical chair bases on tight model curves. It creates metadata only and does not resize production timbers.")
        self.support_margin = QtWidgets.QDoubleSpinBox(); self.support_margin.setRange(0.0, 3.0); self.support_margin.setDecimals(3); self.support_margin.setSuffix(" mm"); self.support_margin.setValue(self._defaults["model_support_edge_margin"])
        self.support_margin.setToolTip("Desired model-scale timber material beyond the analytical chair-base edge when calculating a widening recommendation. It does not alter geometry.")
        self.support_limit = QtWidgets.QDoubleSpinBox(); self.support_limit.setRange(0.0, 10.0); self.support_limit.setDecimals(3); self.support_limit.setSuffix(" mm"); self.support_limit.setValue(self._defaults["preferred_maximum_model_support_extension_per_side"])
        self.support_limit.setToolTip("Extensions above this review value are reported separately. It is advisory and does not cap or apply the recommendation.")
        self.cache = QtWidgets.QCheckBox("Reuse analysis when signatures match"); self.cache.setChecked(self._defaults["cache_enabled"])
        self.cache.setToolTip("Reuses cached metadata only when rail, timber, assignment and setting signatures match exactly.")
        layout.addRow("Chair-position tolerance", self.position)
        layout.addRow("Footprint broad-phase clearance", self.footprint)
        layout.addRow("Minimum timber-end clearance", self.end_clearance)
        layout.addRow("Maximum advisory chair skew", self.skew)
        layout.addRow("Maximum unsupported rail span", self.span)
        layout.addRow("Model support policy", self.model_support)
        layout.addRow("Model support edge margin", self.support_margin)
        layout.addRow("Preferred extension review limit", self.support_limit)
        layout.addRow("Analysis cache", self.cache)
        note = QtWidgets.QLabel("Model timber extensions are recommendations only. Special-chair fitting, chair solids and final production validation remain separate later stages.")
        note.setWordWrap(True); layout.addRow(note)
        buttons = QtWidgets.QDialogButtonBox(QtWidgets.QDialogButtonBox.Ok | QtWidgets.QDialogButtonBox.Cancel)
        buttons.accepted.connect(self.accept); buttons.rejected.connect(self.reject); layout.addRow(buttons)

    def values(self):
        result = dict(self._defaults)
        result.update({
            "position_tolerance": self.position.value(), "footprint_clearance": self.footprint.value(),
            "timber_end_clearance": self.end_clearance.value(), "maximum_advisory_skew_degrees": self.skew.value(),
            "maximum_unsupported_span": self.span.value(), "cache_enabled": self.cache.isChecked(),
            "model_support_recommendations_enabled": self.model_support.isChecked(),
            "model_support_edge_margin": self.support_margin.value(),
            "preferred_maximum_model_support_extension_per_side": self.support_limit.value(),
        })
        return normalise_chair_analysis_settings(result)


def preflight_chair_analysis_readiness(doc, records, set_id):
    representatives = {}
    for record in records or []:
        kind, identifier = _chair_preflight_record_entity(doc, record)
        if kind and identifier:
            representatives.setdefault((kind, identifier), record)
    issues = []
    for (kind, identifier), record in sorted(representatives.items()):
        config = turnout_config_by_id(doc, identifier) if kind == "turnout" else crossover_config_by_id(doc, identifier)
        if not isinstance(config, dict):
            continue
        status = chair_analysis_effective_status(doc, kind, config)
        if status in (CHAIR_STATUS_NOT_ANALYSED, CHAIR_STATUS_STALE):
            issues.append(make_preflight_issue(
                "CHAIR_ANALYSIS_{}".format("STALE" if status == CHAIR_STATUS_STALE else "NOT_RUN"),
                PRODUCTION_PREFLIGHT_SEVERITY_WARNING,
                "{} {} chair analysis is {}. Inspection export remains available.".format(kind.capitalize(), identifier, status.lower()),
                set_id, record, blocks_export=False,
            ))
        elif status == CHAIR_STATUS_CRITICAL:
            issues.append(make_preflight_issue(
                "CHAIR_PRODUCTION_CRITICAL_CONFLICTS", PRODUCTION_PREFLIGHT_SEVERITY_WARNING,
                "{} {} has production-critical logical chair conflicts. Inspection export remains available; production readiness is blocked.".format(kind.capitalize(), identifier),
                set_id, record, blocks_export=False,
            ))
        elif status in (CHAIR_STATUS_CONFLICTS, CHAIR_STATUS_INCOMPLETE):
            issues.append(make_preflight_issue(
                "CHAIR_ASSIGNMENTS_INCOMPLETE", PRODUCTION_PREFLIGHT_SEVERITY_WARNING,
                "{} {} ordinary or turnout chair assignments are not complete ({}). Inspection export remains available.".format(kind.capitalize(), identifier, status),
                set_id, record, blocks_export=False,
            ))
        else:
            issues.append(make_preflight_issue(
                "SPECIAL_CHAIRS_SOLIDS_AND_FINAL_VALIDATION_OUTSTANDING", PRODUCTION_PREFLIGHT_SEVERITY_INFORMATION,
                "{} {} ordinary and turnout assignments are current. Special-chair assignment, any approved model timber support changes, detailed chair solids and final solid/export validation remain outstanding.".format(kind.capitalize(), identifier),
                set_id, record, blocks_export=False,
            ))
    return issues


# ---------------------------------------------------------------------------
# A8A7B13 production chair geometry and automatic model-timber support.
#
# This additive extension keeps the established railway geometry, crossover
# solvers, host integration and export paths unchanged. It retains the fixed
# Templot 556b C&L / EMGS / S4Soc Code 75 rev:A bullhead rail profile and
# source-dimensional S1/S1J bodies, then derives the smallest model-only timber
# widening needed to support a skewed physical chair body. Prototype timber
# references remain intact. Extensions above the configured per-side limit are
# rejected rather than hidden. Special switch, bridge, check and crossing
# chairs remain explicit analytical positions.
# ---------------------------------------------------------------------------
_A8A7B11_CHAIR_ENTITY_OBJECTS = _chair_entity_objects
_A8A7B11_CLEAR_CHAIR_ANALYSIS_DISPLAY = clear_chair_analysis_display
_A8A7B11_INVALIDATE_CHAIR_ANALYSIS = invalidate_chair_analysis
_A8A7B11_ANALYSE_ENTITY_CHAIR_POSITIONS = analyse_entity_chair_positions
_A8A7B11_CHAIR_ANALYSIS_SUMMARY = chair_analysis_summary
_A8A7B11_PREFLIGHT_CHAIR_ANALYSIS_READINESS = preflight_chair_analysis_readiness
_A8A7B11_CROSSOVER_UPDATE_GUIDED_WORKFLOW = CrossoverManagerPanel.update_guided_workflow
_A8A7B11_CROSSOVER_RUN_NEXT_GUIDED_STEP = CrossoverManagerPanel.run_next_guided_step
_A8A7B11_TURNOUT_UPDATE_GUIDED_WORKFLOW = TurnoutManagerDialog.update_guided_workflow
_A8A7B11_TURNOUT_RUN_NEXT_GUIDED_STEP = TurnoutManagerDialog.run_next_guided_step

MACRO_VERSION_NUMBER = "10.2A8A7B15"
MACRO_VERSION = "{} CHAIR PERFORMANCE AND REPRESENTATION".format(MACRO_VERSION_NUMBER)
CHAIR_ANALYSIS_SCHEMA_VERSION = 5
CHAIR_SOLID_SCHEMA_VERSION = 2
CHAIR_SOLID_PROTOTYPE_REVISION = 1
CHAIR_SOLID_ROLE = "ChairProductionSolids"
CHAIR_UNRESOLVED_MARKER_ROLE = "ChairUnresolvedPositionMarkers"
CHAIR_SOLID_STATUS_PROPERTY = "ChairSolidStatus"
CHAIR_SOLID_SIGNATURE_PROPERTY = "ChairSolidSignature"
CHAIR_SOLID_RESULT_PROPERTY = "ChairSolidResultJSON"
CHAIR_PHYSICAL_FIT_STATUS_PROPERTY = "ChairPhysicalFitStatus"
CHAIR_SOLID_PARENT_KIND_PROPERTY = "ChairParentKind"
CHAIR_SOLID_PARENT_ID_PROPERTY = "ChairParentIdentity"
CHAIR_SOLID_STATUS_NOT_GENERATED = "Supported chair solids not generated"
CHAIR_SOLID_STATUS_STALE = "Supported chair solids are stale"
CHAIR_SOLID_STATUS_GENERATED = "Supported S1/S1J chair bodies generated"
CHAIR_SOLID_STATUS_FIT_VALIDATED = "Supported S1/S1J chair-body fit validated"
CHAIR_SOLID_STATUS_FIT_FAILED = "Physical chair-body fit failed"
CHAIR_SOLID_SUPPORTED_CODES = (1, 7)
CHAIR_SOLID_SUPPORTED_LABELS = ("S1", "S1J")
CHAIR_SOLID_SOURCE_BASIS = (
    "Templot5 revision 556b dxf_unit.pas init_rail_section: C&L / EMGS / S4Soc Code 75 rev:A rail section",
    "Templot5 revision 556b chairs_unit.pas init_2d_rea: REA S1 and S1J chair base dimensions",
    "Templot5 revision 556b chairs_unit.pas init_3d_rea: chair edge, plinth, seat and jaw reference dimensions",
)

CHAIR_CODE75_RAIL_PROFILE = {
    "profile_id": "Templot556b-CL-EMGS-S4Soc-Code75-revA",
    "operator_label": "Templot C&L / EMGS / S4Soc Code 75 bullhead rev:A",
    "source_revision": "Templot5 556b, dxf_unit.pas init_rail_section",
    "scale_mm_per_foot": 4.0,
    "vertical_rail": True,
    "rail_depth_mm": 1.90,
    "rail_head_width_mm": 0.90,
    "rail_corner_radius_mm": 0.15,
    "rail_foot_width_mm": 0.90,
    "rail_fish_angle": 1.50,
    "rail_web_top_from_top_mm": 0.80,
    "rail_web_bottom_from_top_mm": 1.25,
    "rail_web_thickness_mm": 0.35,
}

_CHAIR_PROTOTYPE_SHAPE_CACHE = {}


def chair_production_rail_profile():
    """Return the single fixed Code 75 profile used by this production stage."""
    profile = dict(CHAIR_CODE75_RAIL_PROFILE)
    fish = float(profile["rail_fish_angle"])
    head_half = 0.5 * float(profile["rail_head_width_mm"])
    foot_half = 0.5 * float(profile["rail_foot_width_mm"])
    profile["rail_head_depth_mm"] = float(profile["rail_web_top_from_top_mm"]) - head_half / fish
    profile["rail_foot_depth_mm"] = (
        float(profile["rail_depth_mm"])
        - float(profile["rail_web_bottom_from_top_mm"])
        - foot_half / fish
    )
    profile["rail_web_face_top_from_bottom_mm"] = (
        float(profile["rail_depth_mm"])
        - float(profile["rail_web_top_from_top_mm"])
        + 0.5 * float(profile["rail_web_thickness_mm"]) / fish
    )
    profile["rail_web_face_bottom_from_bottom_mm"] = (
        float(profile["rail_depth_mm"])
        - float(profile["rail_web_bottom_from_top_mm"])
        - 0.5 * float(profile["rail_web_thickness_mm"]) / fish
    )
    return profile


def default_chair_analysis_settings():
    """Return analytical and fixed-profile physical-chair settings."""
    return {
        "schema_version": CHAIR_ANALYSIS_SCHEMA_VERSION,
        "position_tolerance": 0.20,
        "footprint_clearance": 0.15,
        "timber_end_clearance": 0.50,
        "maximum_advisory_skew_degrees": 5.0,
        "maximum_unsupported_span": 15.0,
        "markers_visible": True,
        "protected_markers_visible": False,
        "footprints_visible": False,
        "cache_enabled": True,
        "model_support_recommendations_enabled": True,
        "model_support_auto_apply_enabled": True,
        "model_support_edge_margin": 0.15,
        "preferred_maximum_model_support_extension_per_side": 2.0,
        "future_chair_embed_depth": 0.20,
        "future_boolean_overlap_allowance": 0.05,
        "future_boolean_fuzzy_tolerance": 0.01,
        "rail_fit_clearance_per_side": 0.04,
        "physical_overlap_area_tolerance": 0.0025,
        "physical_rail_interference_clearance": 0.02,
        "physical_solids_visible": False,
        "unresolved_markers_visible": False,
    }


def normalise_chair_analysis_settings(settings=None):
    defaults = default_chair_analysis_settings()
    supplied = settings if isinstance(settings, dict) else {}
    result = dict(defaults)
    numeric_keys = (
        "position_tolerance", "footprint_clearance", "timber_end_clearance",
        "maximum_advisory_skew_degrees", "maximum_unsupported_span",
        "model_support_edge_margin", "preferred_maximum_model_support_extension_per_side",
        "future_chair_embed_depth", "future_boolean_overlap_allowance",
        "future_boolean_fuzzy_tolerance", "rail_fit_clearance_per_side",
        "physical_overlap_area_tolerance", "physical_rail_interference_clearance",
    )
    for key in numeric_keys:
        if key in supplied:
            try:
                result[key] = float(supplied[key])
            except Exception:
                raise ValueError("Chair setting {} must be numeric.".format(key.replace("_", " ")))
    limits = {
        "position_tolerance": (0.0, 5.0),
        "footprint_clearance": (0.0, 5.0),
        "timber_end_clearance": (0.0, 10.0),
        "maximum_advisory_skew_degrees": (0.0, 30.0),
        "maximum_unsupported_span": (1.0, 100.0),
        "model_support_edge_margin": (0.0, 3.0),
        "preferred_maximum_model_support_extension_per_side": (0.0, 10.0),
        "future_chair_embed_depth": (0.0, 5.0),
        "future_boolean_overlap_allowance": (0.0, 2.0),
        "future_boolean_fuzzy_tolerance": (0.0, 1.0),
        "rail_fit_clearance_per_side": (0.0, 0.50),
        "physical_overlap_area_tolerance": (0.0, 1.0),
        "physical_rail_interference_clearance": (0.0, 1.0),
    }
    for key, bounds in limits.items():
        value = float(result[key])
        if not math.isfinite(value) or value < bounds[0] or value > bounds[1]:
            raise ValueError(
                "Chair setting {} must be between {:.3f} and {:.3f}.".format(
                    key.replace("_", " "), bounds[0], bounds[1]
                )
            )
    for key in (
        "markers_visible", "protected_markers_visible", "footprints_visible",
        "cache_enabled", "model_support_recommendations_enabled",
        "model_support_auto_apply_enabled",
        "physical_solids_visible", "unresolved_markers_visible",
    ):
        result[key] = bool(supplied.get(key, defaults[key]))
    result["schema_version"] = CHAIR_ANALYSIS_SCHEMA_VERSION
    result["rail_profile_id"] = CHAIR_CODE75_RAIL_PROFILE["profile_id"]
    return result


def _chair_turnout_rail_records(config, host_data=None, parent_crossover_id=None, side=""):
    """Return the established rail midlines plus explicit gauge/outer faces."""
    cfg = dict(config or {})
    turnout_id = str(cfg.get("turnout_id") or "")
    if not turnout_id:
        raise ValueError("A chair rail source has no stable turnout identity.")
    if host_data is None:
        raise ValueError("A chair rail source has no host alignment data.")
    dimensions = rea_c10_dimensions(
        float(cfg.get("track_gauge", TURNOUT_DEFAULT_GAUGE)),
        float(cfg.get("flangeway", TURNOUT_DEFAULT_FLANGEWAY)),
    )
    named = dict(rea_c10_complete_rail_polylines(dimensions))
    records = []
    for gauge_name in sorted(name for name in named if name.endswith(" gauge face")):
        outer_name = gauge_name[:-len(" gauge face")] + " outer face"
        if outer_name not in named:
            continue
        base_name = gauge_name[:-len(" gauge face")]
        local_midline = _chair_resample_midline(named[gauge_name], named[outer_name])
        world_points = _turnout_map_polyline(
            host_data,
            float(cfg.get("toe_chainage") or 0.0),
            str(cfg.get("orientation") or TURNOUT_ORIENTATION_FACING),
            str(cfg.get("handing") or TURNOUT_HAND_LEFT),
            local_midline,
        )
        world_gauge = _turnout_map_polyline(
            host_data,
            float(cfg.get("toe_chainage") or 0.0),
            str(cfg.get("orientation") or TURNOUT_ORIENTATION_FACING),
            str(cfg.get("handing") or TURNOUT_HAND_LEFT),
            named[gauge_name],
        )
        world_outer = _turnout_map_polyline(
            host_data,
            float(cfg.get("toe_chainage") or 0.0),
            str(cfg.get("orientation") or TURNOUT_ORIENTATION_FACING),
            str(cfg.get("handing") or TURNOUT_HAND_LEFT),
            named[outer_name],
        )
        if len(world_points) < 2:
            continue
        rail_id = "{}:rail:{}".format(turnout_id, _chair_slug(base_name))
        records.append({
            "stable_identity": rail_id,
            "parent_turnout_identity": turnout_id,
            "parent_crossover_identity": str(parent_crossover_id or ""),
            "turnout_side": str(side or ""),
            "name": base_name,
            "rail_role": _chair_rail_role(base_name),
            "supported_feature": _chair_supported_feature(base_name),
            "points": [[float(point.x), float(point.y)] for point in world_points],
            "gauge_face_points": [[float(point.x), float(point.y)] for point in world_gauge],
            "outer_face_points": [[float(point.x), float(point.y)] for point in world_outer],
            "source_configuration": {
                "gauge_face": gauge_name,
                "outer_face": outer_name,
                "gauge_orientation_source": "mapped named turnout rail faces",
                "rail_geometry_revision": int(cfg.get("rail_geometry_revision") or TURNOUT_RAIL_GEOMETRY_REVISION),
            },
        })
    if not records:
        raise ValueError("No complete logical rail-face pairs were available for chair analysis.")
    return records


def _chair_connector_rail_records(doc, crossover_config):
    """Return connector rail midlines with an explicit gauge-side normal sign."""
    config = dict(crossover_config or {})
    identifier = str(config.get("crossover_id") or "")
    host_a = doc.getObject(str(config.get("host_a_object") or ""))
    host_b = doc.getObject(str(config.get("host_b_object") or ""))
    if host_a is None or host_b is None:
        return []
    solved = solve_rea_c10_crossover_geometry(
        doc,
        host_a,
        host_b,
        float(config.get("toe_chainage_a") or 0.0),
        arrangement=str(config.get("arrangement") or CROSSOVER_ARRANGEMENT_FACING),
        handing=str(config.get("handing") or CROSSOVER_HAND_AUTO),
        track_gauge=float(config.get("track_gauge", TURNOUT_DEFAULT_GAUGE)),
        flangeway=float(config.get("flangeway", TURNOUT_DEFAULT_FLANGEWAY)),
        minimum_radius=float(config.get("minimum_requested_radius") or CROSSOVER_DEFAULT_MINIMUM_RADIUS),
        ignored_crossover_id=identifier,
    )
    points = list(solved.get("connector", {}).get("points") or [])
    if len(points) < 2:
        return []
    gauge = float(config.get("track_gauge", TURNOUT_DEFAULT_GAUGE))
    records = []
    for label, offset, gauge_normal_sign in (
        ("left connecting rail", 0.5 * gauge, -1.0),
        ("right connecting rail", -0.5 * gauge, 1.0),
    ):
        offset_points = _crossover_offset_polyline(points, offset)
        records.append({
            "stable_identity": "{}:rail:{}".format(identifier, _chair_slug(label)),
            "parent_turnout_identity": "",
            "parent_crossover_identity": identifier,
            "turnout_side": "connector",
            "name": label,
            "rail_role": "crossover connecting rail",
            "supported_feature": "plain crossover connecting-road support",
            "points": [[float(point.x), float(point.y)] for point in offset_points],
            "source_configuration": {
                "source": "stored crossover geometry resolved analytically without rebuilding production shapes",
                "connector_geometry_signature": str(config.get("connector_geometry_signature") or ""),
                "gauge_normal_sign": gauge_normal_sign,
                "gauge_orientation_source": "connector offset sign relative to solved centre road",
            },
        })
    return records


def _chair_entity_objects(doc, entity_kind, entity_id):
    """Exclude production-chair objects from inherited analysis metadata passes."""
    excluded = {CHAIR_SOLID_ROLE, CHAIR_UNRESOLVED_MARKER_ROLE}
    return [
        obj for obj in _A8A7B11_CHAIR_ENTITY_OBJECTS(doc, entity_kind, entity_id)
        if object_string_property(obj, "GeneratedRole", "") not in excluded
    ]


def _chair_auxiliary_objects(doc, entity_kind, entity_id, roles=None):
    kind = str(entity_kind or "").lower()
    property_name = TURNOUT_ID_PROPERTY if kind == "turnout" else CROSSOVER_ID_PROPERTY
    wanted = set(roles or (CHAIR_SOLID_ROLE, CHAIR_UNRESOLVED_MARKER_ROLE))
    return [
        obj for obj in list(doc.Objects)
        if object_string_property(obj, property_name, "") == str(entity_id)
        and object_string_property(obj, "GeneratedRole", "") in wanted
    ]


def _chair_solid_object(doc, entity_kind, entity_id):
    objects = _chair_auxiliary_objects(doc, entity_kind, entity_id, (CHAIR_SOLID_ROLE,))
    if len(objects) > 1:
        raise ValueError("{} {} has duplicate supported-chair solid objects.".format(str(entity_kind).capitalize(), entity_id))
    return objects[0] if objects else None


def _chair_unresolved_marker_object(doc, entity_kind, entity_id):
    objects = _chair_auxiliary_objects(doc, entity_kind, entity_id, (CHAIR_UNRESOLVED_MARKER_ROLE,))
    if len(objects) > 1:
        raise ValueError("{} {} has duplicate unresolved-chair marker objects.".format(str(entity_kind).capitalize(), entity_id))
    return objects[0] if objects else None


def clear_chair_analysis_display(doc, entity_kind, entity_id):
    removed = _A8A7B11_CLEAR_CHAIR_ANALYSIS_DISPLAY(doc, entity_kind, entity_id)
    marker = _chair_unresolved_marker_object(doc, entity_kind, entity_id)
    if marker is not None:
        try:
            doc.removeObject(str(marker.Name))
            removed += 1
        except Exception:
            pass
    return removed


def _chair_mark_solid_stale(doc, entity_kind, entity_id, reason="Chair analysis or railway geometry changed."):
    obj = _chair_solid_object(doc, entity_kind, entity_id)
    if obj is None:
        return False
    props = [
        ensure_property(obj, "App::PropertyString", CHAIR_SOLID_STATUS_PROPERTY, "Physical chairs", "Current supported-chair solid status"),
        ensure_property(obj, "App::PropertyString", CHAIR_PHYSICAL_FIT_STATUS_PROPERTY, "Physical chairs", "Current physical fit-validation status"),
    ]
    _set_persistent_property_if_changed(obj, CHAIR_SOLID_STATUS_PROPERTY, CHAIR_SOLID_STATUS_STALE)
    _set_persistent_property_if_changed(obj, CHAIR_PHYSICAL_FIT_STATUS_PROPERTY, str(reason))
    set_read_only(obj, props)
    try:
        obj.ViewObject.Visibility = False
    except Exception:
        pass
    return True


def invalidate_chair_analysis(doc, entity_kind, entity_id, remove_display=True):
    updated = _A8A7B11_INVALIDATE_CHAIR_ANALYSIS(doc, entity_kind, entity_id, remove_display)
    _chair_mark_solid_stale(doc, entity_kind, entity_id)
    return updated


def _chair_unit(vector):
    x, y = float(vector[0]), float(vector[1])
    length = math.hypot(x, y)
    if length <= 1.0e-12:
        return None
    return x / length, y / length


def _chair_gauge_normal_for_position(rail, position):
    support = position.get("centre_point") or (0.0, 0.0)
    gauge_points = list(rail.get("gauge_face_points") or [])
    outer_points = list(rail.get("outer_face_points") or [])
    if len(gauge_points) >= 2 and len(outer_points) >= 2:
        gauge = _chair_project_to_prepared_polyline(
            support, _chair_prepare_polyline_projection(gauge_points)
        )
        outer = _chair_project_to_prepared_polyline(
            support, _chair_prepare_polyline_projection(outer_points)
        )
        if gauge is not None and outer is not None:
            vector = (float(gauge[2][0]) - float(outer[2][0]), float(gauge[2][1]) - float(outer[2][1]))
            normal = _chair_unit(vector)
            if normal is not None:
                return normal, "named gauge and outer rail faces"
    source = dict(rail.get("source_configuration") or {})
    if "gauge_normal_sign" in source:
        tangent = _chair_unit(position.get("local_rail_tangent") or (0.0, 0.0))
        if tangent is not None:
            left = (-tangent[1], tangent[0])
            sign = 1.0 if float(source.get("gauge_normal_sign") or 0.0) >= 0.0 else -1.0
            return (sign * left[0], sign * left[1]), "connector rail offset sign"
    return None, "gauge side is not explicit"


def _chair_s1_body_dimensions(chair_code, settings=None):
    """Return source-dimensional local body data around the rail centreline."""
    settings = normalise_chair_analysis_settings(settings)
    profile = chair_production_rail_profile()
    inch = 25.4 / TURNOUT_DEFAULT_SCALE
    code = int(chair_code or 0)
    if code not in CHAIR_SOLID_SUPPORTED_CODES:
        raise ValueError("Chair code {} has no supported physical body in this stage.".format(code))
    halfwide_inches = 5.0 if code == 7 else 4.0
    seat_halfwide_inches = 4.9375 if code == 7 else 3.9375
    inlong = 5.25 * inch
    outlong = 9.25 * inch
    gauge_face_x = -0.5 * float(profile["rail_head_width_mm"])
    rail_foot_half = 0.5 * float(profile["rail_foot_width_mm"])
    fit = float(settings["rail_fit_clearance_per_side"])
    edge_thickness = 0.375 * inch
    plinth_thickness = 0.875 * inch
    seat_top = 1.75 * inch
    outer_jaw_top = seat_top + float(profile["rail_web_face_top_from_bottom_mm"]) - (1.0 / 32.0) * inch
    inner_jaw_top = (4.0 + 23.0 / 32.0) * inch
    inner_depth = 2.0 * inch
    outer_depth = (1.0 + 15.0 / 16.0) * inch
    outer_jaw_face = gauge_face_x + (3.0 + 15.0 / 16.0) * inch
    outer_top_height_inches = outer_jaw_top / inch
    outer_rib_width_mid_inches = 5.0 / 8.0 + (outer_top_height_inches - (2.0 + 7.0 / 8.0)) / 17.5
    outer_rib_width_seat_inches = outer_rib_width_mid_inches + ((2.0 + 7.0 / 8.0) - 1.75) / 9.0
    jaw_half_width = (1.0 + 3.0 / 8.0 + outer_rib_width_seat_inches) * inch
    return {
        "chair_code": code,
        "chair_label": "S1J" if code == 7 else "S1",
        "base_x_min": gauge_face_x - inlong,
        "base_x_max": gauge_face_x + outlong,
        "base_y_half": halfwide_inches * inch,
        "edge_thickness": edge_thickness,
        "plinth_thickness": plinth_thickness,
        "seat_top_z": seat_top,
        "seat_y_half": seat_halfwide_inches * inch,
        "inner_jaw_top_z": inner_jaw_top,
        "outer_jaw_top_z": outer_jaw_top,
        "inner_jaw_x_min": gauge_face_x - fit - inner_depth,
        "inner_jaw_x_max": gauge_face_x - fit,
        "outer_jaw_x_min": outer_jaw_face,
        "outer_jaw_x_max": outer_jaw_face + outer_depth,
        "outer_jaw_face_from_gauge_face": (3.0 + 15.0 / 16.0) * inch,
        "jaw_y_half": jaw_half_width,
        "rail_foot_half": rail_foot_half,
        "rail_fit_clearance_per_side": fit,
        "source_basis": list(CHAIR_SOLID_SOURCE_BASIS),
    }


def _chair_physical_top_z(doc, entity_kind, config):
    values = []
    try:
        configured = float((config or {}).get("template_thickness") or 0.0)
        if configured > 0.0:
            values.append(configured)
    except Exception:
        pass
    entity_id = str((config or {}).get("turnout_id") or (config or {}).get("crossover_id") or "")
    for obj in _chair_entity_objects(doc, entity_kind, entity_id):
        try:
            value = quantity_value(obj, "TemplateThickness", 0.0)
            if value > 0.0:
                values.append(float(value))
        except Exception:
            pass
    return max(values) if values else float(TEMPLATE_THICKNESS)


def _chair_supported_physical_position(position):
    code = int(position.get("chair_code") or 0)
    status = str(position.get("assignment_status") or "")
    if bool(position.get("deliberate_omission")):
        return False, "shared support position deliberately has no separate chair body"
    if bool(position.get("special_assignment_deferred")):
        return False, "special chair assignment remains analytical"
    if status != CHAIR_ASSIGNMENT_CONFIRMED:
        return False, "chair assignment is not confirmed for physical generation"
    family = str(position.get("chair_family") or "")
    if family not in (CHAIR_FAMILY_ORDINARY, CHAIR_FAMILY_JOINT):
        return False, "chair family {} requires a dedicated physical definition".format(family or "unresolved")
    if code not in CHAIR_SOLID_SUPPORTED_CODES:
        return False, "chair type {} is not in the supported S1/S1J increment".format(position.get("chair_code_label") or code or "unresolved")
    if str(position.get("chair_footprint_parameters", {}).get("dimension_classification") or "") != CHAIR_CLASS_SOURCE:
        return False, "chair footprint is not source-dimensional"
    return True, "supported source-dimensional ordinary chair body"


def _chair_instance_from_position(position, rail, timber, settings, base_z):
    supported, reason = _chair_supported_physical_position(position)
    if not supported:
        return None, reason
    tangent = _chair_unit(position.get("local_rail_tangent") or (0.0, 0.0))
    if tangent is None:
        return None, "local rail tangent is unresolved"
    gauge_normal, normal_source = _chair_gauge_normal_for_position(rail, position)
    if gauge_normal is None:
        return None, "gauge side is unresolved"
    if abs(tangent[0] * gauge_normal[0] + tangent[1] * gauge_normal[1]) > 1.0e-3:
        return None, "gauge normal is not perpendicular to the local rail tangent"
    outward = (-gauge_normal[0], -gauge_normal[1])
    local_y = (-outward[1], outward[0])
    dimensions = _chair_s1_body_dimensions(position.get("chair_code"), settings)
    centre = _chair_xy(position.get("centre_point") or (0.0, 0.0))
    corners = []
    for local_x, local_y_value in (
        (dimensions["base_x_min"], -dimensions["base_y_half"]),
        (dimensions["base_x_max"], -dimensions["base_y_half"]),
        (dimensions["base_x_max"], dimensions["base_y_half"]),
        (dimensions["base_x_min"], dimensions["base_y_half"]),
    ):
        corners.append([
            centre[0] + local_x * outward[0] + local_y_value * local_y[0],
            centre[1] + local_x * outward[1] + local_y_value * local_y[1],
        ])
    angle = math.degrees(math.atan2(outward[1], outward[0]))
    return {
        "chair_position_identity": str(position.get("stable_chair_position_identity") or ""),
        "chair_code": int(position.get("chair_code") or 0),
        "chair_label": str(position.get("chair_code_label") or dimensions["chair_label"]),
        "chair_subtype": str(position.get("chair_subtype") or ""),
        "chair_family": str(position.get("chair_family") or ""),
        "assignment_status": str(position.get("assignment_status") or ""),
        "timber_identity": str(position.get("timber_identity") or ""),
        "timber_identifier": str(position.get("timber_identifier") or ""),
        "rail_identity": str(position.get("rail_identity") or ""),
        "rail_name": str(position.get("rail_name") or ""),
        "rail_role": str(position.get("rail_role") or ""),
        "centre_point": [centre[0], centre[1]],
        "base_z": float(base_z),
        "rail_bottom_z": float(base_z + dimensions["seat_top_z"]),
        "rotation_degrees": float(angle),
        "outward_axis": [outward[0], outward[1]],
        "local_y_axis": [local_y[0], local_y[1]],
        "local_rail_tangent": [tangent[0], tangent[1]],
        "gauge_normal": [gauge_normal[0], gauge_normal[1]],
        "gauge_normal_source": normal_source,
        "physical_footprint_polygon": corners,
        "body_dimensions": dimensions,
        "key_direction_resolved": int(position.get("key_direction_sign") or 0) != 0,
        "key_direction_sign": int(position.get("key_direction_sign") or 0),
        "key_orientation": str(position.get("key_orientation") or ""),
        "body_includes_key": False,
        "body_includes_loose_jaw_or_plug": False,
    }, ""



CHAIR_MODEL_SUPPORT_INCREMENT_MM = 0.05


def _chair_round_model_support_extension(value):
    """Round a positive support extension upwards to a stable printable step."""
    amount = max(0.0, float(value or 0.0))
    if amount <= 1.0e-9:
        return 0.0
    step = float(CHAIR_MODEL_SUPPORT_INCREMENT_MM)
    return float(math.ceil((amount - 1.0e-12) / step) * step)


def _chair_physical_model_support_adjustments(instances, timber_records, settings=None):
    """Derive model-only timber widening from the actual rotated chair bodies."""
    settings = normalise_chair_analysis_settings(settings)
    timbers = {str(item.get("stable_identity") or ""): item for item in timber_records}
    margin = float(settings.get("model_support_edge_margin") or 0.0)
    limit = float(settings.get("preferred_maximum_model_support_extension_per_side") or 0.0)
    auto_enabled = bool(settings.get("model_support_recommendations_enabled")) and bool(
        settings.get("model_support_auto_apply_enabled", True)
    )
    grouped = {}
    for instance in list(instances or []):
        timber_id = str(instance.get("timber_identity") or "")
        timber = timbers.get(timber_id)
        if timber is None:
            continue
        fit = _chair_footprint_fit_measurements(
            instance.get("physical_footprint_polygon") or [], timber
        )
        if fit is None:
            continue
        approach_required = max(0.0, margin - float(fit.get("approach_side_clearance") or 0.0))
        exit_required = max(0.0, margin - float(fit.get("exit_side_clearance") or 0.0))
        near_end_required = max(0.0, -float(fit.get("near_end_clearance") or 0.0))
        far_end_required = max(0.0, -float(fit.get("far_end_clearance") or 0.0))
        if max(approach_required, exit_required, near_end_required, far_end_required) <= 1.0e-9:
            continue
        record = grouped.setdefault(timber_id, {
            "timber_identity": timber_id,
            "timber_identifier": str(instance.get("timber_identifier") or timber.get("identifier") or timber_id),
            "required_approach_side_extension": 0.0,
            "required_exit_side_extension": 0.0,
            "unresolved_near_end_extension": 0.0,
            "unresolved_far_end_extension": 0.0,
            "approach_side_extension": 0.0,
            "exit_side_extension": 0.0,
            "total_width_increase": 0.0,
            "maximum_extension_per_side": 0.0,
            "chair_position_identities": [],
            "auto_apply_enabled": auto_enabled,
            "configured_limit_per_side": limit,
            "model_support_edge_margin": margin,
            "limit_exceeded": False,
            "applied": False,
            "prototype_timber_width_unchanged": True,
        })
        record["required_approach_side_extension"] = max(
            float(record["required_approach_side_extension"]), approach_required
        )
        record["required_exit_side_extension"] = max(
            float(record["required_exit_side_extension"]), exit_required
        )
        record["unresolved_near_end_extension"] = max(
            float(record["unresolved_near_end_extension"]), near_end_required
        )
        record["unresolved_far_end_extension"] = max(
            float(record["unresolved_far_end_extension"]), far_end_required
        )
        record["chair_position_identities"].append(
            str(instance.get("chair_position_identity") or "")
        )

    result = []
    for record in grouped.values():
        required_approach = _chair_round_model_support_extension(
            record["required_approach_side_extension"]
        )
        required_exit = _chair_round_model_support_extension(
            record["required_exit_side_extension"]
        )
        maximum = max(required_approach, required_exit)
        limit_exceeded = auto_enabled and maximum > limit + 1.0e-9
        can_apply = auto_enabled and not limit_exceeded
        record["required_approach_side_extension"] = required_approach
        record["required_exit_side_extension"] = required_exit
        record["maximum_extension_per_side"] = maximum
        record["limit_exceeded"] = bool(limit_exceeded)
        record["applied"] = bool(can_apply and maximum > 1.0e-9)
        record["approach_side_extension"] = required_approach if record["applied"] else 0.0
        record["exit_side_extension"] = required_exit if record["applied"] else 0.0
        record["total_width_increase"] = (
            float(record["approach_side_extension"]) + float(record["exit_side_extension"])
        )
        record["chair_position_identities"] = sorted(set(
            value for value in record["chair_position_identities"] if value
        ))
        result.append(record)
    return sorted(result, key=lambda item: item["timber_identity"])


def _chair_transform_timber_for_model_support(timber, adjustment):
    """Return an effective timber record enlarged only along its width axis."""
    record = copy.deepcopy(dict(timber or {}))
    approach = float((adjustment or {}).get("approach_side_extension") or 0.0)
    exit_side = float((adjustment or {}).get("exit_side_extension") or 0.0)
    if approach <= 1.0e-12 and exit_side <= 1.0e-12:
        return record
    centre = _chair_xy(record.get("centre") or (0.0, 0.0))
    width_axis = _chair_unit(record.get("width_axis") or (1.0, 0.0))
    length_axis = _chair_unit(record.get("length_axis") or (0.0, 1.0))
    old_width = float(record.get("width") or 0.0)
    if width_axis is None or length_axis is None or old_width <= 1.0e-9:
        return record
    old_half = 0.5 * old_width
    new_half = old_half + 0.5 * (approach + exit_side)
    centre_shift = 0.5 * (exit_side - approach)
    new_centre = (
        centre[0] + centre_shift * width_axis[0],
        centre[1] + centre_shift * width_axis[1],
    )
    scale = new_half / old_half

    determinant = length_axis[0] * width_axis[1] - length_axis[1] * width_axis[0]
    if abs(determinant) <= 1.0e-9:
        return record

    def transform_point(point):
        px, py = _chair_xy(point)
        dx, dy = px - centre[0], py - centre[1]
        longitudinal = (dx * width_axis[1] - dy * width_axis[0]) / determinant
        transverse = (-dx * length_axis[1] + dy * length_axis[0]) / determinant
        return [
            new_centre[0] + longitudinal * length_axis[0] + transverse * scale * width_axis[0],
            new_centre[1] + longitudinal * length_axis[1] + transverse * scale * width_axis[1],
        ]

    for key in ("outline_polygon", "collision_polygon", "support_zone_polygon"):
        points = list(record.get(key) or [])
        if points:
            record[key] = [transform_point(point) for point in points]
    for key in ("near_end_segment", "far_end_segment"):
        points = list(record.get(key) or [])
        if points:
            record[key] = [transform_point(point) for point in points]
    side_segments = []
    for segment in list(record.get("side_segments") or []):
        side_segments.append([transform_point(point) for point in list(segment or [])])
    if side_segments:
        record["side_segments"] = side_segments
    if record.get("outline_polygon"):
        record["collision_polygon"] = [
            [float(point[0]), float(point[1])]
            for point in _timber_convex_hull(record["outline_polygon"])
        ]
        record["bounding_box"] = list(_timber_bbox(record["collision_polygon"]))
    record["prototype_width"] = old_width
    record["prototype_centre"] = [centre[0], centre[1]]
    record["centre"] = [new_centre[0], new_centre[1]]
    record["width"] = old_width + approach + exit_side
    record["model_support_adjusted"] = True
    record["model_support_adjustment"] = copy.deepcopy(dict(adjustment or {}))
    return record


def _chair_apply_physical_model_support(plan, timber_records, settings=None):
    adjustments = list((plan or {}).get("model_timber_support_adjustments") or [])
    by_timber = {
        str(item.get("timber_identity") or ""): item
        for item in adjustments if bool(item.get("applied"))
    }
    effective = []
    for timber in list(timber_records or []):
        adjustment = by_timber.get(str(timber.get("stable_identity") or ""))
        effective.append(
            _chair_transform_timber_for_model_support(timber, adjustment)
            if adjustment is not None else copy.deepcopy(dict(timber or {}))
        )
    return effective, adjustments

def _chair_build_solid_plan(doc, entity_kind, config, analysis_result, rail_records, timber_records, settings=None):
    settings = normalise_chair_analysis_settings(settings)
    kind = str(entity_kind or "").lower()
    entity_id = str(config.get("turnout_id") or config.get("crossover_id") or "")
    rails = {str(item.get("stable_identity") or ""): item for item in rail_records}
    timbers = {str(item.get("stable_identity") or ""): item for item in timber_records}
    base_z = _chair_physical_top_z(doc, kind, config) - float(settings["future_chair_embed_depth"])
    instances = []
    analytical_only = []
    for position in list((analysis_result or {}).get("positions") or []):
        rail = rails.get(str(position.get("rail_identity") or ""))
        timber = timbers.get(str(position.get("timber_identity") or ""))
        if rail is None or timber is None:
            analytical_only.append({
                "chair_position_identity": str(position.get("stable_chair_position_identity") or ""),
                "chair_label": str(position.get("chair_code_label") or ""),
                "reason": "rail or timber source record is missing",
                "unresolved_special": True,
            })
            continue
        instance, reason = _chair_instance_from_position(position, rail, timber, settings, base_z)
        if instance is None:
            analytical_only.append({
                "chair_position_identity": str(position.get("stable_chair_position_identity") or ""),
                "chair_label": str(position.get("chair_code_label") or ""),
                "reason": reason,
                "unresolved_special": bool(position.get("special_assignment_deferred")) or not bool(position.get("deliberate_omission")),
                "deliberate_omission": bool(position.get("deliberate_omission")),
                "chair_family": str(position.get("chair_family") or ""),
                "timber_identity": str(position.get("timber_identity") or ""),
                "rail_identity": str(position.get("rail_identity") or ""),
            })
        else:
            instances.append(instance)
    instances.sort(key=lambda item: item["chair_position_identity"])
    analytical_only.sort(key=lambda item: item["chair_position_identity"])
    model_support_adjustments = _chair_physical_model_support_adjustments(
        instances, timber_records, settings
    )
    payload = {
        "schema_version": CHAIR_SOLID_SCHEMA_VERSION,
        "prototype_revision": CHAIR_SOLID_PROTOTYPE_REVISION,
        "entity_kind": kind,
        "entity_id": entity_id,
        "source_analysis_signature": str((analysis_result or {}).get("geometry_signature") or ""),
        "rail_profile": chair_production_rail_profile(),
        "settings": {
            "rail_fit_clearance_per_side": float(settings["rail_fit_clearance_per_side"]),
            "embed_depth": float(settings["future_chair_embed_depth"]),
            "physical_overlap_area_tolerance": float(settings["physical_overlap_area_tolerance"]),
            "physical_rail_interference_clearance": float(settings["physical_rail_interference_clearance"]),
            "model_support_auto_apply_enabled": bool(settings.get("model_support_auto_apply_enabled", True)),
            "model_support_edge_margin": float(settings.get("model_support_edge_margin") or 0.0),
            "maximum_model_support_extension_per_side": float(settings.get("preferred_maximum_model_support_extension_per_side") or 0.0),
            "model_support_increment_mm": float(CHAIR_MODEL_SUPPORT_INCREMENT_MM),
        },
        "instances": instances,
        "analytical_only": analytical_only,
        "model_timber_support_adjustments": model_support_adjustments,
        "model_timber_support_changes_applied": any(bool(item.get("applied")) for item in model_support_adjustments),
    }
    signature_payload = dict(payload)
    signature_payload["instances"] = [
        {
            "id": item["chair_position_identity"],
            "code": item["chair_code"],
            "centre": [round(float(value), 6) for value in item["centre_point"]],
            "z": round(float(item["base_z"]), 6),
            "angle": round(float(item["rotation_degrees"]), 8),
            "footprint": [[round(float(value), 6) for value in point] for point in item["physical_footprint_polygon"]],
        }
        for item in instances
    ]
    payload["solid_signature"] = hashlib.sha256(
        json.dumps(signature_payload, sort_keys=True, separators=(",", ":")).encode("utf-8")
    ).hexdigest()
    return payload


def _chair_polyline_polygon_minimum_distance(points, polygon):
    polyline = [_chair_xy(point) for point in list(points or [])]
    outline = [_chair_xy(point) for point in list(polygon or [])]
    if len(polyline) < 2 or len(outline) < 3:
        return float("inf")
    for point in polyline:
        if _timber_point_in_convex_polygon(point, outline, tolerance=1.0e-9):
            return 0.0
    minimum = float("inf")
    edges = list(zip(outline, outline[1:] + outline[:1]))
    for first, second in zip(polyline[:-1], polyline[1:]):
        for edge_first, edge_second in edges:
            distance, _a, _b = _timber_segment_distance(first, second, edge_first, edge_second)
            minimum = min(minimum, float(distance))
            if minimum <= 1.0e-12:
                return 0.0
    return minimum


def _chair_physical_finding(code, severity, message, instance=None, related=None):
    item = {
        "code": str(code),
        "severity": str(severity),
        "message": str(message),
        "chair_position_identity": str((instance or {}).get("chair_position_identity") or ""),
        "timber_identity": str((instance or {}).get("timber_identity") or ""),
        "rail_identity": str((instance or {}).get("rail_identity") or ""),
    }
    if related:
        item["related_chair_position_identity"] = str(related.get("chair_position_identity") or "")
    return item


def _chair_validate_solid_plan(plan, rail_records, timber_records, settings=None):
    """Validate generated-body footprints without changing FreeCAD geometry."""
    started = time.perf_counter()
    settings = normalise_chair_analysis_settings(settings)
    rails = {str(item.get("stable_identity") or ""): item for item in rail_records}
    effective_timber_records, support_adjustments = _chair_apply_physical_model_support(
        plan, timber_records, settings
    )
    timbers = {str(item.get("stable_identity") or ""): item for item in effective_timber_records}
    findings = []
    for adjustment in support_adjustments:
        if bool(adjustment.get("limit_exceeded")):
            findings.append(_chair_physical_finding(
                "CHAIR_MODEL_SUPPORT_LIMIT_EXCEEDED", CHAIR_SEVERITY_CRITICAL,
                "The required model timber widening is {:.3f} mm on one side, above the configured {:.3f} mm automatic limit.".format(
                    float(adjustment.get("maximum_extension_per_side") or 0.0),
                    float(adjustment.get("configured_limit_per_side") or 0.0),
                ),
                {"timber_identity": adjustment.get("timber_identity") or ""},
            ))
    profile = chair_production_rail_profile()
    rail_half = 0.5 * max(float(profile["rail_head_width_mm"]), float(profile["rail_foot_width_mm"]))
    for instance in list(plan.get("instances") or []):
        timber = timbers.get(instance["timber_identity"])
        rail = rails.get(instance["rail_identity"])
        if timber is None:
            findings.append(_chair_physical_finding(
                "CHAIR_TIMBER_RECORD_MISSING", CHAIR_SEVERITY_CRITICAL,
                "The supporting timber record is missing.", instance,
            ))
            continue
        if rail is None:
            findings.append(_chair_physical_finding(
                "CHAIR_RAIL_RECORD_MISSING", CHAIR_SEVERITY_CRITICAL,
                "The intended rail record is missing.", instance,
            ))
            continue
        support = _chair_xy(instance["centre_point"])
        timber_polygon = list(timber.get("outline_polygon") or timber.get("collision_polygon") or [])
        if not _timber_point_in_convex_polygon(support, timber_polygon, tolerance=float(settings["position_tolerance"])):
            findings.append(_chair_physical_finding(
                "CHAIR_CENTRE_OUTSIDE_TIMBER", CHAIR_SEVERITY_CRITICAL,
                "The chair centre is outside its intended timber.", instance,
            ))
        footprint = list(instance.get("physical_footprint_polygon") or [])
        outside = [
            point for point in footprint
            if not _timber_point_in_convex_polygon(point, timber_polygon, tolerance=1.0e-7)
        ]
        if outside:
            findings.append(_chair_physical_finding(
                "CHAIR_BODY_EXTENDS_BEYOND_TIMBER", CHAIR_SEVERITY_CRITICAL,
                "The source-dimensional chair body extends beyond its supporting timber.", instance,
            ))
        fit = _chair_footprint_fit_measurements(footprint, timber)
        if fit is not None:
            instance["timber_fit_measurements"] = fit
            if min(float(fit["end_clearance"]), float(fit["side_clearance"])) < -1.0e-7:
                findings.append(_chair_physical_finding(
                    "CHAIR_BODY_UNSUPPORTED", CHAIR_SEVERITY_CRITICAL,
                    "The chair body bridges an unsupported timber edge.", instance,
                ))
            elif float(fit["end_clearance"]) < float(settings["timber_end_clearance"]):
                findings.append(_chair_physical_finding(
                    "CHAIR_END_CLEARANCE_BELOW_PREFERENCE", CHAIR_SEVERITY_ADVISORY,
                    "The chair body fits, but its timber-end clearance is below the configured preference.", instance,
                ))
        tangent = _chair_unit(instance.get("local_rail_tangent") or (0.0, 0.0))
        gauge_normal = _chair_unit(instance.get("gauge_normal") or (0.0, 0.0))
        projected = _chair_project_to_prepared_polyline(
            support, _chair_prepare_polyline_projection(rail.get("points") or [])
        )
        if projected is None or float(projected[0]) > float(settings["position_tolerance"]) + 1.0e-9:
            findings.append(_chair_physical_finding(
                "CHAIR_NOT_CENTRED_ON_INTENDED_RAIL", CHAIR_SEVERITY_CRITICAL,
                "The chair centre is not within tolerance of its assigned rail centreline.", instance,
            ))
        elif tangent is not None:
            projected_tangent = _chair_unit(projected[3])
            alignment = abs(
                tangent[0] * projected_tangent[0] + tangent[1] * projected_tangent[1]
            ) if projected_tangent is not None else 0.0
            minimum_alignment = math.cos(math.radians(float(settings["maximum_advisory_skew_degrees"])))
            if alignment + 1.0e-12 < minimum_alignment:
                findings.append(_chair_physical_finding(
                    "CHAIR_TANGENT_MISMATCH", CHAIR_SEVERITY_CRITICAL,
                    "The chair orientation does not match the tangent of its assigned rail.", instance,
                ))
        if tangent is None or gauge_normal is None or abs(tangent[0] * gauge_normal[0] + tangent[1] * gauge_normal[1]) > 1.0e-3:
            findings.append(_chair_physical_finding(
                "CHAIR_ORIENTATION_INVALID", CHAIR_SEVERITY_CRITICAL,
                "The chair body cannot be aligned unambiguously to the intended rail tangent and gauge side.", instance,
            ))
        dimensions = dict(instance.get("body_dimensions") or {})
        clearance = float(dimensions.get("rail_fit_clearance_per_side") or 0.0)
        inner_gap = abs(float(dimensions.get("inner_jaw_x_max") or 0.0)) - 0.5 * float(profile["rail_foot_width_mm"])
        outer_gap = float(dimensions.get("outer_jaw_x_min") or 0.0) - 0.5 * float(profile["rail_foot_width_mm"])
        if inner_gap + 1.0e-9 < clearance or outer_gap + 1.0e-9 < clearance:
            findings.append(_chair_physical_finding(
                "CODE75_RAIL_FOOT_DOES_NOT_FIT", CHAIR_SEVERITY_CRITICAL,
                "The fixed Templot Code 75 rail foot does not fit inside the body jaw envelope.", instance,
            ))
        for other_id, other_rail in rails.items():
            if other_id == instance["rail_identity"]:
                continue
            minimum = _chair_polyline_polygon_minimum_distance(
                other_rail.get("points") or [], footprint
            )
            if minimum <= rail_half + float(settings["physical_rail_interference_clearance"]):
                findings.append(_chair_physical_finding(
                    "CHAIR_INTERSECTS_INCOMPATIBLE_RAIL", CHAIR_SEVERITY_CRITICAL,
                    "The chair body footprint reaches an incompatible neighbouring rail.", instance,
                ))
                break
    instances = list(plan.get("instances") or [])
    overlap_tolerance = float(settings["physical_overlap_area_tolerance"])
    for first_index, first in enumerate(instances):
        polygon_a = list(first.get("physical_footprint_polygon") or [])
        bbox_a = _chair_bbox_for_points(polygon_a)
        for second in instances[first_index + 1:]:
            polygon_b = list(second.get("physical_footprint_polygon") or [])
            if not _chair_bbox_overlap(bbox_a, _chair_bbox_for_points(polygon_b)):
                continue
            overlap = _timber_convex_intersection(polygon_a, polygon_b)
            area = abs(_timber_polygon_area(overlap)) if len(overlap) >= 3 else 0.0
            if area > overlap_tolerance:
                findings.append(_chair_physical_finding(
                    "CHAIR_BODY_OVERLAP", CHAIR_SEVERITY_CRITICAL,
                    "Two independently generated chair bodies overlap improperly by {:.4f} mm².".format(area),
                    first, second,
                ))
    for adjustment in support_adjustments:
        if bool(adjustment.get("applied")):
            findings.append(_chair_physical_finding(
                "CHAIR_MODEL_TIMBER_WIDENING_APPLIED", CHAIR_SEVERITY_INFORMATION,
                "Effective model support widened {} by {:.3f} mm on the approach side and {:.3f} mm on the exit side; the prototype timber reference is unchanged.".format(
                    adjustment.get("timber_identifier") or adjustment.get("timber_identity") or "the timber",
                    float(adjustment.get("approach_side_extension") or 0.0),
                    float(adjustment.get("exit_side_extension") or 0.0),
                ),
                {"timber_identity": adjustment.get("timber_identity") or ""},
            ))
    counts = {}
    for finding in findings:
        severity = str(finding.get("severity") or "")
        counts[severity] = counts.get(severity, 0) + 1
    critical = int(counts.get(CHAIR_SEVERITY_CRITICAL, 0))
    unresolved_special = sum(
        1 for item in list(plan.get("analytical_only") or [])
        if bool(item.get("unresolved_special")) and not bool(item.get("deliberate_omission"))
    )
    key_unresolved = sum(1 for item in instances if not bool(item.get("key_direction_resolved")))
    blockers = []
    if critical:
        blockers.append("{} physical-fit failure(s)".format(critical))
    if unresolved_special:
        blockers.append("{} special or unsupported chair position(s) remain analytical".format(unresolved_special))
    if key_unresolved:
        blockers.append("{} generated chair body position(s) still require a key-direction policy".format(key_unresolved))
    blockers.append("This staged body scope excludes keys, loose jaws or plugs, and dedicated special-chair solids.")
    status = CHAIR_SOLID_STATUS_FIT_FAILED if critical else CHAIR_SOLID_STATUS_FIT_VALIDATED
    return {
        "status": status,
        "physical_fit_validated": critical == 0,
        "findings": findings,
        "severity_counts": counts,
        "physical_fit_failure_count": critical,
        "unresolved_special_count": unresolved_special,
        "key_direction_unresolved_count": key_unresolved,
        "model_timber_support_adjustments": support_adjustments,
        "model_timber_support_changes_applied": any(bool(item.get("applied")) for item in support_adjustments),
        "model_timber_support_adjusted_count": sum(1 for item in support_adjustments if bool(item.get("applied"))),
        "maximum_model_support_extension_per_side": max([
            float(item.get("maximum_extension_per_side") or 0.0) for item in support_adjustments
        ] or [0.0]),
        "readiness_blockers": blockers,
        "production_ready": False,
        "validation_time_ms": (time.perf_counter() - started) * 1000.0,
    }


def _chair_make_s1_prototype_shape(chair_code, settings=None):
    settings = normalise_chair_analysis_settings(settings)
    dimensions = _chair_s1_body_dimensions(chair_code, settings)
    cache_key = (
        CHAIR_SOLID_PROTOTYPE_REVISION,
        int(chair_code),
        CHAIR_CODE75_RAIL_PROFILE["profile_id"],
        round(float(settings["rail_fit_clearance_per_side"]), 6),
    )
    cached = _CHAIR_PROTOTYPE_SHAPE_CACHE.get(cache_key)
    if cached is not None:
        try:
            return cached.copy(), True
        except Exception:
            pass
    base_length = dimensions["base_x_max"] - dimensions["base_x_min"]
    base_width = 2.0 * dimensions["base_y_half"]
    edge = Part.makeBox(
        base_length, base_width, dimensions["edge_thickness"],
        App.Vector(dimensions["base_x_min"], -dimensions["base_y_half"], 0.0),
    )
    inset = 25.4 / TURNOUT_DEFAULT_SCALE
    plinth_x_min = dimensions["base_x_min"] + inset
    plinth_x_max = dimensions["base_x_max"] - inset
    plinth_y_half = max(0.05, dimensions["base_y_half"] - inset)
    plinth = Part.makeBox(
        plinth_x_max - plinth_x_min,
        2.0 * plinth_y_half,
        dimensions["plinth_thickness"] - dimensions["edge_thickness"],
        App.Vector(plinth_x_min, -plinth_y_half, dimensions["edge_thickness"]),
    )
    seat_x_min = max(plinth_x_min, dimensions["inner_jaw_x_min"])
    seat_x_max = min(plinth_x_max, dimensions["outer_jaw_x_max"])
    seat = Part.makeBox(
        seat_x_max - seat_x_min,
        2.0 * dimensions["seat_y_half"],
        dimensions["seat_top_z"] - dimensions["plinth_thickness"],
        App.Vector(seat_x_min, -dimensions["seat_y_half"], dimensions["plinth_thickness"]),
    )
    inner_jaw = Part.makeBox(
        dimensions["inner_jaw_x_max"] - dimensions["inner_jaw_x_min"],
        2.0 * dimensions["jaw_y_half"],
        dimensions["inner_jaw_top_z"] - dimensions["seat_top_z"],
        App.Vector(dimensions["inner_jaw_x_min"], -dimensions["jaw_y_half"], dimensions["seat_top_z"]),
    )
    outer_jaw = Part.makeBox(
        dimensions["outer_jaw_x_max"] - dimensions["outer_jaw_x_min"],
        2.0 * dimensions["jaw_y_half"],
        dimensions["outer_jaw_top_z"] - dimensions["seat_top_z"],
        App.Vector(dimensions["outer_jaw_x_min"], -dimensions["jaw_y_half"], dimensions["seat_top_z"]),
    )
    prototype = _fuse_shapes([edge, plinth, seat, inner_jaw, outer_jaw], "the {} chair-body prototype".format(dimensions["chair_label"]))
    try:
        if prototype.isNull() or not prototype.isValid() or float(getattr(prototype, "Volume", 0.0)) <= 0.0:
            raise ValueError("FreeCAD produced an invalid {} chair-body prototype.".format(dimensions["chair_label"]))
    except AttributeError:
        pass
    _CHAIR_PROTOTYPE_SHAPE_CACHE[cache_key] = prototype.copy()
    return prototype, False


def _chair_build_compound_from_plan(plan, settings=None):
    started = time.perf_counter()
    shapes = []
    cache_hits = 0
    cache_misses = 0
    for instance in list(plan.get("instances") or []):
        prototype, reused = _chair_make_s1_prototype_shape(instance["chair_code"], settings)
        cache_hits += int(bool(reused))
        cache_misses += int(not bool(reused))
        placed = prototype.copy()
        placed.Placement = App.Placement(
            App.Vector(float(instance["centre_point"][0]), float(instance["centre_point"][1]), float(instance["base_z"])),
            App.Rotation(App.Vector(0.0, 0.0, 1.0), float(instance["rotation_degrees"])),
        )
        shapes.append(placed)
    if not shapes:
        raise ValueError("No supported S1 or S1J chair bodies are available to generate.")
    compound = shapes[0] if len(shapes) == 1 else Part.makeCompound(shapes)
    try:
        if compound.isNull() or not compound.isValid():
            raise ValueError("FreeCAD produced an invalid supported-chair compound.")
    except AttributeError:
        pass
    return compound, {
        "shape_construction_time_ms": (time.perf_counter() - started) * 1000.0,
        "prototype_cache_hits": cache_hits,
        "prototype_cache_misses": cache_misses,
    }


def _chair_tag_auxiliary_object(obj, entity_kind, entity_id, set_id, role):
    tag_generated_object(obj, role, set_id)
    kind = str(entity_kind or "").lower()
    identity_property = TURNOUT_ID_PROPERTY if kind == "turnout" else CROSSOVER_ID_PROPERTY
    properties = [
        ensure_property(obj, "App::PropertyString", identity_property, "Physical chairs", "Parent railway identity"),
        ensure_property(obj, "App::PropertyString", CHAIR_SOLID_PARENT_KIND_PROPERTY, "Physical chairs", "Parent railway kind"),
        ensure_property(obj, "App::PropertyString", CHAIR_SOLID_PARENT_ID_PROPERTY, "Physical chairs", "Parent railway identity"),
    ]
    _set_persistent_property_if_changed(obj, identity_property, str(entity_id))
    _set_persistent_property_if_changed(obj, CHAIR_SOLID_PARENT_KIND_PROPERTY, kind)
    _set_persistent_property_if_changed(obj, CHAIR_SOLID_PARENT_ID_PROPERTY, str(entity_id))
    set_read_only(obj, properties)


def _chair_update_configuration_only(doc, entity_kind, config):
    kind = str(entity_kind or "").lower()
    entity_id = str(config.get("turnout_id") or config.get("crossover_id") or "")
    settings_obj = _chair_settings_object(doc, kind, entity_id)
    if settings_obj is None:
        raise ValueError("The {} settings object is missing.".format(kind))
    property_name = TURNOUT_CONFIGURATION_PROPERTY if kind == "turnout" else CROSSOVER_CONFIGURATION_PROPERTY
    _set_persistent_property_if_changed(settings_obj, property_name, json.dumps(config, sort_keys=True))
    if kind == "turnout":
        _turnout_store_catalogue(doc, str(config.get("template_set_id") or ""))
    else:
        _crossover_store_catalogue(doc, str(config.get("template_set_id") or ""))
    return settings_obj


def _chair_write_physical_state(doc, entity_kind, config, analysis_result, physical_state):
    kind = str(entity_kind or "").lower()
    entity_id = str(config.get("turnout_id") or config.get("crossover_id") or "")
    result = dict(analysis_result or {})
    result["physical_chair_state"] = dict(physical_state or {})
    result["chair_solids_generated"] = int((physical_state or {}).get("generated_count") or 0) > 0
    result["chair_solids_supported_types"] = list(CHAIR_SOLID_SUPPORTED_LABELS)
    result["chair_physical_fit_validated"] = bool((physical_state or {}).get("physical_fit_validated"))
    result["model_timber_support_changes_applied"] = bool((physical_state or {}).get("model_timber_support_changes_applied"))
    result["physical_model_timber_support_adjustments"] = list((physical_state or {}).get("model_timber_support_adjustments") or [])
    result["production_ready"] = bool((physical_state or {}).get("production_ready", False))
    updated = dict(config or {})
    updated["chair_analysis_settings"] = normalise_chair_analysis_settings(result.get("settings"))
    updated["chair_solid_schema_version"] = CHAIR_SOLID_SCHEMA_VERSION
    updated["chair_solid_status"] = str((physical_state or {}).get("status") or CHAIR_SOLID_STATUS_NOT_GENERATED)
    updated["chair_solid_signature"] = str((physical_state or {}).get("solid_signature") or "")
    updated["chair_physical_fit_status"] = str((physical_state or {}).get("physical_fit_status") or updated["chair_solid_status"])
    updated["chair_supported_solid_count"] = int((physical_state or {}).get("generated_count") or 0)
    updated["chair_analytical_only_count"] = int((physical_state or {}).get("analytical_only_count") or 0)
    updated["chair_unresolved_special_count"] = int((physical_state or {}).get("unresolved_special_count") or 0)
    updated["chair_model_support_widening_applied"] = bool((physical_state or {}).get("model_timber_support_changes_applied"))
    updated["chair_model_support_timber_count"] = int((physical_state or {}).get("model_timber_support_adjusted_count") or 0)
    updated["chair_maximum_model_support_extension_per_side"] = float((physical_state or {}).get("maximum_model_support_extension_per_side") or 0.0)
    updated["chair_solids_complete"] = bool((physical_state or {}).get("all_required_chairs_generated", False))
    updated["chair_final_validation_complete"] = bool((physical_state or {}).get("production_ready", False))
    updated["production_ready"] = bool((physical_state or {}).get("production_ready", False))
    settings_obj = _chair_update_configuration_only(doc, kind, updated)
    properties = [
        ensure_property(settings_obj, "App::PropertyString", CHAIR_SOLID_STATUS_PROPERTY, "Physical chairs", "Current supported-chair solid status"),
        ensure_property(settings_obj, "App::PropertyString", CHAIR_SOLID_SIGNATURE_PROPERTY, "Physical chairs", "Stable supported-chair solid signature"),
        ensure_property(settings_obj, "App::PropertyString", CHAIR_SOLID_RESULT_PROPERTY, "Physical chairs", "Cached physical-chair generation and fit result"),
        ensure_property(settings_obj, "App::PropertyString", CHAIR_PHYSICAL_FIT_STATUS_PROPERTY, "Physical chairs", "Current physical fit-validation status"),
    ]
    _set_persistent_property_if_changed(settings_obj, CHAIR_SOLID_STATUS_PROPERTY, updated["chair_solid_status"])
    _set_persistent_property_if_changed(settings_obj, CHAIR_SOLID_SIGNATURE_PROPERTY, updated["chair_solid_signature"])
    _set_persistent_property_if_changed(settings_obj, CHAIR_SOLID_RESULT_PROPERTY, json.dumps(physical_state, sort_keys=True))
    _set_persistent_property_if_changed(settings_obj, CHAIR_PHYSICAL_FIT_STATUS_PROPERTY, updated["chair_physical_fit_status"])
    _set_persistent_property_if_changed(settings_obj, CHAIR_ANALYSIS_RESULT_PROPERTY, json.dumps(result, sort_keys=True))
    set_read_only(settings_obj, properties)
    return updated, result


def _chair_physical_state_from_object(obj):
    if obj is None:
        return None
    try:
        value = json.loads(object_string_property(obj, CHAIR_SOLID_RESULT_PROPERTY, ""))
    except Exception:
        value = None
    return value if isinstance(value, dict) else None


def chair_solid_effective_status(doc, entity_kind, config):
    cfg = dict(config or {})
    entity_id = str(cfg.get("turnout_id") or cfg.get("crossover_id") or "")
    analysis = _chair_read_cached_result(doc, entity_kind, entity_id)
    obj = _chair_solid_object(doc, entity_kind, entity_id)
    if obj is None:
        return CHAIR_SOLID_STATUS_NOT_GENERATED
    state = _chair_physical_state_from_object(obj)
    if not isinstance(analysis, dict) or not isinstance(state, dict):
        return CHAIR_SOLID_STATUS_STALE
    if str(state.get("source_analysis_signature") or "") != str(analysis.get("geometry_signature") or ""):
        return CHAIR_SOLID_STATUS_STALE
    if str(state.get("solid_signature") or "") != object_string_property(obj, CHAIR_SOLID_SIGNATURE_PROPERTY, ""):
        return CHAIR_SOLID_STATUS_STALE
    return str(state.get("status") or CHAIR_SOLID_STATUS_GENERATED)


def _chair_generation_context(doc, entity_kind, entity_id, settings=None):
    kind = str(entity_kind or "").lower()
    config = turnout_config_by_id(doc, entity_id) if kind == "turnout" else crossover_config_by_id(doc, entity_id)
    if not isinstance(config, dict):
        raise ValueError("{} {} was not found.".format(kind.capitalize(), entity_id or "selection"))
    if chair_analysis_effective_status(doc, kind, config) == CHAIR_STATUS_STALE:
        raise ValueError("Chair analysis is stale. Analyse chair positions again before generating physical chairs.")
    analysis = _chair_read_cached_result(doc, kind, entity_id)
    if not isinstance(analysis, dict):
        raise ValueError("Analyse chair positions before generating physical chairs.")
    settings = normalise_chair_analysis_settings(settings if settings is not None else analysis.get("settings") or config.get("chair_analysis_settings"))
    rails = chair_rail_records_for_entity(doc, kind, config)
    timbers = chair_timber_records_for_entity(doc, kind, config)
    return kind, config, analysis, settings, rails, timbers


def generate_supported_chair_solids(doc, entity_kind, entity_id, settings=None):
    """Generate all supported S1/S1J bodies transactionally and all-or-nothing."""
    overall_started = time.perf_counter()
    kind, config, analysis, settings, rails, timbers = _chair_generation_context(
        doc, entity_kind, entity_id, settings
    )
    validation_started = time.perf_counter()
    plan = _chair_build_solid_plan(doc, kind, config, analysis, rails, timbers, settings)
    validation = _chair_validate_solid_plan(plan, rails, timbers, settings)
    validation_time = (time.perf_counter() - validation_started) * 1000.0
    if int(validation.get("physical_fit_failure_count") or 0):
        first = list(validation.get("findings") or [])[:8]
        detail = "\n".join(
            "- {} on {} / {}: {}".format(
                item.get("code"), item.get("timber_identity") or "unknown timber",
                item.get("rail_identity") or "unknown rail", item.get("message")
            ) for item in first
        )
        raise ValueError(
            "Supported chair-body generation was not committed because physical fit validation found {} production-critical failure(s).\n{}".format(
                validation.get("physical_fit_failure_count"), detail
            )
        )
    if not plan.get("instances"):
        raise ValueError("No confirmed S1 or S1J positions are available for physical generation.")
    existing = _chair_solid_object(doc, kind, entity_id)
    existing_state = _chair_physical_state_from_object(existing)
    if (
        bool(settings.get("cache_enabled"))
        and existing is not None
        and isinstance(existing_state, dict)
        and str(existing_state.get("solid_signature") or "") == str(plan.get("solid_signature") or "")
        and str(existing_state.get("source_analysis_signature") or "") == str(analysis.get("geometry_signature") or "")
    ):
        try:
            shape_current = not existing.Shape.isNull() and existing.Shape.isValid()
        except Exception:
            shape_current = True
        if shape_current:
            try:
                existing.ViewObject.Visibility = bool(settings.get("physical_solids_visible"))
            except Exception:
                pass
            reused = dict(existing_state)
            reused["unchanged_result_reused"] = True
            reused["total_time_ms"] = (time.perf_counter() - overall_started) * 1000.0
            return reused
    compound, construction = _chair_build_compound_from_plan(plan, settings)
    physical_state = {
        "schema_version": CHAIR_SOLID_SCHEMA_VERSION,
        "macro_version": MACRO_VERSION_NUMBER,
        "entity_kind": kind,
        "entity_id": str(entity_id),
        "status": CHAIR_SOLID_STATUS_FIT_VALIDATED,
        "physical_fit_status": CHAIR_SOLID_STATUS_FIT_VALIDATED,
        "source_analysis_signature": str(analysis.get("geometry_signature") or ""),
        "solid_signature": str(plan.get("solid_signature") or ""),
        "rail_profile": chair_production_rail_profile(),
        "supported_types": list(CHAIR_SOLID_SUPPORTED_LABELS),
        "generated_count": len(plan.get("instances") or []),
        "s1_count": sum(1 for item in plan.get("instances") or [] if int(item.get("chair_code") or 0) == 1),
        "s1j_count": sum(1 for item in plan.get("instances") or [] if int(item.get("chair_code") or 0) == 7),
        "analytical_only_count": len(plan.get("analytical_only") or []),
        "unresolved_special_count": int(validation.get("unresolved_special_count") or 0),
        "key_direction_unresolved_count": int(validation.get("key_direction_unresolved_count") or 0),
        "model_timber_support_adjustments": list(validation.get("model_timber_support_adjustments") or []),
        "model_timber_support_changes_applied": bool(validation.get("model_timber_support_changes_applied")),
        "model_timber_support_adjusted_count": int(validation.get("model_timber_support_adjusted_count") or 0),
        "maximum_model_support_extension_per_side": float(validation.get("maximum_model_support_extension_per_side") or 0.0),
        "physical_fit_failure_count": int(validation.get("physical_fit_failure_count") or 0),
        "physical_fit_validated": bool(validation.get("physical_fit_validated")),
        "all_required_chairs_generated": False,
        "production_ready": False,
        "readiness_blockers": list(validation.get("readiness_blockers") or []),
        "fit_findings": list(validation.get("findings") or []),
        "analytical_only_positions": list(plan.get("analytical_only") or []),
        "shape_construction_time_ms": float(construction.get("shape_construction_time_ms") or 0.0),
        "physical_fit_validation_time_ms": float(validation_time),
        "prototype_cache_hits": int(construction.get("prototype_cache_hits") or 0),
        "prototype_cache_misses": int(construction.get("prototype_cache_misses") or 0),
        "unchanged_result_reused": False,
        "body_scope": "Source-dimensional S1/S1J body, seat and jaw envelope with bounded model-only timber-side support widening; prototype timber references remain unchanged. Keys, loose jaws, plugs and special chairs are not generated.",
    }
    transaction_open = False
    try:
        doc.openTransaction("Generate Version {} supported chair solids {}".format(MACRO_VERSION_NUMBER, entity_id))
        transaction_open = True
        obj = existing
        if obj is None:
            obj = doc.addObject("Part::Feature", unique_internal_name(doc, "RailwayChairSolids_{}".format(str(entity_id).replace("-", "_"))))
        obj.Label = "{} supported S1/S1J chair bodies".format(entity_id)
        _chair_tag_auxiliary_object(obj, kind, entity_id, str(config.get("template_set_id") or ""), CHAIR_SOLID_ROLE)
        obj.Shape = compound
        properties = [
            ensure_property(obj, "App::PropertyInteger", "ChairSolidSchemaVersion", "Physical chairs", "Supported-chair solid metadata schema"),
            ensure_property(obj, "App::PropertyString", CHAIR_SOLID_STATUS_PROPERTY, "Physical chairs", "Current supported-chair solid status"),
            ensure_property(obj, "App::PropertyString", CHAIR_SOLID_SIGNATURE_PROPERTY, "Physical chairs", "Stable supported-chair solid signature"),
            ensure_property(obj, "App::PropertyString", CHAIR_SOLID_RESULT_PROPERTY, "Physical chairs", "Physical-chair generation and fit result"),
            ensure_property(obj, "App::PropertyString", CHAIR_PHYSICAL_FIT_STATUS_PROPERTY, "Physical chairs", "Current physical fit-validation status"),
            ensure_property(obj, "App::PropertyString", "ChairRailProfile", "Physical chairs", "Fixed rail profile used for fit validation"),
            ensure_property(obj, "App::PropertyString", "ChairSupportedTypes", "Physical chairs", "Chair types physically generated in this stage"),
            ensure_property(obj, "App::PropertyInteger", "ChairSolidInstanceCount", "Physical chairs", "Number of supported physical chair bodies"),
            ensure_property(obj, "App::PropertyInteger", "ChairAnalyticalOnlyCount", "Physical chairs", "Positions retained as analytical-only"),
            ensure_property(obj, "App::PropertyBool", "ChairModelSupportWideningApplied", "Physical chairs", "True when model-only timber support widening was applied"),
            ensure_property(obj, "App::PropertyInteger", "ChairModelSupportTimberCount", "Physical chairs", "Number of effective timbers widened for chair support"),
            ensure_property(obj, "App::PropertyLength", "ChairMaximumModelSupportExtension", "Physical chairs", "Maximum automatic extension applied or required on one timber side"),
            ensure_property(obj, "App::PropertyBool", "ChairProductionReady", "Physical chairs", "True only when every required chair and physical fit gate is complete"),
        ]
        _set_persistent_property_if_changed(obj, "ChairSolidSchemaVersion", CHAIR_SOLID_SCHEMA_VERSION)
        _set_persistent_property_if_changed(obj, CHAIR_SOLID_STATUS_PROPERTY, physical_state["status"])
        _set_persistent_property_if_changed(obj, CHAIR_SOLID_SIGNATURE_PROPERTY, physical_state["solid_signature"])
        _set_persistent_property_if_changed(obj, CHAIR_SOLID_RESULT_PROPERTY, json.dumps(physical_state, sort_keys=True))
        _set_persistent_property_if_changed(obj, CHAIR_PHYSICAL_FIT_STATUS_PROPERTY, physical_state["physical_fit_status"])
        _set_persistent_property_if_changed(obj, "ChairRailProfile", CHAIR_CODE75_RAIL_PROFILE["operator_label"])
        _set_persistent_property_if_changed(obj, "ChairSupportedTypes", ", ".join(CHAIR_SOLID_SUPPORTED_LABELS))
        _set_persistent_property_if_changed(obj, "ChairSolidInstanceCount", physical_state["generated_count"])
        _set_persistent_property_if_changed(obj, "ChairAnalyticalOnlyCount", physical_state["analytical_only_count"])
        _set_persistent_property_if_changed(obj, "ChairModelSupportWideningApplied", physical_state["model_timber_support_changes_applied"])
        _set_persistent_property_if_changed(obj, "ChairModelSupportTimberCount", physical_state["model_timber_support_adjusted_count"])
        _set_persistent_property_if_changed(obj, "ChairMaximumModelSupportExtension", physical_state["maximum_model_support_extension_per_side"])
        _set_persistent_property_if_changed(obj, "ChairProductionReady", False)
        set_read_only(obj, properties)
        try:
            obj.ViewObject.ShapeColor = (0.64, 0.47, 0.25)
            obj.ViewObject.Visibility = bool(settings.get("physical_solids_visible"))
        except Exception:
            pass
        _chair_write_physical_state(doc, kind, config, analysis, physical_state)
        _document_recompute(doc)
        doc.commitTransaction()
        transaction_open = False
    except Exception:
        if transaction_open:
            try:
                doc.abortTransaction()
            except Exception:
                pass
        raise
    physical_state["total_time_ms"] = (time.perf_counter() - overall_started) * 1000.0
    return physical_state


def validate_generated_chair_solids(doc, entity_kind, entity_id, settings=None):
    """Revalidate current supported-chair solids and metadata without rebuilding."""
    kind, config, analysis, settings, rails, timbers = _chair_generation_context(
        doc, entity_kind, entity_id, settings
    )
    obj = _chair_solid_object(doc, kind, entity_id)
    if obj is None:
        raise ValueError("Generate supported chair solids before validating physical fit.")
    plan = _chair_build_solid_plan(doc, kind, config, analysis, rails, timbers, settings)
    if object_string_property(obj, CHAIR_SOLID_SIGNATURE_PROPERTY, "") != str(plan.get("solid_signature") or ""):
        _chair_mark_solid_stale(doc, kind, entity_id)
        raise ValueError("The generated chair solids are stale. Regenerate them before physical fit validation.")
    validation = _chair_validate_solid_plan(plan, rails, timbers, settings)
    shape_valid = True
    shape_reason = "FreeCAD shape validity reported clear."
    try:
        shape_valid = not obj.Shape.isNull() and obj.Shape.isValid()
        if not shape_valid:
            shape_reason = "FreeCAD reports a null or invalid supported-chair compound."
    except Exception:
        shape_reason = "FreeCAD shape validity API was unavailable; analytical fit validation completed."
    if not shape_valid:
        validation["physical_fit_failure_count"] = int(validation.get("physical_fit_failure_count") or 0) + 1
        validation["physical_fit_validated"] = False
        validation["status"] = CHAIR_SOLID_STATUS_FIT_FAILED
        validation.setdefault("readiness_blockers", []).append(shape_reason)
    previous = _chair_physical_state_from_object(obj) or {}
    state = dict(previous)
    state.update({
        "status": validation["status"],
        "physical_fit_status": validation["status"],
        "physical_fit_validated": bool(validation.get("physical_fit_validated")) and shape_valid,
        "physical_fit_failure_count": int(validation.get("physical_fit_failure_count") or 0),
        "unresolved_special_count": int(validation.get("unresolved_special_count") or 0),
        "key_direction_unresolved_count": int(validation.get("key_direction_unresolved_count") or 0),
        "model_timber_support_adjustments": list(validation.get("model_timber_support_adjustments") or []),
        "model_timber_support_changes_applied": bool(validation.get("model_timber_support_changes_applied")),
        "model_timber_support_adjusted_count": int(validation.get("model_timber_support_adjusted_count") or 0),
        "maximum_model_support_extension_per_side": float(validation.get("maximum_model_support_extension_per_side") or 0.0),
        "readiness_blockers": list(validation.get("readiness_blockers") or []),
        "fit_findings": list(validation.get("findings") or []),
        "physical_fit_validation_time_ms": float(validation.get("validation_time_ms") or 0.0),
        "freecad_shape_valid": bool(shape_valid),
        "freecad_shape_validation_note": shape_reason,
        "production_ready": False,
    })
    transaction_open = False
    try:
        doc.openTransaction("Validate Version {} chair fit {}".format(MACRO_VERSION_NUMBER, entity_id))
        transaction_open = True
        _set_persistent_property_if_changed(obj, CHAIR_SOLID_STATUS_PROPERTY, state["status"])
        _set_persistent_property_if_changed(obj, CHAIR_PHYSICAL_FIT_STATUS_PROPERTY, state["physical_fit_status"])
        _set_persistent_property_if_changed(obj, CHAIR_SOLID_RESULT_PROPERTY, json.dumps(state, sort_keys=True))
        if hasattr(obj, "ChairModelSupportWideningApplied"):
            _set_persistent_property_if_changed(obj, "ChairModelSupportWideningApplied", state["model_timber_support_changes_applied"])
        if hasattr(obj, "ChairModelSupportTimberCount"):
            _set_persistent_property_if_changed(obj, "ChairModelSupportTimberCount", state["model_timber_support_adjusted_count"])
        if hasattr(obj, "ChairMaximumModelSupportExtension"):
            _set_persistent_property_if_changed(obj, "ChairMaximumModelSupportExtension", state["maximum_model_support_extension_per_side"])
        _chair_write_physical_state(doc, kind, config, analysis, state)
        doc.commitTransaction()
        transaction_open = False
    except Exception:
        if transaction_open:
            try:
                doc.abortTransaction()
            except Exception:
                pass
        raise
    return state


def remove_generated_chair_solids(doc, entity_kind, entity_id):
    kind = str(entity_kind or "").lower()
    config = turnout_config_by_id(doc, entity_id) if kind == "turnout" else crossover_config_by_id(doc, entity_id)
    if not isinstance(config, dict):
        raise ValueError("{} {} was not found.".format(kind.capitalize(), entity_id or "selection"))
    analysis = _chair_read_cached_result(doc, kind, entity_id) or {}
    objects = _chair_auxiliary_objects(doc, kind, entity_id, (CHAIR_SOLID_ROLE, CHAIR_UNRESOLVED_MARKER_ROLE))
    state = {
        "schema_version": CHAIR_SOLID_SCHEMA_VERSION,
        "macro_version": MACRO_VERSION_NUMBER,
        "entity_kind": kind,
        "entity_id": str(entity_id),
        "status": CHAIR_SOLID_STATUS_NOT_GENERATED,
        "physical_fit_status": CHAIR_SOLID_STATUS_NOT_GENERATED,
        "solid_signature": "",
        "source_analysis_signature": str(analysis.get("geometry_signature") or ""),
        "generated_count": 0,
        "analytical_only_count": len(list(analysis.get("positions") or [])),
        "unresolved_special_count": sum(1 for item in list(analysis.get("positions") or []) if bool(item.get("special_assignment_deferred"))),
        "physical_fit_validated": False,
        "production_ready": False,
        "readiness_blockers": ["Supported physical chair bodies have not been generated."],
    }
    transaction_open = False
    try:
        doc.openTransaction("Remove Version {} supported chair solids {}".format(MACRO_VERSION_NUMBER, entity_id))
        transaction_open = True
        for obj in objects:
            doc.removeObject(str(obj.Name))
        _chair_write_physical_state(doc, kind, config, analysis, state)
        _document_recompute(doc)
        doc.commitTransaction()
        transaction_open = False
    except Exception:
        if transaction_open:
            try:
                doc.abortTransaction()
            except Exception:
                pass
        raise
    return state


def set_chair_solid_visibility(doc, entity_kind, entity_id, visible):
    obj = _chair_solid_object(doc, entity_kind, entity_id)
    if obj is None:
        return False
    try:
        obj.ViewObject.Visibility = bool(visible)
    except Exception:
        return False
    return True


def set_unresolved_chair_visibility(doc, entity_kind, entity_id, visible):
    kind = str(entity_kind or "").lower()
    existing = _chair_unresolved_marker_object(doc, kind, entity_id)
    if not visible:
        if existing is not None:
            try:
                existing.ViewObject.Visibility = False
            except Exception:
                pass
        return False
    config = turnout_config_by_id(doc, entity_id) if kind == "turnout" else crossover_config_by_id(doc, entity_id)
    result = _chair_read_cached_result(doc, kind, entity_id)
    if not isinstance(config, dict) or not isinstance(result, dict):
        raise ValueError("Analyse chair positions before showing unresolved positions.")
    unresolved = [
        item for item in list(result.get("positions") or [])
        if not _chair_supported_physical_position(item)[0]
        and not bool(item.get("deliberate_omission"))
    ]
    if not unresolved:
        if existing is not None:
            try:
                existing.ViewObject.Visibility = False
            except Exception:
                pass
        return False
    z_height = _chair_physical_top_z(doc, kind, config) + 0.10
    shapes = []
    for position in unresolved:
        shapes.extend(_chair_cross_wires(
            position.get("centre_point") or (0.0, 0.0),
            position.get("local_rail_tangent") or (1.0, 0.0),
            half_size=0.70,
            z_height=z_height,
        ))
    transaction_open = False
    try:
        doc.openTransaction("Show unresolved chair positions {}".format(entity_id))
        transaction_open = True
        obj = existing
        if obj is None:
            obj = doc.addObject("Part::Feature", unique_internal_name(doc, "UnresolvedChairPositions_{}".format(str(entity_id).replace("-", "_"))))
        obj.Label = "{} unresolved chair positions".format(entity_id)
        _chair_tag_auxiliary_object(obj, kind, entity_id, str(config.get("template_set_id") or ""), CHAIR_UNRESOLVED_MARKER_ROLE)
        obj.Shape = Part.makeCompound(shapes)
        count_prop = ensure_property(obj, "App::PropertyInteger", "UnresolvedChairPositionCount", "Physical chairs", "Number of analytical-only chair positions shown")
        _set_persistent_property_if_changed(obj, "UnresolvedChairPositionCount", len(unresolved))
        set_read_only(obj, [count_prop])
        try:
            obj.ViewObject.LineColor = (0.86, 0.20, 0.20)
            obj.ViewObject.LineWidth = 2.8
            obj.ViewObject.Visibility = True
        except Exception:
            pass
        _document_recompute(doc)
        doc.commitTransaction()
        transaction_open = False
    except Exception:
        if transaction_open:
            try:
                doc.abortTransaction()
            except Exception:
                pass
        raise
    return True


def analyse_entity_chair_positions(doc, entity_kind, entity_id, settings=None):
    result = _A8A7B11_ANALYSE_ENTITY_CHAIR_POSITIONS(doc, entity_kind, entity_id, settings)
    obj = _chair_solid_object(doc, entity_kind, entity_id)
    state = _chair_physical_state_from_object(obj)
    if obj is not None and isinstance(state, dict):
        if str(state.get("source_analysis_signature") or "") != str(result.get("geometry_signature") or ""):
            _chair_mark_solid_stale(doc, entity_kind, entity_id)
    return result


def chair_analysis_summary(result, include_findings=True):
    base = _A8A7B11_CHAIR_ANALYSIS_SUMMARY(result, include_findings)
    state = dict((result or {}).get("physical_chair_state") or {})
    if not state:
        return base + "\n\nPhysical chair bodies: not generated.\nFixed rail profile: {}.".format(
            CHAIR_CODE75_RAIL_PROFILE["operator_label"]
        )
    lines = [
        base,
        "",
        "Physical chair bodies:",
        "- Status: {}".format(state.get("status") or CHAIR_SOLID_STATUS_NOT_GENERATED),
        "- Fixed rail profile: {}".format(CHAIR_CODE75_RAIL_PROFILE["operator_label"]),
        "- Physically generated: {} (S1 {}; S1J {})".format(
            int(state.get("generated_count") or 0), int(state.get("s1_count") or 0), int(state.get("s1j_count") or 0)
        ),
        "- Analytical-only positions: {}".format(int(state.get("analytical_only_count") or 0)),
        "- Unresolved special positions: {}".format(int(state.get("unresolved_special_count") or 0)),
        "- Physical-fit failures: {}".format(int(state.get("physical_fit_failure_count") or 0)),
        "- Effective model timbers widened: {}".format(int(state.get("model_timber_support_adjusted_count") or 0)),
        "- Maximum model support extension on one side: {:.3f} mm".format(float(state.get("maximum_model_support_extension_per_side") or 0.0)),
        "- Prototype timber references changed: No",
        "- Production ready: {}".format("Yes" if bool(state.get("production_ready")) else "No"),
        "- Chair-shape construction time: {:.1f} ms".format(float(state.get("shape_construction_time_ms") or 0.0)),
        "- Chair physical-fit validation time: {:.1f} ms".format(float(state.get("physical_fit_validation_time_ms") or 0.0)),
    ]
    blockers = list(state.get("readiness_blockers") or [])
    if blockers:
        lines.append("- Remaining readiness blockers: {}".format("; ".join(str(item) for item in blockers)))
    return "\n".join(lines)


def preflight_chair_analysis_readiness(doc, records, set_id):
    issues = _A8A7B11_PREFLIGHT_CHAIR_ANALYSIS_READINESS(doc, records, set_id)
    representatives = {}
    for record in records or []:
        kind, identifier = _chair_preflight_record_entity(doc, record)
        if kind and identifier:
            representatives.setdefault((kind, identifier), record)
    for (kind, identifier), record in sorted(representatives.items()):
        config = turnout_config_by_id(doc, identifier) if kind == "turnout" else crossover_config_by_id(doc, identifier)
        if not isinstance(config, dict):
            continue
        status = chair_solid_effective_status(doc, kind, config)
        if status == CHAIR_SOLID_STATUS_NOT_GENERATED:
            issues.append(make_preflight_issue(
                "SUPPORTED_CHAIR_SOLIDS_NOT_GENERATED", PRODUCTION_PREFLIGHT_SEVERITY_INFORMATION,
                "{} {} has no supported S1/S1J physical chair bodies. Inspection export remains available; production readiness remains false.".format(kind.capitalize(), identifier),
                set_id, record, blocks_export=False,
            ))
        elif status == CHAIR_SOLID_STATUS_STALE:
            issues.append(make_preflight_issue(
                "SUPPORTED_CHAIR_SOLIDS_STALE", PRODUCTION_PREFLIGHT_SEVERITY_WARNING,
                "{} {} has stale supported-chair solids. Regenerate and revalidate them before treating the assembly as physically checked.".format(kind.capitalize(), identifier),
                set_id, record, blocks_export=False,
            ))
        else:
            state = _chair_physical_state_from_object(_chair_solid_object(doc, kind, identifier)) or {}
            if int(state.get("physical_fit_failure_count") or 0):
                issues.append(make_preflight_issue(
                    "CHAIR_PHYSICAL_FIT_FAILURES", PRODUCTION_PREFLIGHT_SEVERITY_WARNING,
                    "{} {} has {} physical chair-body fit failure(s).".format(kind.capitalize(), identifier, state.get("physical_fit_failure_count")),
                    set_id, record, blocks_export=False,
                ))
            issues.append(make_preflight_issue(
                "CHAIR_SPECIALS_KEYS_AND_PRINTED_FIT_OUTSTANDING", PRODUCTION_PREFLIGHT_SEVERITY_INFORMATION,
                "{} {} uses the fixed Templot Code 75 profile and has {} supported S1/S1J body solids. Special-chair bodies, keying and live printed fit remain outstanding.".format(kind.capitalize(), identifier, int(state.get("generated_count") or 0)),
                set_id, record, blocks_export=False,
            ))
    return issues


class ChairAnalysisSettingsDialog(QtWidgets.QDialog):
    def __init__(self, settings, parent=None):
        super(ChairAnalysisSettingsDialog, self).__init__(parent)
        self.setWindowTitle(versioned_dialog_title("Chair analysis and physical-fit settings"))
        self._defaults = normalise_chair_analysis_settings(settings)
        layout = QtWidgets.QFormLayout(self)
        profile = QtWidgets.QLabel(CHAIR_CODE75_RAIL_PROFILE["operator_label"] + " (fixed for this stage)")
        profile.setWordWrap(True)
        layout.addRow("Rail profile", profile)
        self.position = QtWidgets.QDoubleSpinBox(); self.position.setRange(0.0, 5.0); self.position.setDecimals(3); self.position.setSuffix(" mm"); self.position.setValue(self._defaults["position_tolerance"])
        self.footprint = QtWidgets.QDoubleSpinBox(); self.footprint.setRange(0.0, 5.0); self.footprint.setDecimals(3); self.footprint.setSuffix(" mm"); self.footprint.setValue(self._defaults["footprint_clearance"])
        self.end_clearance = QtWidgets.QDoubleSpinBox(); self.end_clearance.setRange(0.0, 10.0); self.end_clearance.setDecimals(3); self.end_clearance.setSuffix(" mm"); self.end_clearance.setValue(self._defaults["timber_end_clearance"])
        self.skew = QtWidgets.QDoubleSpinBox(); self.skew.setRange(0.0, 30.0); self.skew.setDecimals(2); self.skew.setSuffix(" degrees"); self.skew.setValue(self._defaults["maximum_advisory_skew_degrees"])
        self.span = QtWidgets.QDoubleSpinBox(); self.span.setRange(1.0, 100.0); self.span.setDecimals(3); self.span.setSuffix(" mm"); self.span.setValue(self._defaults["maximum_unsupported_span"])
        self.rail_fit = QtWidgets.QDoubleSpinBox(); self.rail_fit.setRange(0.0, 0.50); self.rail_fit.setDecimals(3); self.rail_fit.setSuffix(" mm per side"); self.rail_fit.setValue(self._defaults["rail_fit_clearance_per_side"])
        self.embed = QtWidgets.QDoubleSpinBox(); self.embed.setRange(0.0, 5.0); self.embed.setDecimals(3); self.embed.setSuffix(" mm"); self.embed.setValue(self._defaults["future_chair_embed_depth"])
        self.model_support = QtWidgets.QCheckBox("Calculate model timber support allowances"); self.model_support.setChecked(self._defaults["model_support_recommendations_enabled"])
        self.auto_support = QtWidgets.QCheckBox("Apply small model-only timber widening automatically"); self.auto_support.setChecked(self._defaults.get("model_support_auto_apply_enabled", True))
        self.support_margin = QtWidgets.QDoubleSpinBox(); self.support_margin.setRange(0.0, 3.0); self.support_margin.setDecimals(3); self.support_margin.setSuffix(" mm"); self.support_margin.setValue(self._defaults["model_support_edge_margin"])
        self.support_limit = QtWidgets.QDoubleSpinBox(); self.support_limit.setRange(0.0, 10.0); self.support_limit.setDecimals(3); self.support_limit.setSuffix(" mm"); self.support_limit.setValue(self._defaults["preferred_maximum_model_support_extension_per_side"])
        self.cache = QtWidgets.QCheckBox("Reuse analysis and supported solids when signatures match"); self.cache.setChecked(self._defaults["cache_enabled"])
        layout.addRow("Chair-position tolerance", self.position)
        layout.addRow("Footprint broad-phase clearance", self.footprint)
        layout.addRow("Minimum timber-end clearance", self.end_clearance)
        layout.addRow("Maximum advisory chair skew", self.skew)
        layout.addRow("Maximum unsupported rail span", self.span)
        layout.addRow("Code 75 rail-fit clearance", self.rail_fit)
        layout.addRow("Chair body embed depth", self.embed)
        layout.addRow("Model support analysis", self.model_support)
        layout.addRow("Automatic support widening", self.auto_support)
        layout.addRow("Model support edge margin", self.support_margin)
        layout.addRow("Maximum automatic extension per side", self.support_limit)
        layout.addRow("Analysis and solid cache", self.cache)
        note = QtWidgets.QLabel(
            "Physical generation is limited to S1 and S1J chair bodies. Where a rotated source-dimensional body slightly crosses a timber side, the macro can widen only the effective model support envelope, rounded upwards to 0.05 mm. It never changes rail geometry or the prototype timber reference, and it rejects extensions above the configured limit. Keys, loose jaws, plugs and special chairs remain analytical."
        )
        note.setWordWrap(True); layout.addRow(note)
        buttons = QtWidgets.QDialogButtonBox(QtWidgets.QDialogButtonBox.Ok | QtWidgets.QDialogButtonBox.Cancel)
        buttons.accepted.connect(self.accept); buttons.rejected.connect(self.reject); layout.addRow(buttons)

    def values(self):
        result = dict(self._defaults)
        result.update({
            "position_tolerance": self.position.value(),
            "footprint_clearance": self.footprint.value(),
            "timber_end_clearance": self.end_clearance.value(),
            "maximum_advisory_skew_degrees": self.skew.value(),
            "maximum_unsupported_span": self.span.value(),
            "rail_fit_clearance_per_side": self.rail_fit.value(),
            "future_chair_embed_depth": self.embed.value(),
            "cache_enabled": self.cache.isChecked(),
            "model_support_recommendations_enabled": self.model_support.isChecked(),
            "model_support_auto_apply_enabled": self.auto_support.isChecked(),
            "model_support_edge_margin": self.support_margin.value(),
            "preferred_maximum_model_support_extension_per_side": self.support_limit.value(),
        })
        return normalise_chair_analysis_settings(result)


class ChairAnalysisPanel(QtWidgets.QGroupBox):
    """Shared analytical and supported physical-chair workflow controls."""
    def __init__(self, doc, entity_kind, config_getter, refresh_callback=None, parent=None):
        super(ChairAnalysisPanel, self).__init__("Chair analysis and physical fit", parent)
        self.doc = doc
        self.entity_kind = str(entity_kind).lower()
        self.config_getter = config_getter
        self.refresh_callback = refresh_callback
        self.settings = default_chair_analysis_settings()
        layout = QtWidgets.QGridLayout(self)
        self.status = QtWidgets.QLabel(CHAIR_STATUS_NOT_ANALYSED); self.status.setWordWrap(True)
        self.analyse_button = QtWidgets.QPushButton("Analyse chair positions")
        self.generate_button = QtWidgets.QPushButton("Generate supported chair solids")
        self.validate_button = QtWidgets.QPushButton("Validate physical chair fit")
        self.solid_box = QtWidgets.QCheckBox("Show chair solids")
        self.unresolved_box = QtWidgets.QCheckBox("Show unresolved chair positions")
        self.marker_box = QtWidgets.QCheckBox("Show chair-position markers"); self.marker_box.setChecked(True)
        self.protected_box = QtWidgets.QCheckBox("Show protected chair positions")
        self.footprint_box = QtWidgets.QCheckBox("Show analytical chair footprints")
        self.details_button = QtWidgets.QPushButton("Show chair details")
        self.copy_button = QtWidgets.QPushButton("Copy readable chair summary")
        self.remove_solids_button = QtWidgets.QPushButton("Remove generated chair solids")
        self.clear_button = QtWidgets.QPushButton("Clear temporary chair display")
        self.settings_button = QtWidgets.QPushButton("Chair settings…")
        layout.addWidget(QtWidgets.QLabel("Selected item status"), 0, 0)
        layout.addWidget(self.status, 0, 1, 1, 5)
        layout.addWidget(self.analyse_button, 1, 0, 1, 2)
        layout.addWidget(self.generate_button, 1, 2, 1, 2)
        layout.addWidget(self.validate_button, 1, 4, 1, 2)
        layout.addWidget(self.solid_box, 2, 0)
        layout.addWidget(self.unresolved_box, 2, 1)
        layout.addWidget(self.marker_box, 2, 2)
        layout.addWidget(self.protected_box, 2, 3)
        layout.addWidget(self.footprint_box, 2, 4, 1, 2)
        layout.addWidget(self.details_button, 3, 0)
        layout.addWidget(self.copy_button, 3, 1)
        layout.addWidget(self.remove_solids_button, 3, 2, 1, 2)
        layout.addWidget(self.clear_button, 3, 4)
        layout.addWidget(self.settings_button, 3, 5)
        self.setToolTip("Analyses rail-to-timber support, generates only supported S1/S1J bodies using the fixed Templot Code 75 profile, and keeps special chairs explicit.")
        self.analyse_button.setToolTip("Runs exact rail projection and chair assignment without changing rail geometry or prototype timber references.")
        self.generate_button.setToolTip("Builds a cached compound of source-dimensional S1/S1J chair bodies. Small skew-related timber-side shortfalls can be resolved by the bounded model-only support widening policy before any object is committed.")
        self.validate_button.setToolTip("Rechecks chair orientation, Code 75 rail-foot clearance, timber support, overlaps and incompatible-rail interference without rebuilding the bodies.")
        self.solid_box.setToolTip("Shows or hides the detailed physical chair-body compound. Leave it hidden during routine geometry and timbering work for better responsiveness.")
        self.unresolved_box.setToolTip("Highlights analytical-only special, bridge and unsupported chair positions. It does not generate substitute chairs.")
        self.remove_solids_button.setToolTip("Removes physical chair-body and unresolved-marker objects while preserving chair analysis, railway geometry, timbering and host integration.")
        self.analyse_button.clicked.connect(self.run_analysis)
        self.generate_button.clicked.connect(self.generate_solids)
        self.validate_button.clicked.connect(self.validate_fit)
        self.solid_box.toggled.connect(self.change_solid_visibility)
        self.unresolved_box.toggled.connect(self.change_unresolved_visibility)
        self.marker_box.toggled.connect(self.change_visibility)
        self.protected_box.toggled.connect(self.change_visibility)
        self.footprint_box.toggled.connect(self.change_visibility)
        self.details_button.clicked.connect(self.show_details)
        self.copy_button.clicked.connect(self.copy_summary)
        self.remove_solids_button.clicked.connect(self.remove_solids)
        self.clear_button.clicked.connect(self.clear_display)
        self.settings_button.clicked.connect(self.edit_settings)
        self.refresh()

    def current_config(self):
        try:
            return self.config_getter()
        except Exception:
            return None

    def entity_id(self, config):
        return str((config or {}).get("turnout_id") or (config or {}).get("crossover_id") or "")

    def refresh(self):
        config = self.current_config()
        enabled = isinstance(config, dict)
        for widget in (
            self.analyse_button, self.generate_button, self.validate_button,
            self.solid_box, self.unresolved_box, self.marker_box, self.protected_box,
            self.footprint_box, self.details_button, self.copy_button,
            self.remove_solids_button, self.clear_button, self.settings_button,
        ):
            widget.setEnabled(enabled)
        if not enabled:
            self.status.setText("Select a {} to analyse.".format(self.entity_kind))
            return
        entity_id = self.entity_id(config)
        self.settings = normalise_chair_analysis_settings(config.get("chair_analysis_settings"))
        analysis_status = chair_analysis_effective_status(self.doc, self.entity_kind, config)
        solid_status = chair_solid_effective_status(self.doc, self.entity_kind, config)
        self.status.setText("Chair positions: {}. Physical chairs: {}. Production ready: No.".format(analysis_status, solid_status))
        cached = _chair_read_cached_result(self.doc, self.entity_kind, entity_id)
        solid = _chair_solid_object(self.doc, self.entity_kind, entity_id)
        current_analysis = cached is not None and analysis_status not in (CHAIR_STATUS_NOT_ANALYSED, CHAIR_STATUS_STALE)
        self.generate_button.setEnabled(current_analysis)
        self.validate_button.setEnabled(solid is not None and solid_status != CHAIR_SOLID_STATUS_STALE)
        self.remove_solids_button.setEnabled(solid is not None or _chair_unresolved_marker_object(self.doc, self.entity_kind, entity_id) is not None)
        self.details_button.setEnabled(cached is not None)
        self.copy_button.setEnabled(cached is not None)
        for box, value in (
            (self.marker_box, self.settings["markers_visible"]),
            (self.protected_box, self.settings["protected_markers_visible"]),
            (self.footprint_box, self.settings["footprints_visible"]),
            (self.solid_box, bool(solid is not None and getattr(getattr(solid, "ViewObject", None), "Visibility", False))),
            (self.unresolved_box, bool(_chair_unresolved_marker_object(self.doc, self.entity_kind, entity_id) is not None and getattr(getattr(_chair_unresolved_marker_object(self.doc, self.entity_kind, entity_id), "ViewObject", None), "Visibility", False))),
        ):
            box.blockSignals(True); box.setChecked(bool(value)); box.blockSignals(False)

    def _refresh_parent(self, entity_id):
        if callable(self.refresh_callback):
            self.refresh_callback(entity_id)
        self.refresh()

    def run_analysis(self):
        config = self.current_config()
        if not config:
            return
        try:
            self.settings.update({
                "markers_visible": self.marker_box.isChecked(),
                "protected_markers_visible": self.protected_box.isChecked(),
                "footprints_visible": self.footprint_box.isChecked(),
                "physical_solids_visible": self.solid_box.isChecked(),
                "unresolved_markers_visible": self.unresolved_box.isChecked(),
            })
            analyse_entity_chair_positions(self.doc, self.entity_kind, self.entity_id(config), self.settings)
            self._refresh_parent(self.entity_id(config))
        except Exception as error:
            QtWidgets.QMessageBox.critical(self, versioned_dialog_title("Chair analysis error"), str(error))
        self.refresh()

    def generate_solids(self):
        config = self.current_config()
        if not config:
            return
        try:
            self.settings["physical_solids_visible"] = self.solid_box.isChecked()
            result = generate_supported_chair_solids(self.doc, self.entity_kind, self.entity_id(config), self.settings)
            self.status.setText("{}; {} chair bodies; production ready: No.".format(result.get("status"), result.get("generated_count")))
            self._refresh_parent(self.entity_id(config))
        except Exception as error:
            QtWidgets.QMessageBox.critical(self, versioned_dialog_title("Physical chair generation error"), str(error))
        self.refresh()

    def validate_fit(self):
        config = self.current_config()
        if not config:
            return
        try:
            result = validate_generated_chair_solids(self.doc, self.entity_kind, self.entity_id(config), self.settings)
            self.status.setText("{}; production ready: No.".format(result.get("physical_fit_status") or result.get("status")))
            self._refresh_parent(self.entity_id(config))
        except Exception as error:
            QtWidgets.QMessageBox.critical(self, versioned_dialog_title("Chair physical-fit validation error"), str(error))
        self.refresh()

    def change_solid_visibility(self):
        config = self.current_config()
        if config:
            set_chair_solid_visibility(self.doc, self.entity_kind, self.entity_id(config), self.solid_box.isChecked())

    def change_unresolved_visibility(self):
        config = self.current_config()
        if not config:
            return
        try:
            set_unresolved_chair_visibility(self.doc, self.entity_kind, self.entity_id(config), self.unresolved_box.isChecked())
        except Exception as error:
            QtWidgets.QMessageBox.critical(self, versioned_dialog_title("Unresolved chair display error"), str(error))
        self.refresh()

    def change_visibility(self):
        config = self.current_config()
        if not config:
            return
        set_chair_analysis_visibility(
            self.doc, self.entity_kind, self.entity_id(config),
            markers=self.marker_box.isChecked(),
            protected=self.protected_box.isChecked(),
            footprints=self.footprint_box.isChecked(),
        )

    def show_details(self):
        config = self.current_config()
        if config:
            result = _chair_read_cached_result(self.doc, self.entity_kind, self.entity_id(config))
            QtWidgets.QMessageBox.information(self, versioned_dialog_title("Chair details"), chair_analysis_summary(result, True))

    def copy_summary(self):
        config = self.current_config()
        if not config:
            return
        result = _chair_read_cached_result(self.doc, self.entity_kind, self.entity_id(config))
        try:
            QtWidgets.QApplication.clipboard().setText(chair_analysis_summary(result, True))
        except Exception:
            pass

    def remove_solids(self):
        config = self.current_config()
        if not config:
            return
        try:
            remove_generated_chair_solids(self.doc, self.entity_kind, self.entity_id(config))
            self._refresh_parent(self.entity_id(config))
        except Exception as error:
            QtWidgets.QMessageBox.critical(self, versioned_dialog_title("Remove chair solids error"), str(error))
        self.refresh()

    def clear_display(self):
        config = self.current_config()
        if not config:
            return
        clear_chair_analysis_display(self.doc, self.entity_kind, self.entity_id(config))
        try:
            _document_recompute(self.doc)
        except Exception:
            pass
        self.refresh()

    def edit_settings(self):
        dialog = ChairAnalysisSettingsDialog(self.settings, self)
        if dialog.exec_() != QtWidgets.QDialog.Accepted:
            return
        self.settings = dialog.values()
        self.settings.update({
            "markers_visible": self.marker_box.isChecked(),
            "protected_markers_visible": self.protected_box.isChecked(),
            "footprints_visible": self.footprint_box.isChecked(),
            "physical_solids_visible": self.solid_box.isChecked(),
            "unresolved_markers_visible": self.unresolved_box.isChecked(),
        })
        self.status.setText(CHAIR_STATUS_STALE)


def _chair_guided_action(panel, entity_kind, config):
    kind = str(entity_kind or "").lower()
    entity_id = str(config.get("turnout_id") or config.get("crossover_id") or "")
    analysis_status = chair_analysis_effective_status(panel.doc, kind, config)
    if analysis_status in (CHAIR_STATUS_NOT_ANALYSED, CHAIR_STATUS_STALE):
        panel.chair_analysis_panel.run_analysis()
        return "analysis"
    solid_status = chair_solid_effective_status(panel.doc, kind, config)
    if solid_status in (CHAIR_SOLID_STATUS_NOT_GENERATED, CHAIR_SOLID_STATUS_STALE):
        panel.chair_analysis_panel.generate_solids()
        return "generation"
    state = _chair_physical_state_from_object(_chair_solid_object(panel.doc, kind, entity_id)) or {}
    if not bool(state.get("physical_fit_validated")):
        panel.chair_analysis_panel.validate_fit()
        return "validation"
    return "complete"


def _chair_guided_step_values(doc, entity_kind, config):
    kind = str(entity_kind or "").lower()
    entity_id = str(config.get("turnout_id") or config.get("crossover_id") or "")
    analysis_status = chair_analysis_effective_status(doc, kind, config)
    if analysis_status in (CHAIR_STATUS_NOT_ANALYSED, CHAIR_STATUS_STALE):
        return analysis_status, "ready", "Analyse chair positions", True
    solid_status = chair_solid_effective_status(doc, kind, config)
    if solid_status in (CHAIR_SOLID_STATUS_NOT_GENERATED, CHAIR_SOLID_STATUS_STALE):
        return "{}; {}".format(analysis_status, solid_status), "ready", "Generate supported chair solids", True
    state = _chair_physical_state_from_object(_chair_solid_object(doc, kind, entity_id)) or {}
    if int(state.get("physical_fit_failure_count") or 0):
        return "{}; {} physical-fit failure(s).".format(solid_status, state.get("physical_fit_failure_count")), "attention", "Validate physical chair fit", True
    if not bool(state.get("physical_fit_validated")):
        return solid_status, "ready", "Validate physical chair fit", True
    message = "{}; {} S1/S1J bodies fit-validated. Special chairs and keys remain analytical, so production readiness is still false.".format(
        solid_status, int(state.get("generated_count") or 0)
    )
    return message, "attention", "Revalidate physical chair fit", True


def _crossover_guided_chair_primary_v12(self):
    config = self.current_config()
    if config is not None:
        _chair_guided_action(self, "crossover", config)
    self.update_guided_workflow()


def _turnout_guided_chair_primary_v12(self):
    config = self.current_turnout_config()
    if config is not None:
        _chair_guided_action(self, "turnout", config)
    self.update_guided_workflow()


def _crossover_update_guided_workflow_v12(self):
    _A8A7B11_CROSSOVER_UPDATE_GUIDED_WORKFLOW(self)
    config = self.current_config()
    if config is None:
        return
    status, state, text, enabled = _chair_guided_step_values(self.doc, "crossover", config)
    cached = _chair_read_cached_result(self.doc, "crossover", str(config.get("crossover_id") or "")) is not None
    self.workflow_panel.set_step(2, status, state, text, enabled, "Show chair details" if cached else "Chair settings", True)


def _turnout_update_guided_workflow_v12(self):
    _A8A7B11_TURNOUT_UPDATE_GUIDED_WORKFLOW(self)
    config = self.current_turnout_config()
    if config is None:
        return
    status, state, text, enabled = _chair_guided_step_values(self.doc, "turnout", config)
    cached = _chair_read_cached_result(self.doc, "turnout", str(config.get("turnout_id") or "")) is not None
    self.workflow_panel.set_step(2, status, state, text, enabled and not bool(self.editing_turnout_id), "Show chair details" if cached else "Chair settings", not bool(self.editing_turnout_id))


def _crossover_run_next_guided_step_v12(self):
    config = self.current_config()
    if config is not None and crossover_b4_effective_status(self.doc, config) == CROSSOVER_B4_STATUS_CLEAR:
        action = _chair_guided_action(self, "crossover", config)
        if action != "complete":
            self.update_guided_workflow()
            return
    _A8A7B11_CROSSOVER_RUN_NEXT_GUIDED_STEP(self)


def _turnout_run_next_guided_step_v12(self):
    config = self.current_turnout_config()
    if config is not None and not self.editing_turnout_id:
        revision = int(config.get("timber_geometry_revision") or 0)
        timber_outlines = bool(config.get("timber_outlines", config.get("timber_references", True)))
        if revision >= TURNOUT_TIMBER_GEOMETRY_REVISION and timber_outlines:
            action = _chair_guided_action(self, "turnout", config)
            if action != "complete":
                self.update_guided_workflow()
                return
    _A8A7B11_TURNOUT_RUN_NEXT_GUIDED_STEP(self)


CrossoverManagerPanel.guided_chair_primary = _crossover_guided_chair_primary_v12
CrossoverManagerPanel.update_guided_workflow = _crossover_update_guided_workflow_v12
CrossoverManagerPanel.run_next_guided_step = _crossover_run_next_guided_step_v12
TurnoutManagerDialog.guided_turnout_chair_primary = _turnout_guided_chair_primary_v12
TurnoutManagerDialog.update_guided_workflow = _turnout_update_guided_workflow_v12
TurnoutManagerDialog.run_next_guided_step = _turnout_run_next_guided_step_v12

# ---------------------------------------------------------------------------
# A8A7B13 lightweight 2D chair workflow refinement.
#
# Routine work now stops at a prominent plan-view chair layout.  The bounded
# model-only timber support calculation is a separate guided stage, followed by
# analytical fit validation and lightweight Part wires.  Detailed S1/S1J solids
# remain available only as an explicit export-preparation action.
# ---------------------------------------------------------------------------
CHAIR_MODEL_SUPPORT_STATUS_PROPERTY = "ChairModelSupportStatus"
CHAIR_MODEL_SUPPORT_RESULT_PROPERTY = "ChairModelSupportResultJSON"
CHAIR_2D_LAYOUT_STATUS_PROPERTY = "Chair2DLayoutStatus"
CHAIR_2D_LAYOUT_RESULT_PROPERTY = "Chair2DLayoutResultJSON"

CHAIR_MODEL_SUPPORT_STATUS_NOT_PREPARED = "Model timber support not prepared"
CHAIR_MODEL_SUPPORT_STATUS_STALE = "Model timber support is stale"
CHAIR_MODEL_SUPPORT_STATUS_CLEAR = "No model timber widening required"
CHAIR_MODEL_SUPPORT_STATUS_APPLIED = "Bounded model timber widening prepared"
CHAIR_MODEL_SUPPORT_STATUS_BLOCKED = "Model timber widening is blocked"

CHAIR_2D_LAYOUT_STATUS_NOT_BUILT = "2D chair layout not built"
CHAIR_2D_LAYOUT_STATUS_STALE = "2D chair layout is stale"
CHAIR_2D_LAYOUT_STATUS_VALIDATED = "2D chair layout and fit validated"
CHAIR_2D_LAYOUT_STATUS_FAILED = "2D chair layout has production-critical fit failures"

CHAIR_2D_LAYOUT_GROUP_ROLE = "Chair2DLayoutDisplay"
CHAIR_2D_FOOTPRINT_ROLE = "Chair2DFootprints"
CHAIR_2D_SUPPORT_ROLE = "Chair2DModelSupportOutlines"
CHAIR_2D_FAILURE_ROLE = "Chair2DFitFailureMarkers"
CHAIR_2D_UNRESOLVED_ROLE = "Chair2DUnresolvedPositions"
CHAIR_2D_ROLES = (
    CHAIR_2D_LAYOUT_GROUP_ROLE,
    CHAIR_2D_FOOTPRINT_ROLE,
    CHAIR_2D_SUPPORT_ROLE,
    CHAIR_2D_FAILURE_ROLE,
    CHAIR_2D_UNRESOLVED_ROLE,
)

_A8A7B13_ENTITY_OBJECTS_WITHOUT_LAYOUT = _chair_entity_objects
_A8A7B13_CLEAR_DISPLAY_WITHOUT_LAYOUT = clear_chair_analysis_display
_A8A7B13_CHAIR_SUMMARY_WITHOUT_LAYOUT = chair_analysis_summary
_A8A7B13_PANEL_INIT_WITHOUT_2D = ChairAnalysisPanel.__init__
_A8A7B13_PANEL_REFRESH_WITHOUT_2D = ChairAnalysisPanel.refresh
_A8A7B13_GENERATION_CONTEXT_WITHOUT_SETTINGS_CHECK = _chair_generation_context


def _chair_generation_context(doc, entity_kind, entity_id, settings=None):
    """Require physical/layout settings to match the stored chair analysis."""
    kind, config, analysis, normalised, rails, timbers = _A8A7B13_GENERATION_CONTEXT_WITHOUT_SETTINGS_CHECK(
        doc, entity_kind, entity_id, settings
    )
    current_signature = _chair_geometry_signature(kind, config, normalised, rails, timbers)
    if str(current_signature or "") != str(analysis.get("geometry_signature") or ""):
        raise ValueError(
            "Chair settings have changed since the stored analysis. Analyse chair positions again before preparing model support, building the 2D layout or creating export chair solids."
        )
    return kind, config, analysis, normalised, rails, timbers


def _chair_entity_objects(doc, entity_kind, entity_id):
    """Keep lightweight 2D display objects out of persistent metadata passes."""
    return [
        obj for obj in _A8A7B13_ENTITY_OBJECTS_WITHOUT_LAYOUT(doc, entity_kind, entity_id)
        if object_string_property(obj, "GeneratedRole", "") not in set(CHAIR_2D_ROLES)
    ]


def _chair_2d_objects(doc, entity_kind, entity_id, roles=None):
    kind = str(entity_kind or "").lower()
    property_name = TURNOUT_ID_PROPERTY if kind == "turnout" else CROSSOVER_ID_PROPERTY
    wanted = set(roles or CHAIR_2D_ROLES)
    return [
        obj for obj in list(doc.Objects)
        if object_string_property(obj, property_name, "") == str(entity_id)
        and object_string_property(obj, "GeneratedRole", "") in wanted
    ]


def _chair_remove_2d_display(doc, entity_kind, entity_id):
    objects = _chair_2d_objects(doc, entity_kind, entity_id)
    objects.sort(key=lambda obj: object_string_property(obj, "GeneratedRole", "") == CHAIR_2D_LAYOUT_GROUP_ROLE)
    removed = 0
    for obj in objects:
        try:
            doc.removeObject(str(obj.Name))
            removed += 1
        except Exception:
            pass
    return removed


def clear_chair_analysis_display(doc, entity_kind, entity_id):
    removed = _A8A7B13_CLEAR_DISPLAY_WITHOUT_LAYOUT(doc, entity_kind, entity_id)
    return removed + _chair_remove_2d_display(doc, entity_kind, entity_id)


def _chair_cached_support_state(doc, entity_kind, entity_id):
    result = _chair_read_cached_result(doc, entity_kind, entity_id)
    state = dict((result or {}).get("model_timber_support_state") or {})
    return state if state else None


def _chair_cached_2d_state(doc, entity_kind, entity_id):
    result = _chair_read_cached_result(doc, entity_kind, entity_id)
    state = dict((result or {}).get("chair_2d_layout_state") or {})
    return state if state else None


def chair_model_support_effective_status(doc, entity_kind, config):
    cfg = dict(config or {})
    kind = str(entity_kind or "").lower()
    entity_id = str(cfg.get("turnout_id") or cfg.get("crossover_id") or "")
    analysis_status = chair_analysis_effective_status(doc, kind, cfg)
    if analysis_status in (CHAIR_STATUS_NOT_ANALYSED, CHAIR_STATUS_STALE):
        return CHAIR_MODEL_SUPPORT_STATUS_NOT_PREPARED if analysis_status == CHAIR_STATUS_NOT_ANALYSED else CHAIR_MODEL_SUPPORT_STATUS_STALE
    result = _chair_read_cached_result(doc, kind, entity_id)
    state = dict((result or {}).get("model_timber_support_state") or {})
    if not state:
        return CHAIR_MODEL_SUPPORT_STATUS_NOT_PREPARED
    if str(state.get("source_analysis_signature") or "") != str((result or {}).get("geometry_signature") or ""):
        return CHAIR_MODEL_SUPPORT_STATUS_STALE
    return str(state.get("status") or CHAIR_MODEL_SUPPORT_STATUS_NOT_PREPARED)


def chair_2d_layout_effective_status(doc, entity_kind, config):
    cfg = dict(config or {})
    kind = str(entity_kind or "").lower()
    entity_id = str(cfg.get("turnout_id") or cfg.get("crossover_id") or "")
    support_status = chair_model_support_effective_status(doc, kind, cfg)
    if support_status in (CHAIR_MODEL_SUPPORT_STATUS_NOT_PREPARED, CHAIR_MODEL_SUPPORT_STATUS_STALE):
        return CHAIR_2D_LAYOUT_STATUS_NOT_BUILT if support_status == CHAIR_MODEL_SUPPORT_STATUS_NOT_PREPARED else CHAIR_2D_LAYOUT_STATUS_STALE
    result = _chair_read_cached_result(doc, kind, entity_id)
    state = dict((result or {}).get("chair_2d_layout_state") or {})
    if not state:
        return CHAIR_2D_LAYOUT_STATUS_NOT_BUILT
    support_state = dict((result or {}).get("model_timber_support_state") or {})
    if str(state.get("source_analysis_signature") or "") != str((result or {}).get("geometry_signature") or ""):
        return CHAIR_2D_LAYOUT_STATUS_STALE
    if str(state.get("support_signature") or "") != str(support_state.get("support_signature") or ""):
        return CHAIR_2D_LAYOUT_STATUS_STALE
    return str(state.get("status") or CHAIR_2D_LAYOUT_STATUS_NOT_BUILT)


def _chair_write_2d_workflow_state(doc, entity_kind, config, analysis_result, support_state=None, layout_state=None):
    kind = str(entity_kind or "").lower()
    updated = dict(config or {})
    result = dict(analysis_result or {})
    if support_state is not None:
        support_state = dict(support_state or {})
        result["model_timber_support_state"] = support_state
        result["model_timber_support_changes_applied"] = bool(support_state.get("changes_applied"))
        result["physical_model_timber_support_adjustments"] = list(support_state.get("adjustments") or [])
        updated["chair_model_support_status"] = str(support_state.get("status") or CHAIR_MODEL_SUPPORT_STATUS_NOT_PREPARED)
        updated["chair_model_support_signature"] = str(support_state.get("support_signature") or "")
        updated["chair_model_support_widening_applied"] = bool(support_state.get("changes_applied"))
        updated["chair_model_support_timber_count"] = int(support_state.get("adjusted_timber_count") or 0)
        updated["chair_maximum_model_support_extension_per_side"] = float(support_state.get("maximum_extension_per_side") or 0.0)
    if layout_state is not None:
        layout_state = dict(layout_state or {})
        result["chair_2d_layout_state"] = layout_state
        updated["chair_2d_layout_status"] = str(layout_state.get("status") or CHAIR_2D_LAYOUT_STATUS_NOT_BUILT)
        updated["chair_2d_layout_signature"] = str(layout_state.get("layout_signature") or "")
        updated["chair_2d_fit_validated"] = bool(layout_state.get("fit_validated"))
        updated["chair_2d_fit_failure_count"] = int(layout_state.get("physical_fit_failure_count") or 0)
    updated["chair_solids_complete"] = False
    updated["chair_final_validation_complete"] = False
    updated["production_ready"] = False
    settings_obj = _chair_update_configuration_only(doc, kind, updated)
    properties = [
        ensure_property(settings_obj, "App::PropertyString", CHAIR_MODEL_SUPPORT_STATUS_PROPERTY, "Chair 2D workflow", "Current bounded model-timber support status"),
        ensure_property(settings_obj, "App::PropertyString", CHAIR_MODEL_SUPPORT_RESULT_PROPERTY, "Chair 2D workflow", "Stored model-timber support calculation"),
        ensure_property(settings_obj, "App::PropertyString", CHAIR_2D_LAYOUT_STATUS_PROPERTY, "Chair 2D workflow", "Current lightweight 2D chair-layout status"),
        ensure_property(settings_obj, "App::PropertyString", CHAIR_2D_LAYOUT_RESULT_PROPERTY, "Chair 2D workflow", "Stored 2D chair-layout and fit result"),
    ]
    stored_support = dict(result.get("model_timber_support_state") or {})
    stored_layout = dict(result.get("chair_2d_layout_state") or {})
    _set_persistent_property_if_changed(settings_obj, CHAIR_MODEL_SUPPORT_STATUS_PROPERTY, str(stored_support.get("status") or CHAIR_MODEL_SUPPORT_STATUS_NOT_PREPARED))
    _set_persistent_property_if_changed(settings_obj, CHAIR_MODEL_SUPPORT_RESULT_PROPERTY, json.dumps(stored_support, sort_keys=True))
    _set_persistent_property_if_changed(settings_obj, CHAIR_2D_LAYOUT_STATUS_PROPERTY, str(stored_layout.get("status") or CHAIR_2D_LAYOUT_STATUS_NOT_BUILT))
    _set_persistent_property_if_changed(settings_obj, CHAIR_2D_LAYOUT_RESULT_PROPERTY, json.dumps(stored_layout, sort_keys=True))
    _set_persistent_property_if_changed(settings_obj, CHAIR_ANALYSIS_RESULT_PROPERTY, json.dumps(result, sort_keys=True))
    set_read_only(settings_obj, properties)
    return updated, result


def prepare_chair_model_support(doc, entity_kind, entity_id, settings=None):
    """Prepare bounded model-only timber side extensions without building solids."""
    kind, config, analysis, settings, rails, timbers = _chair_generation_context(
        doc, entity_kind, entity_id, settings
    )
    plan = _chair_build_solid_plan(doc, kind, config, analysis, rails, timbers, settings)
    adjustments = list(plan.get("model_timber_support_adjustments") or [])
    exceeded = [item for item in adjustments if bool(item.get("limit_exceeded"))]
    adjusted = [item for item in adjustments if bool(item.get("applied"))]
    required = [item for item in adjustments if float(item.get("maximum_extension_per_side") or 0.0) > 1.0e-9]
    auto_enabled = bool(settings.get("model_support_auto_apply_enabled", True))
    disabled_required = required if required and not auto_enabled else []
    maximum = max([float(item.get("maximum_extension_per_side") or 0.0) for item in adjustments] or [0.0])
    status = (
        CHAIR_MODEL_SUPPORT_STATUS_BLOCKED if (exceeded or disabled_required) else
        CHAIR_MODEL_SUPPORT_STATUS_APPLIED if adjusted else
        CHAIR_MODEL_SUPPORT_STATUS_CLEAR
    )
    blocking_reason = (
        "Required model-only timber widening is disabled in the chair settings."
        if disabled_required else
        "One or more required timber-side extensions exceed the configured automatic limit."
        if exceeded else ""
    )
    state = {
        "schema_version": CHAIR_SOLID_SCHEMA_VERSION,
        "macro_version": MACRO_VERSION_NUMBER,
        "entity_kind": kind,
        "entity_id": str(entity_id),
        "status": status,
        "prepared": not bool(exceeded or disabled_required),
        "source_analysis_signature": str(analysis.get("geometry_signature") or ""),
        "support_signature": str(plan.get("solid_signature") or ""),
        "adjustments": adjustments,
        "changes_applied": bool(adjusted),
        "adjusted_timber_count": len(adjusted),
        "limit_exceeded_count": len(exceeded),
        "disabled_required_count": len(disabled_required),
        "blocking_reason": blocking_reason,
        "maximum_extension_per_side": maximum,
        "configured_limit_per_side": float(settings.get("preferred_maximum_model_support_extension_per_side") or 0.0),
        "rounding_increment_mm": float(CHAIR_MODEL_SUPPORT_INCREMENT_MM),
        "prototype_timber_references_changed": False,
        "rail_geometry_changed": False,
    }
    layout_reset = {
        "schema_version": CHAIR_SOLID_SCHEMA_VERSION,
        "macro_version": MACRO_VERSION_NUMBER,
        "entity_kind": kind,
        "entity_id": str(entity_id),
        "status": CHAIR_2D_LAYOUT_STATUS_NOT_BUILT,
        "source_analysis_signature": str(analysis.get("geometry_signature") or ""),
        "support_signature": str(plan.get("solid_signature") or ""),
        "layout_signature": "",
        "fit_validated": False,
        "physical_fit_failure_count": 0,
        "display_generated": False,
        "production_ready": False,
    }
    transaction_open = False
    try:
        doc.openTransaction("Prepare Version {} model timber support {}".format(MACRO_VERSION_NUMBER, entity_id))
        transaction_open = True
        _chair_remove_2d_display(doc, kind, entity_id)
        _chair_mark_solid_stale(doc, kind, entity_id, "The model-timber support plan changed; rebuild export chair solids.")
        _chair_write_2d_workflow_state(doc, kind, config, analysis, state, layout_reset)
        _document_recompute(doc)
        doc.commitTransaction()
        transaction_open = False
    except Exception:
        if transaction_open:
            try:
                doc.abortTransaction()
            except Exception:
                pass
        raise
    return state


def _chair_closed_wire(points, z_height):
    raw = list(points or [])
    if len(raw) < 3:
        return None
    vectors = [vector_xy(float(point[0]), float(point[1])) for point in raw]
    vectors.append(vectors[0])
    return _turnout_wire(vectors, float(z_height))


def _chair_make_2d_feature(doc, group, entity_kind, entity_id, set_id, role, label, shapes, line_colour, line_width, visible=True):
    shapes = [shape for shape in list(shapes or []) if shape is not None]
    if not shapes:
        return None
    obj = doc.addObject("Part::Feature", unique_internal_name(doc, "{}_{}".format(role, str(entity_id).replace("-", "_"))))
    obj.Label = label
    obj.Shape = _turnout_compound(shapes, label)
    _chair_tag_auxiliary_object(obj, entity_kind, entity_id, set_id, role)
    group.addObject(obj)
    try:
        obj.ViewObject.Visibility = bool(visible)
        obj.ViewObject.LineColor = tuple(line_colour)
        obj.ViewObject.LineWidth = float(line_width)
    except Exception:
        pass
    return obj


def _create_chair_2d_layout_display(doc, entity_kind, config, analysis, plan, validation, timber_records):
    kind = str(entity_kind or "").lower()
    entity_id = str(config.get("turnout_id") or config.get("crossover_id") or "")
    set_id = str(config.get("template_set_id") or "")
    _chair_remove_2d_display(doc, kind, entity_id)
    group = doc.addObject("App::DocumentObjectGroup", unique_internal_name(doc, "Chair2DLayout_{}".format(entity_id.replace("-", "_"))))
    group.Label = "{} 2D chair layout".format(entity_id)
    _chair_tag_auxiliary_object(group, kind, entity_id, set_id, CHAIR_2D_LAYOUT_GROUP_ROLE)
    try:
        group.ViewObject.Visibility = True
    except Exception:
        pass

    levels = _chair_display_z_levels(doc, kind, config)
    footprint_z = float(levels["footprints"]) + 0.080
    support_z = footprint_z - 0.025
    failure_z = footprint_z + 0.050
    unresolved_z = failure_z + 0.025

    effective_timbers, adjustments = _chair_apply_physical_model_support(plan, timber_records, analysis.get("settings"))
    effective_by_id = {str(item.get("stable_identity") or ""): item for item in effective_timbers}
    applied_ids = {str(item.get("timber_identity") or "") for item in adjustments if bool(item.get("applied"))}
    support_shapes = []
    for timber_id in sorted(applied_ids):
        timber = effective_by_id.get(timber_id)
        if timber is not None:
            support_shapes.append(_chair_closed_wire(timber.get("outline_polygon") or timber.get("collision_polygon") or [], support_z))

    critical_findings = [item for item in list(validation.get("findings") or []) if str(item.get("severity") or "") == CHAIR_SEVERITY_CRITICAL]
    failed_chair_ids = {str(item.get("chair_position_identity") or "") for item in critical_findings if item.get("chair_position_identity")}
    failed_timber_ids = {str(item.get("timber_identity") or "") for item in critical_findings if item.get("timber_identity")}
    footprint_shapes = []
    failure_shapes = []
    for instance in list(plan.get("instances") or []):
        wire = _chair_closed_wire(instance.get("physical_footprint_polygon") or [], footprint_z)
        footprint_shapes.append(wire)
        if str(instance.get("chair_position_identity") or "") in failed_chair_ids:
            failure_shapes.append(_chair_closed_wire(instance.get("physical_footprint_polygon") or [], failure_z))
    for timber_id in sorted(failed_timber_ids):
        timber = effective_by_id.get(timber_id)
        if timber is not None:
            failure_shapes.append(_chair_closed_wire(timber.get("outline_polygon") or timber.get("collision_polygon") or [], failure_z))

    positions_by_id = {
        str(item.get("stable_chair_position_identity") or ""): item
        for item in list(analysis.get("positions") or [])
    }
    unresolved_shapes = []
    for item in list(plan.get("analytical_only") or []):
        if bool(item.get("deliberate_omission")):
            continue
        position = positions_by_id.get(str(item.get("chair_position_identity") or ""))
        if position is None:
            continue
        unresolved_shapes.extend(_chair_cross_wires(
            position.get("centre_point") or (0.0, 0.0),
            position.get("local_rail_tangent") or (1.0, 0.0),
            half_size=1.20,
            z_height=unresolved_z,
        ))

    _chair_make_2d_feature(
        doc, group, kind, entity_id, set_id, CHAIR_2D_SUPPORT_ROLE,
        "{} bounded model timber support outlines".format(entity_id), support_shapes,
        (0.95, 0.65, 0.10), 3.2, True,
    )
    _chair_make_2d_feature(
        doc, group, kind, entity_id, set_id, CHAIR_2D_FOOTPRINT_ROLE,
        "{} source-dimensional chair footprints".format(entity_id), footprint_shapes,
        (0.20, 0.55, 0.95), 2.5, True,
    )
    _chair_make_2d_feature(
        doc, group, kind, entity_id, set_id, CHAIR_2D_FAILURE_ROLE,
        "{} chair fit failures".format(entity_id), failure_shapes,
        (0.95, 0.15, 0.15), 4.0, True,
    )
    _chair_make_2d_feature(
        doc, group, kind, entity_id, set_id, CHAIR_2D_UNRESOLVED_ROLE,
        "{} unresolved special chair positions".format(entity_id), unresolved_shapes,
        (0.85, 0.20, 0.85), 3.2, True,
    )
    parent = production_parent_group_for_set(doc, set_id)
    if parent is not None:
        try:
            parent.addObject(group)
        except Exception:
            pass
    return group


def build_and_validate_chair_2d_layout(doc, entity_kind, entity_id, settings=None):
    """Build prominent plan-view chair footprints and validate without 3D solids."""
    kind, config, analysis, settings, rails, timbers = _chair_generation_context(
        doc, entity_kind, entity_id, settings
    )
    support_state = dict(analysis.get("model_timber_support_state") or {})
    if not support_state:
        raise ValueError("Prepare model timber support before building the 2D chair layout.")
    if str(support_state.get("status") or "") == CHAIR_MODEL_SUPPORT_STATUS_BLOCKED:
        raise ValueError("The model timber support stage is blocked because a required side extension exceeds the configured limit.")
    plan = _chair_build_solid_plan(doc, kind, config, analysis, rails, timbers, settings)
    if str(support_state.get("support_signature") or "") != str(plan.get("solid_signature") or ""):
        raise ValueError("The model timber support plan is stale. Prepare model timber support again.")
    validation = _chair_validate_solid_plan(plan, rails, timbers, settings)
    failure_count = int(validation.get("physical_fit_failure_count") or 0)
    status = CHAIR_2D_LAYOUT_STATUS_FAILED if failure_count else CHAIR_2D_LAYOUT_STATUS_VALIDATED
    layout_state = {
        "schema_version": CHAIR_SOLID_SCHEMA_VERSION,
        "macro_version": MACRO_VERSION_NUMBER,
        "entity_kind": kind,
        "entity_id": str(entity_id),
        "status": status,
        "source_analysis_signature": str(analysis.get("geometry_signature") or ""),
        "support_signature": str(support_state.get("support_signature") or ""),
        "layout_signature": str(plan.get("solid_signature") or ""),
        "fit_validated": failure_count == 0,
        "physical_fit_failure_count": failure_count,
        "supported_2d_chair_count": len(list(plan.get("instances") or [])),
        "analytical_only_count": len(list(plan.get("analytical_only") or [])),
        "unresolved_special_count": int(validation.get("unresolved_special_count") or 0),
        "key_direction_unresolved_count": int(validation.get("key_direction_unresolved_count") or 0),
        "model_timber_support_adjusted_count": int(validation.get("model_timber_support_adjusted_count") or 0),
        "maximum_model_support_extension_per_side": float(validation.get("maximum_model_support_extension_per_side") or 0.0),
        "findings": list(validation.get("findings") or []),
        "severity_counts": dict(validation.get("severity_counts") or {}),
        "readiness_blockers": list(validation.get("readiness_blockers") or []),
        "validation_time_ms": float(validation.get("validation_time_ms") or 0.0),
        "display_generated": True,
        "production_geometry_changed": False,
        "detailed_chair_solids_generated": False,
        "production_ready": False,
    }
    transaction_open = False
    try:
        doc.openTransaction("Build Version {} 2D chair layout {}".format(MACRO_VERSION_NUMBER, entity_id))
        transaction_open = True
        _create_chair_2d_layout_display(doc, kind, config, analysis, plan, validation, timbers)
        _chair_mark_solid_stale(doc, kind, entity_id, "The 2D chair layout was rebuilt; rebuild export chair solids if required.")
        _chair_write_2d_workflow_state(doc, kind, config, analysis, support_state, layout_state)
        _document_recompute(doc)
        doc.commitTransaction()
        transaction_open = False
    except Exception:
        if transaction_open:
            try:
                doc.abortTransaction()
            except Exception:
                pass
        raise
    return layout_state


def set_chair_2d_layout_visibility(doc, entity_kind, entity_id, visible):
    objects = _chair_2d_objects(doc, entity_kind, entity_id)
    if not objects and visible:
        return False
    changed = False
    for obj in objects:
        try:
            obj.ViewObject.Visibility = bool(visible)
            changed = True
        except Exception:
            pass
    return changed


def _chair_2d_layout_visible(doc, entity_kind, entity_id):
    objects = _chair_2d_objects(doc, entity_kind, entity_id, (
        CHAIR_2D_FOOTPRINT_ROLE, CHAIR_2D_SUPPORT_ROLE, CHAIR_2D_FAILURE_ROLE, CHAIR_2D_UNRESOLVED_ROLE,
    ))
    return bool(objects) and any(bool(getattr(getattr(obj, "ViewObject", None), "Visibility", False)) for obj in objects)


def chair_analysis_summary(result, include_findings=True):
    base = _A8A7B13_CHAIR_SUMMARY_WITHOUT_LAYOUT(result, include_findings)
    support = dict((result or {}).get("model_timber_support_state") or {})
    layout = dict((result or {}).get("chair_2d_layout_state") or {})
    lines = [base, "", "Lightweight 2D chair workflow:"]
    if support:
        lines.extend([
            "- Model timber support: {}".format(support.get("status") or CHAIR_MODEL_SUPPORT_STATUS_NOT_PREPARED),
            "- Effective timbers widened: {}".format(int(support.get("adjusted_timber_count") or 0)),
            "- Maximum extension on one timber side: {:.3f} mm".format(float(support.get("maximum_extension_per_side") or 0.0)),
            "- Prototype timber references changed: No",
        ])
    else:
        lines.append("- Model timber support: not prepared")
    if layout:
        lines.extend([
            "- 2D layout: {}".format(layout.get("status") or CHAIR_2D_LAYOUT_STATUS_NOT_BUILT),
            "- Source-dimensional S1/S1J footprints displayed: {}".format(int(layout.get("supported_2d_chair_count") or 0)),
            "- 2D fit failures: {}".format(int(layout.get("physical_fit_failure_count") or 0)),
            "- Detailed 3D bodies: deferred to explicit export preparation",
        ])
    else:
        lines.append("- 2D layout: not built")
    return "\n".join(lines)


# Add specialist controls without burdening the ordinary guided view.
def _chair_panel_init_v13(self, doc, entity_kind, config_getter, refresh_callback=None, parent=None):
    _A8A7B13_PANEL_INIT_WITHOUT_2D(self, doc, entity_kind, config_getter, refresh_callback, parent)
    self.setTitle("Chair analysis, model support and 2D layout")
    layout = self.layout()
    self.support_button = QtWidgets.QPushButton("Prepare model timber support")
    self.layout_button = QtWidgets.QPushButton("Build 2D chair layout")
    self.layout_box = QtWidgets.QCheckBox("Show 2D chair layout")
    self.layout_box.setChecked(True)
    layout.addWidget(self.support_button, 4, 0, 1, 2)
    layout.addWidget(self.layout_button, 4, 2, 1, 2)
    layout.addWidget(self.layout_box, 4, 4, 1, 2)
    self.generate_button.setText("Build 3D chairs for export")
    self.validate_button.setText("Revalidate 3D export chairs")
    self.generate_button.setToolTip("Explicit export-preparation action. It builds the detailed S1/S1J compound only after the lightweight 2D layout has passed.")
    self.support_button.setToolTip("Calculates the smallest bounded model-only side extension needed by each rotated chair footprint. It does not alter rail geometry or prototype timber references.")
    self.layout_button.setToolTip("Creates prominent plan-view chair footprints and validates them against the effective model support without constructing 3D chair bodies.")
    self.layout_box.setToolTip("Shows or hides the lightweight plan-view chair layout, adjusted support outlines, failure overlays and unresolved special-position markers.")
    self.support_button.clicked.connect(self.prepare_model_support)
    self.layout_button.clicked.connect(self.build_2d_layout)
    self.layout_box.toggled.connect(self.change_2d_layout_visibility)
    self.refresh()


def _chair_panel_refresh_v13(self):
    _A8A7B13_PANEL_REFRESH_WITHOUT_2D(self)
    if not hasattr(self, "support_button"):
        return
    config = self.current_config()
    enabled = isinstance(config, dict)
    for widget in (getattr(self, "support_button", None), getattr(self, "layout_button", None), getattr(self, "layout_box", None)):
        if widget is not None:
            widget.setEnabled(enabled)
    if not enabled:
        return
    entity_id = self.entity_id(config)
    analysis_status = chair_analysis_effective_status(self.doc, self.entity_kind, config)
    support_status = chair_model_support_effective_status(self.doc, self.entity_kind, config)
    layout_status = chair_2d_layout_effective_status(self.doc, self.entity_kind, config)
    solid_status = chair_solid_effective_status(self.doc, self.entity_kind, config)
    analysis_current = analysis_status not in (CHAIR_STATUS_NOT_ANALYSED, CHAIR_STATUS_STALE)
    support_ready = support_status in (CHAIR_MODEL_SUPPORT_STATUS_CLEAR, CHAIR_MODEL_SUPPORT_STATUS_APPLIED)
    layout_valid = layout_status == CHAIR_2D_LAYOUT_STATUS_VALIDATED
    self.support_button.setEnabled(analysis_current)
    self.layout_button.setEnabled(support_ready)
    self.generate_button.setEnabled(layout_valid)
    layout_objects = bool(_chair_2d_objects(self.doc, self.entity_kind, entity_id))
    self.layout_box.setEnabled(layout_objects)
    self.layout_box.blockSignals(True)
    self.layout_box.setChecked(_chair_2d_layout_visible(self.doc, self.entity_kind, entity_id))
    self.layout_box.blockSignals(False)
    self.status.setText(
        "Chair positions: {}. Model support: {}. 2D layout: {}. 3D export chairs: {}. Production ready: No.".format(
            analysis_status, support_status, layout_status, solid_status
        )
    )


def _chair_panel_prepare_model_support(self):
    config = self.current_config()
    if not config:
        return
    try:
        state = prepare_chair_model_support(self.doc, self.entity_kind, self.entity_id(config), self.settings)
        if str(state.get("status") or "") == CHAIR_MODEL_SUPPORT_STATUS_BLOCKED:
            QtWidgets.QMessageBox.warning(
                self, versioned_dialog_title("Model timber support blocked"),
                "{} No 2D layout or 3D chair object was committed.".format(
                    str(state.get("blocking_reason") or "The bounded model-support calculation could not be applied.")
                ),
            )
        self._refresh_parent(self.entity_id(config))
    except Exception as error:
        QtWidgets.QMessageBox.critical(self, versioned_dialog_title("Model timber support error"), str(error))
    self.refresh()


def _chair_panel_build_2d_layout(self):
    config = self.current_config()
    if not config:
        return
    try:
        state = build_and_validate_chair_2d_layout(self.doc, self.entity_kind, self.entity_id(config), self.settings)
        set_chair_2d_layout_visibility(self.doc, self.entity_kind, self.entity_id(config), True)
        if int(state.get("physical_fit_failure_count") or 0):
            QtWidgets.QMessageBox.warning(
                self, versioned_dialog_title("2D chair fit needs review"),
                "The 2D layout was created, but {} production-critical fit failure(s) remain. Failed chair or timber outlines are shown in red.".format(
                    int(state.get("physical_fit_failure_count") or 0)
                ),
            )
        self._refresh_parent(self.entity_id(config))
    except Exception as error:
        QtWidgets.QMessageBox.critical(self, versioned_dialog_title("2D chair layout error"), str(error))
    self.refresh()


def _chair_panel_change_2d_visibility(self):
    config = self.current_config()
    if config:
        set_chair_2d_layout_visibility(self.doc, self.entity_kind, self.entity_id(config), self.layout_box.isChecked())


ChairAnalysisPanel.__init__ = _chair_panel_init_v13
ChairAnalysisPanel.refresh = _chair_panel_refresh_v13
ChairAnalysisPanel.prepare_model_support = _chair_panel_prepare_model_support
ChairAnalysisPanel.build_2d_layout = _chair_panel_build_2d_layout
ChairAnalysisPanel.change_2d_layout_visibility = _chair_panel_change_2d_visibility


# Guided-stage callbacks.  These are resolved by the seven-row constructor when
# the manager is created after this additive patch has been installed.
def _crossover_guided_model_support_primary_v13(self):
    self.chair_analysis_panel.prepare_model_support()
    self.update_guided_workflow()


def _crossover_guided_model_support_secondary_v13(self):
    self.chair_analysis_panel.show_details()
    self.update_guided_workflow()


def _crossover_guided_2d_layout_primary_v13(self):
    self.chair_analysis_panel.build_2d_layout()
    self.update_guided_workflow()


def _crossover_guided_2d_layout_secondary_v13(self):
    config = self.current_config()
    if config is not None:
        identifier = str(config.get("crossover_id") or "")
        present = bool(_chair_2d_objects(self.doc, "crossover", identifier))
        if not present:
            self.chair_analysis_panel.build_2d_layout()
        else:
            set_chair_2d_layout_visibility(self.doc, "crossover", identifier, True)
    self.update_guided_workflow()


def _crossover_guided_export_chairs_primary_v13(self):
    self.chair_analysis_panel.generate_solids()
    self.update_guided_workflow()


def _turnout_guided_model_support_primary_v13(self):
    self.chair_analysis_panel.prepare_model_support()
    self.update_guided_workflow()


def _turnout_guided_model_support_secondary_v13(self):
    self.chair_analysis_panel.show_details()
    self.update_guided_workflow()


def _turnout_guided_2d_layout_primary_v13(self):
    self.chair_analysis_panel.build_2d_layout()
    self.update_guided_workflow()


def _turnout_guided_2d_layout_secondary_v13(self):
    config = self.current_turnout_config()
    if config is not None:
        identifier = str(config.get("turnout_id") or "")
        present = bool(_chair_2d_objects(self.doc, "turnout", identifier))
        if not present:
            self.chair_analysis_panel.build_2d_layout()
        else:
            set_chair_2d_layout_visibility(self.doc, "turnout", identifier, True)
    self.update_guided_workflow()


def _turnout_guided_export_chairs_primary_v13(self):
    self.chair_analysis_panel.generate_solids()
    self.update_guided_workflow()


CrossoverManagerPanel.guided_model_support_primary = _crossover_guided_model_support_primary_v13
CrossoverManagerPanel.guided_model_support_secondary = _crossover_guided_model_support_secondary_v13
CrossoverManagerPanel.guided_2d_layout_primary = _crossover_guided_2d_layout_primary_v13
CrossoverManagerPanel.guided_2d_layout_secondary = _crossover_guided_2d_layout_secondary_v13
CrossoverManagerPanel.guided_export_chairs_primary = _crossover_guided_export_chairs_primary_v13
TurnoutManagerDialog.guided_turnout_model_support_primary = _turnout_guided_model_support_primary_v13
TurnoutManagerDialog.guided_turnout_model_support_secondary = _turnout_guided_model_support_secondary_v13
TurnoutManagerDialog.guided_turnout_2d_layout_primary = _turnout_guided_2d_layout_primary_v13
TurnoutManagerDialog.guided_turnout_2d_layout_secondary = _turnout_guided_2d_layout_secondary_v13
TurnoutManagerDialog.guided_turnout_export_chairs_primary = _turnout_guided_export_chairs_primary_v13


def _crossover_update_guided_workflow_v13(self):
    panel = getattr(self, "workflow_panel", None)
    if panel is None:
        return
    config = self.current_config()
    editing = bool(self.editing_crossover_id)
    extending = bool(self.extending_turnout_id)
    preview_current = False
    try:
        preview_current = self._last_preview_signature == self._preview_signature(self.proposed_values()) and self._last_preview_result is not None
    except Exception:
        preview_current = False

    if config is None:
        geometry_status = (
            "A valid geometry preview is ready. Create it transactionally when satisfied."
            if preview_current else
            ("The selected turnout is ready to extend. Confirm the second host and preview the crossover." if extending else "Choose or pick both hosts, the Host A chainage, arrangement and handing, then preview the geometry.")
        )
        panel.set_step(0, geometry_status, "ready", "Preview geometry", True, "Extend turnout" if extending else "Create crossover", bool(preview_current))
        waiting = (
            "Create a crossover before resolving timbering.",
            "Create and timber the crossover before analysing chair positions.",
            "Analyse chair positions before adjusting model timber support.",
            "Prepare bounded model timber support before building the 2D layout.",
            "Integration remains unavailable until the preceding checks pass.",
            "Finish and export actions remain unavailable until the 2D layout has passed.",
        )
        for index, message in enumerate(waiting, start=1):
            panel.set_step(index, message, "waiting", "Continue", False, "", False)
        panel.set_summary("The guided workflow uses lightweight 2D chair footprints during routine work and creates detailed 3D chair bodies only through the final export-preparation action.")
        panel.run_next_button.setText("Create previewed crossover" if preview_current else "Run next safe step")
        return

    identifier = str(config.get("crossover_id") or "the selected crossover")
    if editing:
        panel.set_step(0, "Editing {} transactionally. Preview the revised geometry, then apply it.".format(identifier), "ready", "Preview changes", True, "Apply changes", bool(preview_current))
    else:
        panel.set_step(0, "{} has accepted crossover geometry and topology.".format(identifier), "complete", "Edit position", self.edit_crossover_button.isEnabled(), "Show geometry details", True)

    integration_active = bool(config.get("integration_active", False))
    b4_status = crossover_b4_effective_status(self.doc, config)
    b4_clear = b4_status == CROSSOVER_B4_STATUS_CLEAR
    panel.set_step(1, self._operator_timber_status(b4_status), "complete" if b4_clear else "ready", "Rebuild automatic timbering" if b4_clear else "Resolve timbering automatically", not integration_active, "Show timber result" if config.get("b4_result") else "Analyse timbering", True)

    chair_status = chair_analysis_effective_status(self.doc, "crossover", config)
    chair_state = "ready" if chair_status in (CHAIR_STATUS_NOT_ANALYSED, CHAIR_STATUS_STALE) else ("attention" if chair_status in (CHAIR_STATUS_INCOMPLETE, CHAIR_STATUS_CONFLICTS, CHAIR_STATUS_CRITICAL) else "complete")
    chair_cached = _chair_read_cached_result(self.doc, "crossover", identifier) is not None
    panel.set_step(2, chair_status, chair_state, "Analyse chair positions", b4_clear and not integration_active, "Show chair details" if chair_cached else "Chair settings", True)

    support_status = chair_model_support_effective_status(self.doc, "crossover", config)
    support_state = "blocked" if support_status == CHAIR_MODEL_SUPPORT_STATUS_BLOCKED else ("ready" if support_status in (CHAIR_MODEL_SUPPORT_STATUS_NOT_PREPARED, CHAIR_MODEL_SUPPORT_STATUS_STALE) else "complete")
    support_enabled = chair_status not in (CHAIR_STATUS_NOT_ANALYSED, CHAIR_STATUS_STALE, CHAIR_STATUS_INCOMPLETE, CHAIR_STATUS_CONFLICTS, CHAIR_STATUS_CRITICAL) and not integration_active
    panel.set_step(3, support_status, support_state, "Prepare model support", support_enabled, "Support details", chair_cached)

    layout_status = chair_2d_layout_effective_status(self.doc, "crossover", config)
    layout_state = "attention" if layout_status == CHAIR_2D_LAYOUT_STATUS_FAILED else ("ready" if layout_status in (CHAIR_2D_LAYOUT_STATUS_NOT_BUILT, CHAIR_2D_LAYOUT_STATUS_STALE) else "complete")
    support_ready = support_status in (CHAIR_MODEL_SUPPORT_STATUS_CLEAR, CHAIR_MODEL_SUPPORT_STATUS_APPLIED)
    panel.set_step(4, layout_status, layout_state, "Build 2D chair layout" if layout_status != CHAIR_2D_LAYOUT_STATUS_VALIDATED else "Rebuild 2D chair layout", support_ready and not integration_active, "Show 2D layout", bool(_chair_2d_objects(self.doc, "crossover", identifier)))

    allowed = bool(config.get("host_integration_allowed")) and b4_clear and layout_status == CHAIR_2D_LAYOUT_STATUS_VALIDATED
    if integration_active:
        panel.set_step(5, crossover_host_integration_effective_status(self.doc, config), "complete", "Remove integration", True, "Integration details", True)
    elif allowed:
        panel.set_step(5, "Geometry, timbering and the lightweight 2D chair fit all report ready.", "ready", "Integrate hosts", True, "Integration details", True)
    else:
        reason = "Complete a valid 2D chair layout before host integration."
        if layout_status == CHAIR_2D_LAYOUT_STATUS_FAILED:
            reason = "The 2D chair layout contains production-critical fit failures."
        elif b4_clear and layout_status == CHAIR_2D_LAYOUT_STATUS_VALIDATED:
            reason = crossover_host_integration_effective_status(self.doc, config)
        panel.set_step(5, reason, "blocked", "Integrate hosts", False, "Integration details", True)

    solid_status = chair_solid_effective_status(self.doc, "crossover", config)
    export_ready = layout_status == CHAIR_2D_LAYOUT_STATUS_VALIDATED
    solid_complete = solid_status not in (CHAIR_SOLID_STATUS_NOT_GENERATED, CHAIR_SOLID_STATUS_STALE, CHAIR_SOLID_STATUS_FIT_FAILED)
    finish_state = "complete" if solid_complete else ("attention" if solid_status == CHAIR_SOLID_STATUS_FIT_FAILED else "ready")
    finish_message = (
        "Supported S1/S1J 3D export bodies are prepared; special chairs and keys remain analytical."
        if solid_complete else
        "Routine viewing remains 2D. Build detailed S1/S1J bodies only when preparing an export."
    )
    panel.set_step(6, finish_message, finish_state, "Prepare 3D export chairs", export_ready, "Convert to turnout", self.revert_button.isEnabled())
    panel.set_summary("Selected {}. The stable sequence is geometry, timbering, chair analysis, bounded model support, 2D fit validation, integration, then optional 3D export preparation.".format(identifier))
    panel.run_next_button.setText("Run next safe step")


def _turnout_update_guided_workflow_v13(self):
    panel = getattr(self, "workflow_panel", None)
    if panel is None:
        return
    config = self.current_turnout_config()
    editing = bool(self.editing_turnout_id)
    if config is None and not editing:
        messages = (
            (0, "Choose a host centreline, switch-toe chainage, orientation, handing and production options.", "ready", "Create turnout", self.create_button.isEnabled(), "", False),
            (1, "REA timbering will be built as part of the validated turnout geometry.", "waiting", "Timber options", True, "Show all controls", True),
            (2, "Create a turnout before analysing chair positions.", "waiting", "Analyse chairs", False, "", False),
            (3, "Analyse chair positions before adjusting model timber support.", "waiting", "Prepare model support", False, "", False),
            (4, "Prepare bounded model timber support before building the 2D layout.", "waiting", "Build 2D layout", False, "", False),
            (5, "Create and review the turnout before integrating it with the host template.", "waiting", "Integrate host", False, "", False),
            (6, "Finish and export actions remain unavailable until the 2D layout has passed.", "waiting", "Prepare 3D export chairs", False, "Convert to crossover", False),
        )
        for values in messages:
            panel.set_step(*values)
        panel.set_summary("The turnout workflow uses a prominent lightweight 2D chair layout for routine work and defers detailed 3D chair bodies to explicit export preparation.")
        panel.run_next_button.setText("Run next safe step")
        return

    selected = config or self.editing_original_config or {}
    identifier = str(selected.get("turnout_id") or self.editing_turnout_id or "the selected turnout")
    if editing:
        panel.set_step(0, "Editing {} transactionally. Review the controls, then apply or cancel.".format(identifier), "ready", "Apply turnout changes", self.apply_edit_button.isEnabled(), "Cancel edit", True)
    else:
        panel.set_step(0, "{} has validated turnout geometry on its host alignment.".format(identifier), "complete", "Create another turnout", self.create_button.isEnabled(), "Edit selected turnout", self.edit_button.isEnabled())

    revision = int(selected.get("timber_geometry_revision") or 0)
    timber_outlines = bool(selected.get("timber_outlines", selected.get("timber_references", True)))
    timber_ready = revision >= TURNOUT_TIMBER_GEOMETRY_REVISION and timber_outlines
    if timber_ready:
        panel.set_step(1, "Current source-driven REA timber outlines are included.", "complete", "Review timber options", not editing, "Show all controls", True)
    elif not timber_outlines:
        panel.set_step(1, "Timber outlines are disabled for this turnout. Edit the turnout to enable production timbering.", "attention", "Edit timber options", not editing, "Show all controls", True)
    else:
        panel.set_step(1, "Older timber geometry can be upgraded transactionally without moving the turnout.", "attention", "Upgrade timbering", not editing, "Show all controls", True)

    chair_status = chair_analysis_effective_status(self.doc, "turnout", selected)
    chair_state = "ready" if chair_status in (CHAIR_STATUS_NOT_ANALYSED, CHAIR_STATUS_STALE) else ("attention" if chair_status in (CHAIR_STATUS_INCOMPLETE, CHAIR_STATUS_CONFLICTS, CHAIR_STATUS_CRITICAL) else "complete")
    chair_cached = _chair_read_cached_result(self.doc, "turnout", identifier) is not None
    panel.set_step(2, chair_status, chair_state, "Analyse chair positions", timber_ready and not editing, "Show chair details" if chair_cached else "Chair settings", not editing)

    support_status = chair_model_support_effective_status(self.doc, "turnout", selected)
    support_state = "blocked" if support_status == CHAIR_MODEL_SUPPORT_STATUS_BLOCKED else ("ready" if support_status in (CHAIR_MODEL_SUPPORT_STATUS_NOT_PREPARED, CHAIR_MODEL_SUPPORT_STATUS_STALE) else "complete")
    support_enabled = chair_status not in (CHAIR_STATUS_NOT_ANALYSED, CHAIR_STATUS_STALE, CHAIR_STATUS_INCOMPLETE, CHAIR_STATUS_CONFLICTS, CHAIR_STATUS_CRITICAL) and not editing
    panel.set_step(3, support_status, support_state, "Prepare model support", support_enabled, "Support details", chair_cached and not editing)

    layout_status = chair_2d_layout_effective_status(self.doc, "turnout", selected)
    layout_state = "attention" if layout_status == CHAIR_2D_LAYOUT_STATUS_FAILED else ("ready" if layout_status in (CHAIR_2D_LAYOUT_STATUS_NOT_BUILT, CHAIR_2D_LAYOUT_STATUS_STALE) else "complete")
    support_ready = support_status in (CHAIR_MODEL_SUPPORT_STATUS_CLEAR, CHAIR_MODEL_SUPPORT_STATUS_APPLIED)
    panel.set_step(4, layout_status, layout_state, "Build 2D chair layout" if layout_status != CHAIR_2D_LAYOUT_STATUS_VALIDATED else "Rebuild 2D chair layout", support_ready and not editing, "Show 2D layout", bool(_chair_2d_objects(self.doc, "turnout", identifier)) and not editing)

    integrated = turnout_integration_by_id(self.doc, identifier) is not None
    integration_allowed = layout_status == CHAIR_2D_LAYOUT_STATUS_VALIDATED and not editing
    if integrated:
        panel.set_step(5, "The turnout is integrated reversibly with its host template.", "complete", "Remove integration", not editing, "Create reference copy", not editing)
    elif integration_allowed:
        panel.set_step(5, "The turnout remains a separate managed module; the 2D chair fit reports ready.", "ready", "Integrate with host", self.integrate_button.isEnabled(), "Create reference copy", self.reference_button.isEnabled())
    else:
        reason = "Complete a valid 2D chair layout before host integration."
        if layout_status == CHAIR_2D_LAYOUT_STATUS_FAILED:
            reason = "The 2D chair layout contains production-critical fit failures."
        panel.set_step(5, reason, "blocked", "Integrate with host", False, "Create reference copy", self.reference_button.isEnabled() and not editing)

    solid_status = chair_solid_effective_status(self.doc, "turnout", selected)
    export_ready = layout_status == CHAIR_2D_LAYOUT_STATUS_VALIDATED and not editing
    solid_complete = solid_status not in (CHAIR_SOLID_STATUS_NOT_GENERATED, CHAIR_SOLID_STATUS_STALE, CHAIR_SOLID_STATUS_FIT_FAILED)
    finish_state = "complete" if solid_complete else ("attention" if solid_status == CHAIR_SOLID_STATUS_FIT_FAILED else "ready")
    finish_message = "Supported S1/S1J 3D export bodies are prepared; special chairs and keys remain analytical." if solid_complete else "Routine viewing remains 2D. Build detailed S1/S1J bodies only when preparing an export."
    panel.set_step(6, finish_message, finish_state, "Prepare 3D export chairs", export_ready, "Convert to crossover", self.extend_crossover_button.isEnabled() and not editing)
    panel.set_summary("Selected {}. The stable sequence is geometry, timbering, chair analysis, bounded model support, 2D fit validation, integration, then optional 3D export preparation.".format(identifier))
    panel.run_next_button.setText("Run next safe step")


def _crossover_run_next_guided_step_v13(self):
    config = self.current_config()
    if config is None or self.editing_crossover_id or self.extending_turnout_id:
        try:
            values = self.proposed_values()
            signature = self._preview_signature(values)
            if self._last_preview_signature == signature and self._last_preview_result is not None:
                self.create_crossover()
            else:
                self.preview_geometry()
        except Exception as error:
            QtWidgets.QMessageBox.critical(self, crossover_dialog_title("Guided crossover workflow"), str(error))
        self.update_guided_workflow()
        return
    if crossover_b4_effective_status(self.doc, config) != CROSSOVER_B4_STATUS_CLEAR:
        self.apply_b4_timbering(); self.update_guided_workflow(); return
    chair_status = chair_analysis_effective_status(self.doc, "crossover", config)
    if chair_status in (CHAIR_STATUS_NOT_ANALYSED, CHAIR_STATUS_STALE):
        self.chair_analysis_panel.run_analysis(); self.update_guided_workflow(); return
    if chair_status in (CHAIR_STATUS_INCOMPLETE, CHAIR_STATUS_CONFLICTS, CHAIR_STATUS_CRITICAL):
        QtWidgets.QMessageBox.information(self, crossover_dialog_title("Guided workflow stopped"), "Chair-position analysis needs review before model support can be prepared. No geometry, timbering or readiness gate has been changed.")
        return
    support_status = chair_model_support_effective_status(self.doc, "crossover", config)
    if support_status in (CHAIR_MODEL_SUPPORT_STATUS_NOT_PREPARED, CHAIR_MODEL_SUPPORT_STATUS_STALE):
        self.chair_analysis_panel.prepare_model_support(); self.update_guided_workflow(); return
    if support_status == CHAIR_MODEL_SUPPORT_STATUS_BLOCKED:
        QtWidgets.QMessageBox.information(self, crossover_dialog_title("Guided workflow stopped"), "A required model timber extension exceeds the configured automatic limit. Review the support details before continuing.")
        return
    layout_status = chair_2d_layout_effective_status(self.doc, "crossover", config)
    if layout_status in (CHAIR_2D_LAYOUT_STATUS_NOT_BUILT, CHAIR_2D_LAYOUT_STATUS_STALE):
        self.chair_analysis_panel.build_2d_layout(); self.update_guided_workflow(); return
    if layout_status == CHAIR_2D_LAYOUT_STATUS_FAILED:
        QtWidgets.QMessageBox.information(self, crossover_dialog_title("Guided workflow stopped"), "The lightweight 2D chair layout contains production-critical fit failures. Red outlines identify the affected chair or timber positions.")
        return
    if not bool(config.get("integration_active", False)) and self.integrate_hosts_button.isEnabled():
        self.integrate_selected_crossover(); self.update_guided_workflow(); return
    QtWidgets.QMessageBox.information(self, crossover_dialog_title("Guided crossover workflow"), "Every routine guided stage is complete. The viewer remains lightweight and 2D; use the final button only when preparing supported S1/S1J bodies for export.")


def _turnout_run_next_guided_step_v13(self):
    config = self.current_turnout_config()
    if self.editing_turnout_id:
        self.apply_turnout_edit(); self.update_guided_workflow(); return
    if config is None:
        self.create_turnout(); self.update_guided_workflow(); return
    revision = int(config.get("timber_geometry_revision") or 0)
    timber_outlines = bool(config.get("timber_outlines", config.get("timber_references", True)))
    if revision < TURNOUT_TIMBER_GEOMETRY_REVISION or not timber_outlines:
        self.begin_edit_turnout(); self.update_guided_workflow(); return
    chair_status = chair_analysis_effective_status(self.doc, "turnout", config)
    if chair_status in (CHAIR_STATUS_NOT_ANALYSED, CHAIR_STATUS_STALE):
        self.chair_analysis_panel.run_analysis(); self.update_guided_workflow(); return
    if chair_status in (CHAIR_STATUS_INCOMPLETE, CHAIR_STATUS_CONFLICTS, CHAIR_STATUS_CRITICAL):
        QtWidgets.QMessageBox.information(self, versioned_dialog_title("Guided turnout workflow stopped"), "Chair-position analysis needs review before model support can be prepared. No turnout geometry, timbering or integration record has been changed.")
        return
    support_status = chair_model_support_effective_status(self.doc, "turnout", config)
    if support_status in (CHAIR_MODEL_SUPPORT_STATUS_NOT_PREPARED, CHAIR_MODEL_SUPPORT_STATUS_STALE):
        self.chair_analysis_panel.prepare_model_support(); self.update_guided_workflow(); return
    if support_status == CHAIR_MODEL_SUPPORT_STATUS_BLOCKED:
        QtWidgets.QMessageBox.information(self, versioned_dialog_title("Guided turnout workflow stopped"), "A required model timber extension exceeds the configured automatic limit. Review the support details before continuing.")
        return
    layout_status = chair_2d_layout_effective_status(self.doc, "turnout", config)
    if layout_status in (CHAIR_2D_LAYOUT_STATUS_NOT_BUILT, CHAIR_2D_LAYOUT_STATUS_STALE):
        self.chair_analysis_panel.build_2d_layout(); self.update_guided_workflow(); return
    if layout_status == CHAIR_2D_LAYOUT_STATUS_FAILED:
        QtWidgets.QMessageBox.information(self, versioned_dialog_title("Guided turnout workflow stopped"), "The lightweight 2D chair layout contains production-critical fit failures. Red outlines identify the affected chair or timber positions.")
        return
    identifier = str(config.get("turnout_id") or "")
    if turnout_integration_by_id(self.doc, identifier) is None and self.integrate_button.isEnabled():
        self.integrate_selected_turnout(); self.update_guided_workflow(); return
    QtWidgets.QMessageBox.information(self, versioned_dialog_title("Guided turnout workflow"), "Every routine guided stage is complete. The viewer remains lightweight and 2D; use the final button only when preparing supported S1/S1J bodies for export.")


CrossoverManagerPanel.update_guided_workflow = _crossover_update_guided_workflow_v13
CrossoverManagerPanel.run_next_guided_step = _crossover_run_next_guided_step_v13
TurnoutManagerDialog.update_guided_workflow = _turnout_update_guided_workflow_v13
TurnoutManagerDialog.run_next_guided_step = _turnout_run_next_guided_step_v13


# ---------------------------------------------------------------------------
# A8A7B14 whole-workflow benchmark and low-cost Templot-guided 2D chair symbol.
#
# Benchmarking is intentionally operator-facing and read-only. It records the
# actual total duration of each user action, not only the internal timber solver,
# together with process CPU, current RSS and document-object deltas. The display
# symbol remains lightweight: no text labels, screw circles or 3D topology are
# created during routine viewing.
# ---------------------------------------------------------------------------
WORKFLOW_BENCHMARK_MAX_EVENTS = 64


def _workflow_current_rss_mb():
    """Return current Linux resident memory without importing another module."""
    try:
        with open("/proc/self/status", "r") as handle:
            for line in handle:
                if line.startswith("VmRSS:"):
                    parts = line.split()
                    return float(parts[1]) / 1024.0
    except Exception:
        pass
    return 0.0


def _workflow_document_object_count(doc):
    try:
        return len(list(doc.Objects))
    except Exception:
        return 0


def _workflow_benchmark_owner(widget):
    current = widget
    for _index in range(16):
        if current is None:
            return None
        if hasattr(current, "workflow_panel") and hasattr(current, "doc"):
            return current
        try:
            current = current.parent()
        except Exception:
            return None
    return None


def _workflow_benchmark_events(owner):
    if owner is None:
        return []
    events = getattr(owner, "_whole_workflow_benchmark_events", None)
    if not isinstance(events, list):
        events = []
        owner._whole_workflow_benchmark_events = events
    return events


def _workflow_entity_context(widget, owner, forced_kind=""):
    kind = str(forced_kind or getattr(widget, "entity_kind", "") or "").lower()
    config = None
    try:
        if hasattr(widget, "current_config"):
            config = widget.current_config()
    except Exception:
        config = None
    if config is None and owner is not None:
        try:
            if kind == "turnout" and hasattr(owner, "current_turnout_config"):
                config = owner.current_turnout_config()
            elif kind == "crossover" and hasattr(owner, "current_config"):
                config = owner.current_config()
        except Exception:
            config = None
    config = dict(config or {})
    if not kind:
        if config.get("turnout_id"):
            kind = "turnout"
        elif config.get("crossover_id"):
            kind = "crossover"
    identifier = str(config.get("turnout_id") or config.get("crossover_id") or "")
    return kind, identifier


def _workflow_recorded_method(cls, method_name, stage_label, forced_kind="", reset=False):
    original = getattr(cls, method_name, None)
    if original is None or bool(getattr(original, "_whole_workflow_benchmark_wrapper", False)):
        return

    def wrapped(self, *args, **kwargs):
        owner = _workflow_benchmark_owner(self)
        if owner is None and hasattr(self, "doc"):
            owner = self
        events = _workflow_benchmark_events(owner)
        if reset:
            del events[:]
        doc = getattr(self, "doc", None) or getattr(owner, "doc", None)
        kind_before, id_before = _workflow_entity_context(self, owner, forced_kind)
        wall_start = time.perf_counter()
        cpu_start = time.process_time()
        rss_start = _workflow_current_rss_mb()
        objects_start = _workflow_document_object_count(doc)
        raised = ""
        try:
            return original(self, *args, **kwargs)
        except Exception as error:
            raised = "{}: {}".format(type(error).__name__, error)
            raise
        finally:
            wall_ms = (time.perf_counter() - wall_start) * 1000.0
            cpu_ms = (time.process_time() - cpu_start) * 1000.0
            rss_end = _workflow_current_rss_mb()
            objects_end = _workflow_document_object_count(doc)
            kind_after, id_after = _workflow_entity_context(self, owner, forced_kind)
            event = {
                "stage": str(stage_label),
                "entity_kind": kind_after or kind_before,
                "entity_id": id_after or id_before,
                "wall_ms": float(wall_ms),
                "cpu_ms": float(cpu_ms),
                "cpu_percent_of_one_core": float((cpu_ms / wall_ms) * 100.0) if wall_ms > 1.0e-9 else 0.0,
                "rss_start_mb": float(rss_start),
                "rss_end_mb": float(rss_end),
                "rss_delta_mb": float(rss_end - rss_start),
                "objects_start": int(objects_start),
                "objects_end": int(objects_end),
                "objects_delta": int(objects_end - objects_start),
                "error": str(raised),
                "recorded_at": datetime.datetime.now().isoformat(timespec="seconds"),
            }
            events.append(event)
            if len(events) > WORKFLOW_BENCHMARK_MAX_EVENTS:
                del events[:-WORKFLOW_BENCHMARK_MAX_EVENTS]

    wrapped._whole_workflow_benchmark_wrapper = True
    wrapped._whole_workflow_original = original
    setattr(cls, method_name, wrapped)


def _workflow_performance_report(owner):
    events = list(_workflow_benchmark_events(owner))
    doc = getattr(owner, "doc", None)
    current_kind, current_id = _workflow_entity_context(owner, owner, "")
    lines = [
        "Version {} — Whole workflow performance benchmark".format(MACRO_VERSION_NUMBER),
        "Scope: {} {}".format(current_kind.capitalize() if current_kind else "Current manager", current_id or "session"),
        "Recorded stages: {}".format(len(events)),
        "Current FreeCAD objects: {}".format(_workflow_document_object_count(doc)),
        "Current process resident memory: {:.1f} MB".format(_workflow_current_rss_mb()),
    ]
    if not events:
        lines.extend([
            "",
            "No production-stage timings have been recorded in this manager session.",
            "Run the guided sequence normally; every geometry, timbering, chair, support, display, integration and optional 3D-chair action will be added automatically.",
        ])
        return "\n".join(lines)

    total_wall = sum(float(item.get("wall_ms") or 0.0) for item in events)
    total_cpu = sum(float(item.get("cpu_ms") or 0.0) for item in events)
    first_rss = float(events[0].get("rss_start_mb") or 0.0)
    final_rss = float(events[-1].get("rss_end_mb") or 0.0)
    object_delta = sum(int(item.get("objects_delta") or 0) for item in events)
    largest = max(events, key=lambda item: float(item.get("wall_ms") or 0.0))
    lines.extend([
        "Total recorded wall time: {:.1f} ms ({:.2f} s)".format(total_wall, total_wall / 1000.0),
        "Total recorded process CPU time: {:.1f} ms".format(total_cpu),
        "Session resident-memory change: {:+.1f} MB".format(final_rss - first_rss),
        "Net document-object change: {:+d}".format(object_delta),
        "Largest stage: {} — {:.1f} ms".format(largest.get("stage") or "Unknown", float(largest.get("wall_ms") or 0.0)),
        "",
        "Stage timings:",
    ])
    for index, item in enumerate(events, 1):
        status = "FAILED" if item.get("error") else "completed"
        entity = "{} {}".format(str(item.get("entity_kind") or "").capitalize(), str(item.get("entity_id") or "")).strip()
        lines.append(
            "{:>2}. {}{} — wall {:.1f} ms; CPU {:.1f} ms ({:.0f}% of one core); RSS {:+.1f} MB; objects {:+d}; {}".format(
                index,
                item.get("stage") or "Unnamed stage",
                " [{}]".format(entity) if entity else "",
                float(item.get("wall_ms") or 0.0),
                float(item.get("cpu_ms") or 0.0),
                float(item.get("cpu_percent_of_one_core") or 0.0),
                float(item.get("rss_delta_mb") or 0.0),
                int(item.get("objects_delta") or 0),
                status,
            )
        )
        if item.get("error"):
            lines.append("    Error: {}".format(item.get("error")))
    lines.extend([
        "",
        "Interpretation:",
        "- Wall time is the operator-visible duration of the complete action, including FreeCAD shape construction, metadata updates, display changes and recomputes.",
        "- CPU percentage compares process CPU time with wall time; values above 100% indicate work across more than one core or accounting overlap.",
        "- RSS is an end-minus-start memory snapshot, not a sampled peak. A later optimisation pass should target the largest repeatable wall-time and memory stages first.",
    ])
    return "\n".join(lines)


def _show_whole_workflow_performance_report(self):
    report = _workflow_performance_report(self)
    dialog = QtWidgets.QDialog(self)
    dialog.setWindowTitle(versioned_dialog_title("Whole workflow performance benchmark"))
    dialog.resize(980, 720)
    layout = QtWidgets.QVBoxLayout(dialog)
    editor = QtWidgets.QPlainTextEdit()
    editor.setReadOnly(True)
    editor.setPlainText(report)
    layout.addWidget(editor)
    controls = QtWidgets.QHBoxLayout()
    copy_button = QtWidgets.QPushButton("Copy report")
    close_button = QtWidgets.QPushButton("Close")
    copy_button.clicked.connect(lambda: QtWidgets.QApplication.clipboard().setText(report))
    close_button.clicked.connect(dialog.accept)
    controls.addWidget(copy_button)
    controls.addStretch(1)
    controls.addWidget(close_button)
    layout.addLayout(controls)
    dialog.exec_()


def _reset_whole_workflow_performance(self):
    events = _workflow_benchmark_events(self)
    del events[:]
    QtWidgets.QMessageBox.information(
        self,
        versioned_dialog_title("Whole workflow performance benchmark"),
        "The manager-session benchmark has been reset. The next guided action will start a fresh measurement sequence.",
    )


CrossoverManagerPanel.show_workflow_performance_report = _show_whole_workflow_performance_report
CrossoverManagerPanel.reset_workflow_performance = _reset_whole_workflow_performance
TurnoutManagerDialog.show_workflow_performance_report = _show_whole_workflow_performance_report
TurnoutManagerDialog.reset_workflow_performance = _reset_whole_workflow_performance

_A8A7B14_GUIDED_PANEL_INIT = GuidedTrackworkWorkflowPanel.__init__


def _guided_workflow_panel_init_v14(self, title, step_titles, parent=None):
    _A8A7B14_GUIDED_PANEL_INIT(self, title, step_titles, parent)
    controls = QtWidgets.QHBoxLayout()
    self.performance_button = QtWidgets.QPushButton("Whole-process benchmark")
    self.performance_button.setToolTip(
        "Shows automatically recorded wall time, process CPU, current-memory change and FreeCAD object change for every production stage run in this manager session."
    )
    self.reset_performance_button = QtWidgets.QPushButton("Reset timings")
    self.reset_performance_button.setToolTip("Clears only the in-memory benchmark for this manager session. It changes no railway object or stored production result.")

    def show_report():
        owner = _workflow_benchmark_owner(self)
        if owner is not None and hasattr(owner, "show_workflow_performance_report"):
            owner.show_workflow_performance_report()

    def reset_report():
        owner = _workflow_benchmark_owner(self)
        if owner is not None and hasattr(owner, "reset_workflow_performance"):
            owner.reset_workflow_performance()

    self.performance_button.clicked.connect(show_report)
    self.reset_performance_button.clicked.connect(reset_report)
    controls.addWidget(self.performance_button)
    controls.addWidget(self.reset_performance_button)
    controls.addStretch(1)
    self.layout().addLayout(controls)


GuidedTrackworkWorkflowPanel.__init__ = _guided_workflow_panel_init_v14

# Record complete operator actions. Do not wrap Run-next itself, otherwise a
# guided action would be counted twice when it calls one of these methods.
_workflow_recorded_method(CrossoverManagerPanel, "preview_geometry", "1a Crossover geometry preview", "crossover", True)
_workflow_recorded_method(CrossoverManagerPanel, "create_crossover", "1b Crossover geometry commit", "crossover", False)
_workflow_recorded_method(CrossoverManagerPanel, "apply_b4_timbering", "2 Automatic crossover timbering", "crossover", False)
_workflow_recorded_method(CrossoverManagerPanel, "integrate_selected_crossover", "6 Crossover host integration", "crossover", False)
_workflow_recorded_method(TurnoutManagerDialog, "create_turnout", "1 Turnout geometry and source timbering", "turnout", True)
_workflow_recorded_method(TurnoutManagerDialog, "integrate_selected_turnout", "6 Turnout host integration", "turnout", False)
_workflow_recorded_method(ChairAnalysisPanel, "run_analysis", "3 Chair-position analysis", "", False)
_workflow_recorded_method(ChairAnalysisPanel, "prepare_model_support", "4 Bounded model timber support", "", False)
_workflow_recorded_method(ChairAnalysisPanel, "build_2d_layout", "5 Templot-style 2D chair layout and fit", "", False)
_workflow_recorded_method(ChairAnalysisPanel, "generate_solids", "7 Optional 3D export-chair preparation", "", False)
_workflow_recorded_method(ChairAnalysisPanel, "validate_fit", "7b Optional 3D export-chair revalidation", "", False)


def _chair_symbol_world_point(instance, local_x, local_y, z_height):
    centre = _chair_xy(instance.get("centre_point") or (0.0, 0.0))
    outward = _chair_unit(instance.get("outward_axis") or (1.0, 0.0)) or (1.0, 0.0)
    along = _chair_unit(instance.get("local_y_axis") or (0.0, 1.0)) or (0.0, 1.0)
    return vector_xy(
        centre[0] + float(local_x) * outward[0] + float(local_y) * along[0],
        centre[1] + float(local_x) * outward[1] + float(local_y) * along[1],
    )


def _chair_symbol_wire(instance, local_points, z_height, closed=False):
    points = list(local_points or [])
    if len(points) < 2:
        return None
    vectors = [_chair_symbol_world_point(instance, point[0], point[1], z_height) for point in points]
    if closed and vectors:
        vectors.append(vectors[0])
    return _turnout_wire(vectors, float(z_height))


def _chair_symbol_base_wire(instance, z_height):
    dims = dict(instance.get("body_dimensions") or {})
    xmin = float(dims.get("base_x_min") or -2.0)
    xmax = float(dims.get("base_x_max") or 2.0)
    half = max(0.05, float(dims.get("base_y_half") or 1.0))
    chamfer = min(0.28, max(0.08, 0.12 * min(xmax - xmin, 2.0 * half)))
    points = (
        (xmin + chamfer, -half),
        (xmax - chamfer, -half),
        (xmax, -half + chamfer),
        (xmax, half - chamfer),
        (xmax - chamfer, half),
        (xmin + chamfer, half),
        (xmin, half - chamfer),
        (xmin, -half + chamfer),
    )
    return _chair_symbol_wire(instance, points, z_height, True)


def _chair_symbol_jaw_wires(instance, z_height):
    dims = dict(instance.get("body_dimensions") or {})
    base_half = max(0.10, float(dims.get("base_y_half") or 1.0))
    jaw_half = min(base_half * 0.58, max(0.16, float(dims.get("jaw_y_half") or base_half * 0.50)))
    base_x_min = float(dims.get("base_x_min") or -2.0)
    base_x_max = float(dims.get("base_x_max") or 2.0)
    boxes = []
    for first_key, second_key in (
        ("inner_jaw_x_min", "inner_jaw_x_max"),
        ("outer_jaw_x_min", "outer_jaw_x_max"),
    ):
        xmin = max(base_x_min + 0.05, float(dims.get(first_key) or 0.0))
        xmax = min(base_x_max - 0.05, float(dims.get(second_key) or 0.0))
        if xmax - xmin <= 0.05:
            continue
        boxes.append(_chair_symbol_wire(
            instance,
            ((xmin, -jaw_half), (xmax, -jaw_half), (xmax, jaw_half), (xmin, jaw_half)),
            z_height,
            True,
        ))
    if bool(instance.get("key_direction_resolved")):
        xmin = float(dims.get("outer_jaw_x_min") or 0.0)
        xmax = float(dims.get("outer_jaw_x_max") or xmin)
        if xmax - xmin > 0.08:
            sign = 1.0 if int(instance.get("key_direction_sign") or 1) >= 0 else -1.0
            key_x0 = xmin + 0.24 * (xmax - xmin)
            key_x1 = xmin + 0.78 * (xmax - xmin)
            key_y0 = -sign * jaw_half * 0.72
            key_y1 = sign * jaw_half * 0.72
            boxes.append(_chair_symbol_wire(instance, ((key_x0, key_y0), (key_x1, key_y1)), z_height, False))
    return [shape for shape in boxes if shape is not None]


_A8A7B14_CREATE_2D_DISPLAY_WITH_RECTANGLES = _create_chair_2d_layout_display


def _create_chair_2d_layout_display(doc, entity_kind, config, analysis, plan, validation, timber_records):
    """Create a recognisable low-detail S1/S1J plan symbol without 3D bodies."""
    started = time.perf_counter()
    kind = str(entity_kind or "").lower()
    entity_id = str(config.get("turnout_id") or config.get("crossover_id") or "")
    set_id = str(config.get("template_set_id") or "")
    _chair_remove_2d_display(doc, kind, entity_id)
    group = doc.addObject("App::DocumentObjectGroup", unique_internal_name(doc, "Chair2DLayout_{}".format(entity_id.replace("-", "_"))))
    group.Label = "{} Templot-style 2D chair layout".format(entity_id)
    _chair_tag_auxiliary_object(group, kind, entity_id, set_id, CHAIR_2D_LAYOUT_GROUP_ROLE)
    try:
        group.ViewObject.Visibility = True
    except Exception:
        pass

    levels = _chair_display_z_levels(doc, kind, config)
    base_z = float(levels["footprints"]) + 0.080
    detail_z = base_z + 0.012
    support_z = base_z - 0.025
    failure_z = base_z + 0.050
    unresolved_z = failure_z + 0.025

    effective_timbers, adjustments = _chair_apply_physical_model_support(plan, timber_records, analysis.get("settings"))
    effective_by_id = {str(item.get("stable_identity") or ""): item for item in effective_timbers}
    applied_ids = {str(item.get("timber_identity") or "") for item in adjustments if bool(item.get("applied"))}
    support_shapes = []
    for timber_id in sorted(applied_ids):
        timber = effective_by_id.get(timber_id)
        if timber is not None:
            support_shapes.append(_chair_closed_wire(timber.get("outline_polygon") or timber.get("collision_polygon") or [], support_z))

    critical_findings = [item for item in list(validation.get("findings") or []) if str(item.get("severity") or "") == CHAIR_SEVERITY_CRITICAL]
    failed_chair_ids = {str(item.get("chair_position_identity") or "") for item in critical_findings if item.get("chair_position_identity")}
    failed_timber_ids = {str(item.get("timber_identity") or "") for item in critical_findings if item.get("timber_identity")}
    base_shapes = []
    detail_shapes = []
    failure_shapes = []
    for instance in list(plan.get("instances") or []):
        base_shapes.append(_chair_symbol_base_wire(instance, base_z))
        detail_shapes.extend(_chair_symbol_jaw_wires(instance, detail_z))
        if str(instance.get("chair_position_identity") or "") in failed_chair_ids:
            failure_shapes.append(_chair_closed_wire(instance.get("physical_footprint_polygon") or [], failure_z))
    for timber_id in sorted(failed_timber_ids):
        timber = effective_by_id.get(timber_id)
        if timber is not None:
            failure_shapes.append(_chair_closed_wire(timber.get("outline_polygon") or timber.get("collision_polygon") or [], failure_z))

    positions_by_id = {
        str(item.get("stable_chair_position_identity") or ""): item
        for item in list(analysis.get("positions") or [])
    }
    unresolved_shapes = []
    for item in list(plan.get("analytical_only") or []):
        if bool(item.get("deliberate_omission")):
            continue
        position = positions_by_id.get(str(item.get("chair_position_identity") or ""))
        if position is None:
            continue
        unresolved_shapes.extend(_chair_cross_wires(
            position.get("centre_point") or (0.0, 0.0),
            position.get("local_rail_tangent") or (1.0, 0.0),
            half_size=1.20,
            z_height=unresolved_z,
        ))

    _chair_make_2d_feature(
        doc, group, kind, entity_id, set_id, CHAIR_2D_SUPPORT_ROLE,
        "{} bounded model timber support outlines".format(entity_id), support_shapes,
        (0.95, 0.65, 0.10), 2.6, True,
    )
    _chair_make_2d_feature(
        doc, group, kind, entity_id, set_id, CHAIR_2D_FOOTPRINT_ROLE,
        "{} S1/S1J chair base symbols".format(entity_id), base_shapes,
        (0.70, 0.78, 0.88), 2.0, True,
    )
    _chair_make_2d_feature(
        doc, group, kind, entity_id, set_id, CHAIR_2D_FOOTPRINT_ROLE,
        "{} S1/S1J chair jaw and key details".format(entity_id), detail_shapes,
        (0.30, 0.45, 0.65), 1.5, True,
    )
    _chair_make_2d_feature(
        doc, group, kind, entity_id, set_id, CHAIR_2D_FAILURE_ROLE,
        "{} chair fit failures".format(entity_id), failure_shapes,
        (0.95, 0.15, 0.15), 4.0, True,
    )
    _chair_make_2d_feature(
        doc, group, kind, entity_id, set_id, CHAIR_2D_UNRESOLVED_ROLE,
        "{} unresolved special chair positions".format(entity_id), unresolved_shapes,
        (0.85, 0.20, 0.85), 3.2, True,
    )
    build_time_ms = (time.perf_counter() - started) * 1000.0
    properties = [
        ensure_property(group, "App::PropertyInteger", "Chair2DSymbolCount", "Chair 2D display", "Number of supported S1/S1J plan symbols"),
        ensure_property(group, "App::PropertyInteger", "Chair2DDetailWireCount", "Chair 2D display", "Number of lightweight jaw and key detail wires"),
        ensure_property(group, "App::PropertyFloat", "Chair2DDisplayBuildTimeMs", "Chair 2D display", "Measured display-construction time before the document recompute"),
        ensure_property(group, "App::PropertyString", "Chair2DRepresentation", "Chair 2D display", "Viewer-only chair representation"),
    ]
    _set_persistent_property_if_changed(group, "Chair2DSymbolCount", len([shape for shape in base_shapes if shape is not None]))
    _set_persistent_property_if_changed(group, "Chair2DDetailWireCount", len([shape for shape in detail_shapes if shape is not None]))
    _set_persistent_property_if_changed(group, "Chair2DDisplayBuildTimeMs", float(build_time_ms))
    _set_persistent_property_if_changed(group, "Chair2DRepresentation", "Low-detail Templot-guided S1/S1J base, jaw and optional key symbol; exact footprint retained separately for validation")
    set_read_only(group, properties)
    parent = production_parent_group_for_set(doc, set_id)
    if parent is not None:
        try:
            parent.addObject(group)
        except Exception:
            pass
    return group


# ---------------------------------------------------------------------------
# A8A7B15 chair performance and representation.
#
# This final compatibility layer leaves the accepted railway geometry,
# crossover/timber solvers, production records, host integration and exporters
# unchanged.  Routine chair work remains 2D.  Compact physical plans and one
# canonical plan symbol per supported chair type are cached in memory; detailed
# Part solids remain reachable only through the explicit export-chair action.
# ---------------------------------------------------------------------------
MACRO_VERSION_NUMBER = "10.2A8A7B15"
MACRO_VERSION = "{} CHAIR PERFORMANCE AND REPRESENTATION".format(MACRO_VERSION_NUMBER)
CHAIR_2D_REPRESENTATION_REVISION = 2
CHAIR_2D_SOURCE_BASIS = (
    "Templot5 revision 556b chairs_unit.pas T_2d_data and init_2d_rea S1/S1J base dimensions",
    "Templot5 revision 556b chairs_unit.pas init_3d_rea S1 one-rib inner and two-rib outer jaw relationship",
    "Templot5 revision 556b math_unit.pas S1/S1J jaw, seat and longitudinal-key assembly",
)

_CHAIR_SOLID_PLAN_CACHE = {}
_CHAIR_SOLID_PLAN_CACHE_MAXIMUM = 8
_CHAIR_2D_SYMBOL_CACHE = {}
_WORKFLOW_ACTIVE_MEASUREMENTS = []


def _workflow_active_measurement():
    return _WORKFLOW_ACTIVE_MEASUREMENTS[-1] if _WORKFLOW_ACTIVE_MEASUREMENTS else None


def _workflow_note_cache(cache_name, hits=0, misses=0, unchanged_reused=False):
    measurement = _workflow_active_measurement()
    if measurement is None:
        return
    measurement["cache_hits"] += max(0, int(hits or 0))
    measurement["cache_misses"] += max(0, int(misses or 0))
    if unchanged_reused:
        measurement["unchanged_result_reused"] = True
    if hits or misses or unchanged_reused:
        label = "{}: {} hit(s), {} miss(es){}".format(
            str(cache_name or "cache"), int(hits or 0), int(misses or 0),
            "; unchanged result reused" if unchanged_reused else "",
        )
        measurement.setdefault("cache_notes", []).append(label)


def _workflow_note_shape_build(label, shape_instances=0, subshapes=0):
    measurement = _workflow_active_measurement()
    if measurement is None:
        return
    measurement["reported_shape_instances"] += max(0, int(shape_instances or 0))
    measurement["reported_subshapes"] += max(0, int(subshapes or 0))
    if shape_instances or subshapes:
        measurement.setdefault("shape_notes", []).append(
            "{}: {} shape instance(s), {} lightweight sub-shape(s)".format(
                str(label or "shape build"), int(shape_instances or 0), int(subshapes or 0)
            )
        )


def _document_recompute(doc, *args, **kwargs):
    """Recompute normally while timing calls made inside a guided stage."""
    started = time.perf_counter()
    try:
        return doc.recompute(*args, **kwargs)
    finally:
        measurement = _workflow_active_measurement()
        if measurement is not None:
            measurement["recompute_count"] += 1
            measurement["recompute_ms"] += (time.perf_counter() - started) * 1000.0


def _workflow_document_snapshot(doc):
    try:
        objects = list(doc.Objects)
    except Exception:
        objects = []
    shape_objects = 0
    for obj in objects:
        try:
            shape = getattr(obj, "Shape", None)
            if shape is not None and not shape.isNull():
                shape_objects += 1
        except Exception:
            if getattr(obj, "Shape", None) is not None:
                shape_objects += 1
    return {
        "objects": objects,
        "object_ids": {id(obj) for obj in objects},
        "object_count": len(objects),
        "shape_object_count": shape_objects,
    }


def _workflow_new_subshape_counts(objects, previous_ids):
    counts = {
        "shape_objects": 0,
        "solids": 0,
        "faces": 0,
        "edges": 0,
        "vertices": 0,
    }
    known_ids = previous_ids if isinstance(previous_ids, set) else set(previous_ids or ())
    for obj in list(objects or []):
        if id(obj) in known_ids:
            continue
        try:
            shape = getattr(obj, "Shape", None)
            if shape is None or shape.isNull():
                continue
            counts["shape_objects"] += 1
            for key, subshape_name, attribute_name in (
                ("solids", "Solid", "Solids"),
                ("faces", "Face", "Faces"),
                ("edges", "Edge", "Edges"),
                ("vertices", "Vertex", "Vertexes"),
            ):
                try:
                    counts[key] += int(shape.countSubShapes(subshape_name))
                except Exception:
                    counts[key] += len(list(getattr(shape, attribute_name, ()) or ()))
        except Exception:
            continue
    return counts


def _workflow_recorded_method_v15(cls, method_name, stage_label, forced_kind="", reset=False):
    current = getattr(cls, method_name, None)
    if current is None:
        return
    if str(getattr(current, "_whole_workflow_wrapper_version", "")) == MACRO_VERSION_NUMBER:
        return
    original = getattr(current, "_whole_workflow_original", current)

    def wrapped(self, *args, **kwargs):
        pre_measurement_started = time.perf_counter()
        owner = _workflow_benchmark_owner(self)
        if owner is None and hasattr(self, "doc"):
            owner = self
        events = _workflow_benchmark_events(owner)
        if reset:
            del events[:]
        doc = getattr(self, "doc", None) or getattr(owner, "doc", None)
        kind_before, id_before = _workflow_entity_context(self, owner, forced_kind)
        rss_start = _workflow_current_rss_mb()
        before = _workflow_document_snapshot(doc)
        pre_measurement_ms = (time.perf_counter() - pre_measurement_started) * 1000.0
        measurement = {
            "recompute_count": 0,
            "recompute_ms": 0.0,
            "cache_hits": 0,
            "cache_misses": 0,
            "unchanged_result_reused": False,
            "cache_notes": [],
            "reported_shape_instances": 0,
            "reported_subshapes": 0,
            "shape_notes": [],
        }
        _WORKFLOW_ACTIVE_MEASUREMENTS.append(measurement)
        wall_started = time.perf_counter()
        cpu_started = time.process_time()
        raised = ""
        try:
            return original(self, *args, **kwargs)
        except Exception as error:
            raised = "{}: {}".format(type(error).__name__, error)
            raise
        finally:
            wall_ms = (time.perf_counter() - wall_started) * 1000.0
            cpu_ms = (time.process_time() - cpu_started) * 1000.0
            if _WORKFLOW_ACTIVE_MEASUREMENTS and _WORKFLOW_ACTIVE_MEASUREMENTS[-1] is measurement:
                _WORKFLOW_ACTIVE_MEASUREMENTS.pop()
            else:
                try:
                    _WORKFLOW_ACTIVE_MEASUREMENTS.remove(measurement)
                except ValueError:
                    pass
            post_measurement_started = time.perf_counter()
            rss_end = _workflow_current_rss_mb()
            after = _workflow_document_snapshot(doc)
            generated = _workflow_new_subshape_counts(after["objects"], before["object_ids"])
            kind_after, id_after = _workflow_entity_context(self, owner, forced_kind)
            event = {
                "stage": str(stage_label),
                "entity_kind": kind_after or kind_before,
                "entity_id": id_after or id_before,
                "wall_ms": float(wall_ms),
                "cpu_ms": float(cpu_ms),
                "cpu_percent_of_one_core": float((cpu_ms / wall_ms) * 100.0) if wall_ms > 1.0e-9 else 0.0,
                "rss_start_mb": float(rss_start),
                "rss_end_mb": float(rss_end),
                "rss_delta_mb": float(rss_end - rss_start),
                "objects_start": int(before["object_count"]),
                "objects_end": int(after["object_count"]),
                "objects_delta": int(after["object_count"] - before["object_count"]),
                "shape_objects_start": int(before["shape_object_count"]),
                "shape_objects_end": int(after["shape_object_count"]),
                "shape_objects_delta": int(after["shape_object_count"] - before["shape_object_count"]),
                "generated_shape_objects": int(generated["shape_objects"]),
                "generated_solids": int(generated["solids"]),
                "generated_faces": int(generated["faces"]),
                "generated_edges": int(generated["edges"]),
                "generated_vertices": int(generated["vertices"]),
                "reported_shape_instances": int(measurement["reported_shape_instances"]),
                "reported_subshapes": int(measurement["reported_subshapes"]),
                "shape_notes": list(measurement["shape_notes"]),
                "recompute_count": int(measurement["recompute_count"]),
                "recompute_ms": float(measurement["recompute_ms"]),
                "cache_hits": int(measurement["cache_hits"]),
                "cache_misses": int(measurement["cache_misses"]),
                "cache_notes": list(measurement["cache_notes"]),
                "unchanged_result_reused": bool(measurement["unchanged_result_reused"]),
                "error": str(raised),
                "recorded_at": datetime.datetime.now().isoformat(timespec="seconds"),
                "instrumentation_overhead_ms": 0.0,
            }
            events.append(event)
            if len(events) > WORKFLOW_BENCHMARK_MAX_EVENTS:
                del events[:-WORKFLOW_BENCHMARK_MAX_EVENTS]
            event["instrumentation_overhead_ms"] = float(
                pre_measurement_ms + (time.perf_counter() - post_measurement_started) * 1000.0
            )

    wrapped._whole_workflow_benchmark_wrapper = True
    wrapped._whole_workflow_wrapper_version = MACRO_VERSION_NUMBER
    wrapped._whole_workflow_original = original
    setattr(cls, method_name, wrapped)


def _workflow_performance_report(owner):
    events = list(_workflow_benchmark_events(owner))
    doc = getattr(owner, "doc", None)
    current_kind, current_id = _workflow_entity_context(owner, owner, "")
    lines = [
        "Version {} — Chair performance and whole-workflow benchmark".format(MACRO_VERSION_NUMBER),
        "Scope: {} {}".format(current_kind.capitalize() if current_kind else "Current manager", current_id or "session"),
        "Recorded operator actions: {}".format(len(events)),
        "Current FreeCAD objects: {}".format(_workflow_document_object_count(doc)),
        "Current process resident memory: {:.1f} MB".format(_workflow_current_rss_mb()),
    ]
    if not events:
        lines.extend([
            "",
            "No guided production-stage timings have been recorded in this manager session.",
            "Reset the benchmark, then run the seven guided stages in order. Repeating stages records cache reuse separately.",
        ])
        return "\n".join(lines)

    total_wall = sum(float(item.get("wall_ms") or 0.0) for item in events)
    total_cpu = sum(float(item.get("cpu_ms") or 0.0) for item in events)
    total_overhead = sum(float(item.get("instrumentation_overhead_ms") or 0.0) for item in events)
    total_recompute_count = sum(int(item.get("recompute_count") or 0) for item in events)
    total_recompute_ms = sum(float(item.get("recompute_ms") or 0.0) for item in events)
    total_cache_hits = sum(int(item.get("cache_hits") or 0) for item in events)
    total_cache_misses = sum(int(item.get("cache_misses") or 0) for item in events)
    total_reported_shapes = sum(int(item.get("reported_shape_instances") or 0) for item in events)
    total_reported_subshapes = sum(int(item.get("reported_subshapes") or 0) for item in events)
    first_rss = float(events[0].get("rss_start_mb") or 0.0)
    final_rss = float(events[-1].get("rss_end_mb") or 0.0)
    total_cpu_percent = (total_cpu / total_wall) * 100.0 if total_wall > 1.0e-9 else 0.0
    percentage_checksum = sum(
        (float(item.get("wall_ms") or 0.0) / total_wall) * 100.0
        for item in events
    ) if total_wall > 1.0e-9 else 0.0
    overhead_percent = (total_overhead / total_wall) * 100.0 if total_wall > 1.0e-9 else 0.0
    contributors = sorted(events, key=lambda item: float(item.get("wall_ms") or 0.0), reverse=True)[:3]
    lines.extend([
        "Total workflow wall time: {:.1f} ms ({:.2f} s)".format(total_wall, total_wall / 1000.0),
        "Reconciled sum of individual stage actions: {:.1f} ms".format(sum(float(item.get("wall_ms") or 0.0) for item in events)),
        "Stage percentage checksum: {:.3f}%".format(percentage_checksum),
        "Total process CPU time: {:.1f} ms ({:.0f}% of one core)".format(total_cpu, total_cpu_percent),
        "Benchmark instrumentation overhead: {:.2f} ms ({:.2f}% of measured work)".format(total_overhead, overhead_percent),
        "Session resident-memory change: {:+.1f} MB".format(final_rss - first_rss),
        "Net document-object change: {:+d}".format(int(events[-1].get("objects_end") or 0) - int(events[0].get("objects_start") or 0)),
        "Document recomputes: {} taking {:.1f} ms total".format(total_recompute_count, total_recompute_ms),
        "Recorded cache activity: {} hit(s), {} miss(es); unchanged stage results reused: {}".format(
            total_cache_hits, total_cache_misses,
            sum(1 for item in events if bool(item.get("unchanged_result_reused"))),
        ),
        "Reported in-memory shape instances/sub-shapes: {} / {}".format(total_reported_shapes, total_reported_subshapes),
        "",
        "Largest three performance contributors:",
    ])
    for index, item in enumerate(contributors, 1):
        percent = (float(item.get("wall_ms") or 0.0) / total_wall) * 100.0 if total_wall > 1.0e-9 else 0.0
        lines.append(
            "{}. {} — {:.1f} ms ({:.1f}%)".format(index, item.get("stage") or "Unnamed stage", float(item.get("wall_ms") or 0.0), percent)
        )

    lines.extend(["", "Stage actions:"])
    for index, item in enumerate(events, 1):
        wall = float(item.get("wall_ms") or 0.0)
        percent = (wall / total_wall) * 100.0 if total_wall > 1.0e-9 else 0.0
        status = "FAILED" if item.get("error") else "completed"
        entity = "{} {}".format(str(item.get("entity_kind") or "").capitalize(), str(item.get("entity_id") or "")).strip()
        lines.append(
            "{:>2}. {}{} — wall {:.1f} ms ({:.1f}%); CPU {:.1f} ms ({:.0f}%); RSS {:+.1f} MB; objects {:+d}; shape objects {:+d}; recomputes {} / {:.1f} ms; cache {}/{}; reused {}; {}".format(
                index,
                item.get("stage") or "Unnamed stage",
                " [{}]".format(entity) if entity else "",
                wall,
                percent,
                float(item.get("cpu_ms") or 0.0),
                float(item.get("cpu_percent_of_one_core") or 0.0),
                float(item.get("rss_delta_mb") or 0.0),
                int(item.get("objects_delta") or 0),
                int(item.get("shape_objects_delta") or 0),
                int(item.get("recompute_count") or 0),
                float(item.get("recompute_ms") or 0.0),
                int(item.get("cache_hits") or 0),
                int(item.get("cache_misses") or 0),
                "Yes" if item.get("unchanged_result_reused") else "No",
                status,
            )
        )
        lines.append(
            "    New shape objects: {}; solids/faces/edges/vertices: {}/{}/{}/{}; reported instances/sub-shapes: {}/{}; instrumentation {:.2f} ms".format(
                int(item.get("generated_shape_objects") or 0),
                int(item.get("generated_solids") or 0),
                int(item.get("generated_faces") or 0),
                int(item.get("generated_edges") or 0),
                int(item.get("generated_vertices") or 0),
                int(item.get("reported_shape_instances") or 0),
                int(item.get("reported_subshapes") or 0),
                float(item.get("instrumentation_overhead_ms") or 0.0),
            )
        )
        for note in list(item.get("cache_notes") or []):
            lines.append("    Cache: {}".format(note))
        for note in list(item.get("shape_notes") or []):
            lines.append("    Shapes: {}".format(note))
        if item.get("error"):
            lines.append("    Error: {}".format(item.get("error")))

    lines.extend([
        "",
        "Interpretation:",
        "- Stage wall time measures the wrapped production action; benchmark sampling is timed separately so its own cost is visible.",
        "- CPU utilisation compares process CPU with wall time. RSS is an end-minus-start resident-memory snapshot, not a sampled peak.",
        "- Recompute timing covers macro-requested document recomputes. FreeCAD-internal redraw work outside those calls may still appear only in wall time.",
        "- Sub-shape counts are exact for newly created document shapes where FreeCAD exposes topology, plus explicit lightweight chair-instance counts for cached viewer geometry.",
    ])
    return "\n".join(lines)


_A8A7B15_GUIDED_PANEL_INIT = GuidedTrackworkWorkflowPanel.__init__


def _guided_workflow_panel_init_v15(self, title, step_titles, parent=None):
    _A8A7B15_GUIDED_PANEL_INIT(self, title, step_titles, parent)
    if hasattr(self, "performance_button"):
        self.performance_button.setToolTip(
            "Shows reconciled wall-time percentages, CPU, RSS, objects, shape/sub-shape counts, macro-requested recomputes, cache reuse and instrumentation overhead for the complete guided workflow."
        )


GuidedTrackworkWorkflowPanel.__init__ = _guided_workflow_panel_init_v15


# Remove the B14 measurement wrappers and reinstall one low-overhead B15
# wrapper around each complete operator action. Run-next remains unwrapped so a
# guided action is never counted twice.
_workflow_recorded_method_v15(CrossoverManagerPanel, "preview_geometry", "1a Crossover geometry preview", "crossover", True)
_workflow_recorded_method_v15(CrossoverManagerPanel, "create_crossover", "1b Crossover geometry commit", "crossover", False)
_workflow_recorded_method_v15(CrossoverManagerPanel, "apply_b4_timbering", "2 Automatic crossover timbering", "crossover", False)
_workflow_recorded_method_v15(CrossoverManagerPanel, "integrate_selected_crossover", "6 Crossover host integration", "crossover", False)
_workflow_recorded_method_v15(TurnoutManagerDialog, "create_turnout", "1 Turnout geometry and source timbering", "turnout", True)
_workflow_recorded_method_v15(TurnoutManagerDialog, "integrate_selected_turnout", "6 Turnout host integration", "turnout", False)
_workflow_recorded_method_v15(ChairAnalysisPanel, "run_analysis", "3 Chair-position generation and classification", "", False)
_workflow_recorded_method_v15(ChairAnalysisPanel, "prepare_model_support", "4 Bounded model timber support", "", False)
_workflow_recorded_method_v15(ChairAnalysisPanel, "build_2d_layout", "5 Cached Templot-guided 2D chair layout and fit", "", False)
_workflow_recorded_method_v15(ChairAnalysisPanel, "generate_solids", "7 Optional 3D export-chair preparation", "", False)
_workflow_recorded_method_v15(ChairAnalysisPanel, "validate_fit", "7b Optional 3D export-chair revalidation", "", False)


_A8A7B15_BUILD_SOLID_PLAN = _chair_build_solid_plan
_A8A7B15_APPLY_MODEL_SUPPORT = _chair_apply_physical_model_support
_A8A7B15_PREPARE_MODEL_SUPPORT = prepare_chair_model_support
_A8A7B15_BUILD_2D_LAYOUT = build_and_validate_chair_2d_layout
_A8A7B15_ANALYSE_CHAIRS = analyse_entity_chair_positions
_A8A7B15_GENERATE_CHAIR_SOLIDS = generate_supported_chair_solids


def _chair_solid_plan_cache_key(doc, entity_kind, config, analysis_result, settings):
    normalised = normalise_chair_analysis_settings(settings)
    relevant = {
        "rail_fit_clearance_per_side": float(normalised["rail_fit_clearance_per_side"]),
        "future_chair_embed_depth": float(normalised["future_chair_embed_depth"]),
        "model_support_edge_margin": float(normalised["model_support_edge_margin"]),
        "preferred_maximum_model_support_extension_per_side": float(normalised["preferred_maximum_model_support_extension_per_side"]),
        "model_support_recommendations_enabled": bool(normalised["model_support_recommendations_enabled"]),
        "model_support_auto_apply_enabled": bool(normalised["model_support_auto_apply_enabled"]),
    }
    return (
        id(doc),
        str(entity_kind or "").lower(),
        str((config or {}).get("turnout_id") or (config or {}).get("crossover_id") or ""),
        str((analysis_result or {}).get("geometry_signature") or ""),
        round(float(_chair_physical_top_z(doc, entity_kind, config)), 6),
        json.dumps(relevant, sort_keys=True, separators=(",", ":")),
    )


def _chair_build_solid_plan(doc, entity_kind, config, analysis_result, rail_records, timber_records, settings=None):
    key = _chair_solid_plan_cache_key(doc, entity_kind, config, analysis_result, settings)
    cached = _CHAIR_SOLID_PLAN_CACHE.get(key)
    if cached is not None:
        _workflow_note_cache("compact chair plan", hits=1)
        return cached
    plan = _A8A7B15_BUILD_SOLID_PLAN(
        doc, entity_kind, config, analysis_result, rail_records, timber_records, settings
    )
    if len(_CHAIR_SOLID_PLAN_CACHE) >= _CHAIR_SOLID_PLAN_CACHE_MAXIMUM:
        try:
            del _CHAIR_SOLID_PLAN_CACHE[next(iter(_CHAIR_SOLID_PLAN_CACHE))]
        except Exception:
            _CHAIR_SOLID_PLAN_CACHE.clear()
    _CHAIR_SOLID_PLAN_CACHE[key] = plan
    _workflow_note_cache("compact chair plan", misses=1)
    return plan


def _chair_apply_physical_model_support(plan, timber_records, settings=None):
    """Copy only records that actually require model-only widening."""
    adjustments = list((plan or {}).get("model_timber_support_adjustments") or [])
    by_timber = {
        str(item.get("timber_identity") or ""): item
        for item in adjustments if bool(item.get("applied"))
    }
    effective = []
    for timber in list(timber_records or []):
        adjustment = by_timber.get(str(timber.get("stable_identity") or ""))
        effective.append(
            _chair_transform_timber_for_model_support(timber, adjustment)
            if adjustment is not None else timber
        )
    return effective, adjustments


def prepare_chair_model_support(doc, entity_kind, entity_id, settings=None):
    """Reuse a current B15 support result without metadata writes or recompute."""
    kind, config, analysis, normalised, _rails, _timbers = _chair_generation_context(
        doc, entity_kind, entity_id, settings
    )
    state = dict(analysis.get("model_timber_support_state") or {})
    reusable = (
        bool(normalised.get("cache_enabled"))
        and str(state.get("macro_version") or "") == MACRO_VERSION_NUMBER
        and str(state.get("source_analysis_signature") or "") == str(analysis.get("geometry_signature") or "")
        and str(state.get("status") or "") in (
            CHAIR_MODEL_SUPPORT_STATUS_CLEAR,
            CHAIR_MODEL_SUPPORT_STATUS_APPLIED,
            CHAIR_MODEL_SUPPORT_STATUS_BLOCKED,
        )
    )
    if reusable:
        state["unchanged_result_reused"] = True
        state["reuse_reason"] = "The analysis signature and B15 support settings are unchanged."
        _workflow_note_cache("model timber support", hits=1, unchanged_reused=True)
        return state
    _workflow_note_cache("model timber support", misses=1)
    return _A8A7B15_PREPARE_MODEL_SUPPORT(doc, kind, entity_id, normalised)


def _chair_layout_group_representation_current(doc, entity_kind, entity_id):
    groups = _chair_2d_objects(doc, entity_kind, entity_id, (CHAIR_2D_LAYOUT_GROUP_ROLE,))
    if len(groups) != 1:
        return False
    try:
        return int(getattr(groups[0], "Chair2DRepresentationRevision", 0) or 0) == CHAIR_2D_REPRESENTATION_REVISION
    except Exception:
        return False


def build_and_validate_chair_2d_layout(doc, entity_kind, entity_id, settings=None):
    """Reuse an unchanged displayed B15 layout before constructing any Part wire."""
    kind, config, analysis, normalised, _rails, _timbers = _chair_generation_context(
        doc, entity_kind, entity_id, settings
    )
    support_state = dict(analysis.get("model_timber_support_state") or {})
    layout_state = dict(analysis.get("chair_2d_layout_state") or {})
    reusable = (
        bool(normalised.get("cache_enabled"))
        and str(layout_state.get("macro_version") or "") == MACRO_VERSION_NUMBER
        and str(layout_state.get("source_analysis_signature") or "") == str(analysis.get("geometry_signature") or "")
        and str(layout_state.get("support_signature") or "") == str(support_state.get("support_signature") or "")
        and str(layout_state.get("layout_signature") or "") == str(support_state.get("support_signature") or "")
        and str(layout_state.get("status") or "") in (CHAIR_2D_LAYOUT_STATUS_VALIDATED, CHAIR_2D_LAYOUT_STATUS_FAILED)
        and bool(_chair_2d_objects(doc, kind, entity_id))
        and _chair_layout_group_representation_current(doc, kind, entity_id)
    )
    if reusable:
        layout_state["unchanged_result_reused"] = True
        layout_state["display_cache_reused"] = True
        layout_state["representation_revision"] = CHAIR_2D_REPRESENTATION_REVISION
        _workflow_note_cache("2D chair layout", hits=1, unchanged_reused=True)
        return layout_state
    _workflow_note_cache("2D chair layout", misses=1)
    result = _A8A7B15_BUILD_2D_LAYOUT(doc, kind, entity_id, normalised)
    result["unchanged_result_reused"] = False
    result["display_cache_reused"] = False
    result["representation_revision"] = CHAIR_2D_REPRESENTATION_REVISION
    return result


def analyse_entity_chair_positions(doc, entity_kind, entity_id, settings=None):
    result = _A8A7B15_ANALYSE_CHAIRS(doc, entity_kind, entity_id, settings)
    reused = bool((result or {}).get("cache_reused"))
    _workflow_note_cache("chair analysis", hits=int(reused), misses=int(not reused), unchanged_reused=reused)
    return result


def generate_supported_chair_solids(doc, entity_kind, entity_id, settings=None):
    result = _A8A7B15_GENERATE_CHAIR_SOLIDS(doc, entity_kind, entity_id, settings)
    reused = bool((result or {}).get("unchanged_result_reused"))
    hits = int((result or {}).get("prototype_cache_hits") or 0) + int(reused)
    misses = int((result or {}).get("prototype_cache_misses") or 0)
    _workflow_note_cache("3D export-chair prototype", hits=hits, misses=misses, unchanged_reused=reused)
    if not reused:
        generated = int((result or {}).get("generated_count") or 0)
        _workflow_note_shape_build("3D export-chair bodies", generated, generated)
    return result


def _chair_rounded_rectangle_points(xmin, xmax, ymin, ymax, radius, segments=2):
    radius = min(max(0.0, float(radius)), 0.5 * (xmax - xmin), 0.5 * (ymax - ymin))
    if radius <= 1.0e-9:
        return [(xmin, ymin), (xmax, ymin), (xmax, ymax), (xmin, ymax)]
    points = []
    for centre_x, centre_y, start_degrees in (
        (xmax - radius, ymin + radius, -90.0),
        (xmax - radius, ymax - radius, 0.0),
        (xmin + radius, ymax - radius, 90.0),
        (xmin + radius, ymin + radius, 180.0),
    ):
        for index in range(max(1, int(segments)) + 1):
            angle = math.radians(start_degrees + 90.0 * index / float(max(1, int(segments))))
            points.append((centre_x + radius * math.cos(angle), centre_y + radius * math.sin(angle)))
    return points


def _chair_local_wire(points, closed=False):
    local = list(points or [])
    if len(local) < 2:
        return None
    vectors = [App.Vector(float(point[0]), float(point[1]), 0.0) for point in local]
    if closed:
        vectors.append(vectors[0])
    return Part.makePolygon(vectors)


def _chair_local_compound(shapes):
    valid = [shape for shape in list(shapes or []) if shape is not None]
    if not valid:
        return None
    return valid[0] if len(valid) == 1 else Part.makeCompound(valid)


def _chair_key_symbol_wires(dimensions, direction_sign):
    rail_half = float(dimensions.get("rail_foot_half") or 0.45)
    fit = float(dimensions.get("rail_fit_clearance_per_side") or 0.04)
    outer_face = float(dimensions.get("outer_jaw_x_min") or (rail_half + 0.5))
    xmin = rail_half + 0.55 * fit
    xmax = outer_face - max(0.025, 0.35 * fit)
    if xmax - xmin <= 0.08:
        return []
    centre_x = 0.5 * (xmin + xmax)
    available = xmax - xmin
    wide = 0.82 * available
    narrow = 0.34 * available
    half_length = min(
        0.82 * float(dimensions.get("jaw_y_half") or 0.65),
        0.50 * float(dimensions.get("base_y_half") or 1.30),
    )
    sign = 1 if int(direction_sign or 1) >= 0 else -1
    tail_y = -sign * half_length
    tip_y = sign * half_length
    polygon = (
        (centre_x - 0.5 * wide, tail_y),
        (centre_x + 0.5 * wide, tail_y),
        (centre_x + 0.5 * narrow, tip_y),
        (centre_x - 0.5 * narrow, tip_y),
    )
    shaft_end = sign * half_length * 0.62
    chevron_y = sign * half_length * 0.34
    chevron_dx = 0.20 * available
    return [
        _chair_local_wire(polygon, True),
        _chair_local_wire(((centre_x, -sign * half_length * 0.58), (centre_x, shaft_end)), False),
        _chair_local_wire(((centre_x - chevron_dx, chevron_y), (centre_x, shaft_end), (centre_x + chevron_dx, chevron_y)), False),
    ]


def _chair_canonical_2d_symbol(chair_code, settings=None):
    normalised = normalise_chair_analysis_settings(settings)
    code = int(chair_code or 0)
    key = (
        CHAIR_2D_REPRESENTATION_REVISION,
        code,
        CHAIR_CODE75_RAIL_PROFILE["profile_id"],
        round(float(normalised["rail_fit_clearance_per_side"]), 6),
    )
    cached = _CHAIR_2D_SYMBOL_CACHE.get(key)
    if cached is not None:
        return cached, True
    dimensions = _chair_s1_body_dimensions(code, normalised)
    xmin = float(dimensions["base_x_min"])
    xmax = float(dimensions["base_x_max"])
    half = float(dimensions["base_y_half"])
    inch = 25.4 / TURNOUT_DEFAULT_SCALE
    base_points = _chair_rounded_rectangle_points(
        xmin, xmax, -half, half, min(inch, 0.24 * min(xmax - xmin, 2.0 * half)), 2
    )
    base = _chair_local_wire(base_points, True)

    inner_min = float(dimensions["inner_jaw_x_min"])
    inner_max = float(dimensions["inner_jaw_x_max"])
    outer_min = float(dimensions["outer_jaw_x_min"])
    outer_max = float(dimensions["outer_jaw_x_max"])
    jaw_half = min(0.88 * half, float(dimensions["jaw_y_half"]))
    seat_half = min(0.94 * half, float(dimensions["seat_y_half"]))
    seat_xmin = inner_max + 0.018
    seat_xmax = outer_min - 0.018
    detail_wires = []
    if seat_xmax > seat_xmin:
        seat_points = _chair_rounded_rectangle_points(
            seat_xmin, seat_xmax, -seat_half, seat_half,
            min(0.12, 0.18 * (seat_xmax - seat_xmin)), 1,
        )
        detail_wires.append(_chair_local_wire(seat_points, True))

    rail_half = float(dimensions["rail_foot_half"])
    rail_length = min(0.91 * half, 0.96 * seat_half)
    detail_wires.extend([
        _chair_local_wire(((-rail_half, -rail_length), (-rail_half, rail_length)), False),
        _chair_local_wire(((rail_half, -rail_length), (rail_half, rail_length)), False),
    ])

    inner_outline = (
        (inner_min, -jaw_half),
        (inner_max, -0.68 * jaw_half),
        (inner_max, 0.68 * jaw_half),
        (inner_min, jaw_half),
    )
    outer_outline = (
        (outer_min, -0.68 * jaw_half),
        (outer_max, -jaw_half),
        (outer_max, jaw_half),
        (outer_min, 0.68 * jaw_half),
    )
    detail_wires.extend([
        _chair_local_wire(inner_outline, True),
        _chair_local_wire(((inner_min, 0.0), (inner_max, 0.0)), False),
        _chair_local_wire(outer_outline, True),
        _chair_local_wire(((outer_min, -0.38 * jaw_half), (outer_max, -0.50 * jaw_half)), False),
        _chair_local_wire(((outer_min, 0.38 * jaw_half), (outer_max, 0.50 * jaw_half)), False),
    ])
    detail_wires = [shape for shape in detail_wires if shape is not None]
    key_forward = [shape for shape in _chair_key_symbol_wires(dimensions, 1) if shape is not None]
    key_backward = [shape for shape in _chair_key_symbol_wires(dimensions, -1) if shape is not None]
    symbol = {
        "chair_code": code,
        "chair_label": dimensions["chair_label"],
        "base": base,
        "details": _chair_local_compound(detail_wires),
        "key_forward": _chair_local_compound(key_forward),
        "key_backward": _chair_local_compound(key_backward),
        "base_wire_count": 1,
        "detail_wire_count": len(detail_wires),
        "key_wire_count": len(key_forward),
        "source_basis": list(CHAIR_2D_SOURCE_BASIS),
    }
    _CHAIR_2D_SYMBOL_CACHE[key] = symbol
    return symbol, False


def _chair_place_canonical_shape(shape, instance, z_height):
    if shape is None:
        return None
    placed = shape.copy()
    centre = _chair_xy(instance.get("centre_point") or (0.0, 0.0))
    placed.Placement = App.Placement(
        App.Vector(float(centre[0]), float(centre[1]), float(z_height)),
        App.Rotation(App.Vector(0.0, 0.0, 1.0), float(instance.get("rotation_degrees") or 0.0)),
    )
    return placed


def _create_chair_2d_layout_display(doc, entity_kind, config, analysis, plan, validation, timber_records):
    """Create cached S1/S1J plan symbols; never build a detailed 3D body."""
    started = time.perf_counter()
    kind = str(entity_kind or "").lower()
    entity_id = str(config.get("turnout_id") or config.get("crossover_id") or "")
    set_id = str(config.get("template_set_id") or "")
    _chair_remove_2d_display(doc, kind, entity_id)
    group = doc.addObject("App::DocumentObjectGroup", unique_internal_name(doc, "Chair2DLayout_{}".format(entity_id.replace("-", "_"))))
    group.Label = "{} Templot-guided S1/S1J 2D chair layout".format(entity_id)
    _chair_tag_auxiliary_object(group, kind, entity_id, set_id, CHAIR_2D_LAYOUT_GROUP_ROLE)
    try:
        group.ViewObject.Visibility = True
    except Exception:
        pass

    levels = _chair_display_z_levels(doc, kind, config)
    base_z = float(levels["footprints"]) + 0.080
    detail_z = base_z + 0.012
    support_z = base_z - 0.025
    failure_z = base_z + 0.050
    unresolved_z = failure_z + 0.025

    effective_timbers, adjustments = _chair_apply_physical_model_support(plan, timber_records, analysis.get("settings"))
    effective_by_id = {str(item.get("stable_identity") or ""): item for item in effective_timbers}
    applied_ids = {str(item.get("timber_identity") or "") for item in adjustments if bool(item.get("applied"))}
    support_shapes = []
    for timber_id in sorted(applied_ids):
        timber = effective_by_id.get(timber_id)
        if timber is not None:
            support_shapes.append(_chair_closed_wire(timber.get("outline_polygon") or timber.get("collision_polygon") or [], support_z))

    critical_findings = [
        item for item in list(validation.get("findings") or [])
        if str(item.get("severity") or "") == CHAIR_SEVERITY_CRITICAL
    ]
    failed_chair_ids = {str(item.get("chair_position_identity") or "") for item in critical_findings if item.get("chair_position_identity")}
    failed_timber_ids = {str(item.get("timber_identity") or "") for item in critical_findings if item.get("timber_identity")}
    base_shapes = []
    detail_shapes = []
    failure_shapes = []
    symbol_cache_hits = 0
    symbol_cache_misses = 0
    base_wire_count = 0
    detail_wire_count = 0
    key_symbol_count = 0
    for instance in list(plan.get("instances") or []):
        symbol, reused = _chair_canonical_2d_symbol(instance.get("chair_code"), analysis.get("settings"))
        symbol_cache_hits += int(bool(reused))
        symbol_cache_misses += int(not bool(reused))
        base_shapes.append(_chair_place_canonical_shape(symbol.get("base"), instance, base_z))
        detail_shapes.append(_chair_place_canonical_shape(symbol.get("details"), instance, detail_z))
        base_wire_count += int(symbol.get("base_wire_count") or 0)
        detail_wire_count += int(symbol.get("detail_wire_count") or 0)
        if bool(instance.get("key_direction_resolved")):
            key_shape = symbol.get("key_forward") if int(instance.get("key_direction_sign") or 1) >= 0 else symbol.get("key_backward")
            detail_shapes.append(_chair_place_canonical_shape(key_shape, instance, detail_z + 0.004))
            detail_wire_count += int(symbol.get("key_wire_count") or 0)
            key_symbol_count += 1
        if str(instance.get("chair_position_identity") or "") in failed_chair_ids:
            failure_shapes.append(_chair_closed_wire(instance.get("physical_footprint_polygon") or [], failure_z))
    for timber_id in sorted(failed_timber_ids):
        timber = effective_by_id.get(timber_id)
        if timber is not None:
            failure_shapes.append(_chair_closed_wire(timber.get("outline_polygon") or timber.get("collision_polygon") or [], failure_z))

    positions_by_id = {
        str(item.get("stable_chair_position_identity") or ""): item
        for item in list(analysis.get("positions") or [])
    }
    unresolved_shapes = []
    for item in list(plan.get("analytical_only") or []):
        if bool(item.get("deliberate_omission")):
            continue
        position = positions_by_id.get(str(item.get("chair_position_identity") or ""))
        if position is None:
            continue
        unresolved_shapes.extend(_chair_cross_wires(
            position.get("centre_point") or (0.0, 0.0),
            position.get("local_rail_tangent") or (1.0, 0.0),
            half_size=1.20,
            z_height=unresolved_z,
        ))

    feature_objects = []
    feature_objects.append(_chair_make_2d_feature(
        doc, group, kind, entity_id, set_id, CHAIR_2D_SUPPORT_ROLE,
        "{} bounded model timber support outlines".format(entity_id), support_shapes,
        (0.95, 0.65, 0.10), 2.6, True,
    ))
    feature_objects.append(_chair_make_2d_feature(
        doc, group, kind, entity_id, set_id, CHAIR_2D_FOOTPRINT_ROLE,
        "{} rounded S1/S1J chair bases".format(entity_id), base_shapes,
        (0.67, 0.76, 0.88), 2.0, True,
    ))
    feature_objects.append(_chair_make_2d_feature(
        doc, group, kind, entity_id, set_id, CHAIR_2D_FOOTPRINT_ROLE,
        "{} rail seats, S1 jaws, ribs and resolved keys".format(entity_id), detail_shapes,
        (0.24, 0.40, 0.64), 1.55, True,
    ))
    feature_objects.append(_chair_make_2d_feature(
        doc, group, kind, entity_id, set_id, CHAIR_2D_FAILURE_ROLE,
        "{} exact support-envelope fit failures".format(entity_id), failure_shapes,
        (0.95, 0.15, 0.15), 4.0, True,
    ))
    feature_objects.append(_chair_make_2d_feature(
        doc, group, kind, entity_id, set_id, CHAIR_2D_UNRESOLVED_ROLE,
        "{} unresolved special chair positions".format(entity_id), unresolved_shapes,
        (0.85, 0.20, 0.85), 3.2, True,
    ))
    feature_objects = [obj for obj in feature_objects if obj is not None]
    total_lightweight_subshapes = (
        base_wire_count + detail_wire_count + len(support_shapes)
        + len(failure_shapes) + len(unresolved_shapes)
    )
    build_time_ms = (time.perf_counter() - started) * 1000.0
    properties = [
        ensure_property(group, "App::PropertyInteger", "Chair2DRepresentationRevision", "Chair 2D display", "Lightweight plan-symbol revision"),
        ensure_property(group, "App::PropertyInteger", "Chair2DSymbolCount", "Chair 2D display", "Number of supported S1/S1J plan symbols"),
        ensure_property(group, "App::PropertyInteger", "Chair2DKeySymbolCount", "Chair 2D display", "Number of resolved directional key symbols"),
        ensure_property(group, "App::PropertyInteger", "Chair2DDetailWireCount", "Chair 2D display", "Number of lightweight seat, jaw, rib and key wires"),
        ensure_property(group, "App::PropertyInteger", "Chair2DSubShapeCount", "Chair 2D display", "Total lightweight display sub-shapes"),
        ensure_property(group, "App::PropertyInteger", "Chair2DDocumentObjectCount", "Chair 2D display", "Group plus batched Part feature count"),
        ensure_property(group, "App::PropertyInteger", "Chair2DCanonicalCacheHits", "Chair 2D display", "Canonical plan-symbol cache hits during this build"),
        ensure_property(group, "App::PropertyInteger", "Chair2DCanonicalCacheMisses", "Chair 2D display", "Canonical plan-symbol cache misses during this build"),
        ensure_property(group, "App::PropertyFloat", "Chair2DDisplayBuildTimeMs", "Chair 2D display", "Display construction time before document recompute"),
        ensure_property(group, "App::PropertyString", "Chair2DRepresentation", "Chair 2D display", "Viewer-only chair representation"),
        ensure_property(group, "App::PropertyString", "Chair2DValidationEnvelope", "Chair 2D display", "Envelope used for fit and timber support"),
    ]
    _set_persistent_property_if_changed(group, "Chair2DRepresentationRevision", CHAIR_2D_REPRESENTATION_REVISION)
    _set_persistent_property_if_changed(group, "Chair2DSymbolCount", len(list(plan.get("instances") or [])))
    _set_persistent_property_if_changed(group, "Chair2DKeySymbolCount", key_symbol_count)
    _set_persistent_property_if_changed(group, "Chair2DDetailWireCount", detail_wire_count)
    _set_persistent_property_if_changed(group, "Chair2DSubShapeCount", total_lightweight_subshapes)
    _set_persistent_property_if_changed(group, "Chair2DDocumentObjectCount", 1 + len(feature_objects))
    _set_persistent_property_if_changed(group, "Chair2DCanonicalCacheHits", symbol_cache_hits)
    _set_persistent_property_if_changed(group, "Chair2DCanonicalCacheMisses", symbol_cache_misses)
    _set_persistent_property_if_changed(group, "Chair2DDisplayBuildTimeMs", float(build_time_ms))
    _set_persistent_property_if_changed(
        group,
        "Chair2DRepresentation",
        "Cached rounded S1/S1J base; S1 one-rib inner and two-rib outer jaws; S1/S1J rail seat; Code 75 rail-foot lines; longitudinal key only where direction is resolved",
    )
    _set_persistent_property_if_changed(
        group,
        "Chair2DValidationEnvelope",
        "Separate exact transformed source-dimensional support rectangle; decorative symbol never controls validation or timber widening",
    )
    set_read_only(group, properties)
    _workflow_note_cache("canonical 2D S1/S1J symbol", hits=symbol_cache_hits, misses=symbol_cache_misses)
    _workflow_note_shape_build(
        "batched 2D chair display",
        len(base_shapes) + len(detail_shapes),
        total_lightweight_subshapes,
    )
    parent = production_parent_group_for_set(doc, set_id)
    if parent is not None:
        try:
            parent.addObject(group)
        except Exception:
            pass
    return group


run_macro()
