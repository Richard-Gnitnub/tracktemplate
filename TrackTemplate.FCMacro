"""Small modular-only B16 composition root for Track Template development."""

import importlib
import json
import pathlib
import sys


LAUNCH_SENTINEL = "TRACKTEMPLATE_B16_FOUNDATION="


def _launcher_root():
    source_path = globals().get("__file__")
    if not source_path:
        raise RuntimeError(
            "Track Template cannot locate its package because __file__ is unavailable."
        )
    return pathlib.Path(str(source_path)).resolve().parent


def _load_foundation(repository_root):
    root_text = str(repository_root)
    if not sys.path or sys.path[0] != root_text:
        sys.path.insert(0, root_text)

    package = importlib.import_module("tracktemplate")
    expected_package = (repository_root / "tracktemplate").resolve()
    observed_package = pathlib.Path(str(package.__file__)).resolve().parent
    if observed_package != expected_package:
        raise RuntimeError(
            "Track Template resolved package {!s}, expected {!s}.".format(
                observed_package,
                expected_package,
            )
        )
    api = importlib.import_module("tracktemplate.api")
    bootstrap = importlib.import_module("tracktemplate.bootstrap")
    return api, bootstrap


def _load_modular_transition_workflow(
    repository_root,
    api,
    bootstrap,
):
    compatibility = importlib.import_module("tracktemplate.compatibility")
    export_files = importlib.import_module(
        "tracktemplate.adapters.export.core_layout_set"
    )
    export_document = importlib.import_module(
        "tracktemplate.adapters.freecad.core_export_document"
    )
    chair_preview = importlib.import_module(
        "tracktemplate.adapters.freecad.chair_reference_preview"
    )
    chair_catalogue = importlib.import_module(
        "tracktemplate.adapters.freecad.chair_catalogue_preview"
    )
    catalogue_placement = importlib.import_module(
        "tracktemplate.adapters.freecad.chair_catalogue_placement_preview"
    )
    transition_contract = bootstrap.load_contract(
        repository_root
        / "reference"
        / "contracts"
        / "phase1-transition-pilot.json"
    )
    session = compatibility.load_modular_transition_workflow_session(
        repository_root,
        api,
        transition_contract,
        export_files_factory=export_files.CoreLayoutExportSetFiles,
        export_dispatcher_factory=export_document.CoreExportDocument,
        selected_export_files_factory=export_files.CoreLayoutExportSetFiles,
        selected_export_atomic=True,
        runtime_record=bootstrap.runtime_record,
        s1_reference_preview_factory=chair_preview.create_s1_reference_preview,
        s1j_reference_preview_factory=(
            chair_preview.create_s1j_reference_preview
        ),
        s1_s1j_reference_preview_factory=(
            chair_preview.create_s1_s1j_reference_preview
        ),
        l1_reference_preview_factory=chair_preview.create_l1_reference_preview,
        private_catalogue_preview_factory=(
            chair_catalogue.create_private_catalogue_preview
        ),
        private_catalogue_p_preview_factory=(
            catalogue_placement.create_private_catalogue_p_preview
        ),
        private_catalogue_s1j_preview_factory=(
            catalogue_placement.create_private_catalogue_s1j_preview
        ),
        private_catalogue_l1_preview_factory=(
            catalogue_placement.create_private_catalogue_l1_preview
        ),
        private_catalogue_cc_preview_factory=(
            catalogue_placement.create_private_catalogue_cc_preview
        ),
        private_catalogue_turnout_check_end_preview_factory=(
            catalogue_placement.create_private_catalogue_turnout_check_end_preview
        ),
        private_catalogue_turnout_block_preview_factory=(
            catalogue_placement.create_private_catalogue_turnout_block_preview
        ),
        private_catalogue_turnout_zy_preview_factory=(
            catalogue_placement.create_private_catalogue_turnout_zy_preview
        ),
        private_catalogue_turnout_crossing_preview_factory=(
            catalogue_placement.create_private_catalogue_turnout_crossing_preview
        ),
        private_catalogue_turnout_single_rail_preview_factory=(
            catalogue_placement.create_private_catalogue_turnout_single_rail_preview
        ),
        private_catalogue_crossover_preview_factory=(
            catalogue_placement.create_private_catalogue_crossover_preview
        ),
    )
    return session, session.routing_record()



def _launch_workflow_with_rea_editor(session, qualification):
    """Compose the source editor during one inherited modal launch.

    This temporary bridge belongs to the B16 composition root. Remove it
    when the modular manager owns the qualified operator workflow.
    """
    module = session.module
    original = module.dialog_exec
    if getattr(original, "_tracktemplate_rea_editor_launch", False):
        raise RuntimeError("The REA operator launch is already active.")
    curve_class = module.CurveInputDialog
    manager_class = module.TurnoutManagerDialog
    document_adapter = importlib.import_module(
        "tracktemplate.adapters.freecad.rea_turnout_state"
    )
    presentation = importlib.import_module(
        "tracktemplate.presentation.rea_trackwork"
    )
    editor = importlib.import_module("tracktemplate.ui.rea_trackwork_editor")
    from uuid import uuid4

    store = document_adapter.FreeCADReaTrackworkStore(
        qualification,
        view_factory=presentation.attach_rea_trackwork_view,
        view_reader=presentation.read_rea_trackwork_view,
    )

    def scene_factory(entity_id, lines):
        return presentation.ReaTrackworkScene(entity_id, tuple(
            presentation.ReaTrackworkLine(*line) for line in lines
        ))

    workflow = session.rea_trackwork_workflow(store, scene_factory)

    def read_hosts(document):
        return tuple(editor.ReaHostChoice(
            obj, str(obj.Name),
            module.object_string_property(obj, "TemplateSetID", ""),
            module.turnout_host_label(obj),
        ) for obj in module.turnout_host_objects(document))

    def dialog_exec(dialog):
        if type(dialog) is curve_class:
            dialog.turnout_manager_button.setText(
                "Turnouts and Crossovers (C10 / REA B/C)..."
            )
            dialog.turnout_manager_button.setToolTip(
                "Open the existing C10 tools or the source REA B/C "
                "research editor. Production qualification remains pending."
            )
        elif type(dialog) is manager_class:
            if getattr(dialog, "_tracktemplate_rea_panel", None) is None:
                controller = editor.ReaTrackworkEditorController(
                    dialog.doc, workflow,
                    read_records=document_adapter.read_rea_trackwork_objects,
                    read_hosts=read_hosts,
                    active_document=lambda: module.App.ActiveDocument,
                    new_entity_id=lambda: "REA-" + uuid4().hex,
                )
                editor.attach_rea_trackwork_panel(
                    dialog, controller, module.QtWidgets,
                    minimum_radius_mm=module.CROSSOVER_DEFAULT_MINIMUM_RADIUS,
                )
        return original(dialog)

    dialog_exec._tracktemplate_rea_editor_launch = True
    module.dialog_exec = dialog_exec
    try:
        return session.launch_workflow()
    finally:
        binding_changed = module.dialog_exec is not dialog_exec
        module.dialog_exec = original
        if binding_changed:
            raise RuntimeError("The REA dialog execution binding changed.")


def run_macro(launch_workflow=False):
    """Qualify the modular foundation and optionally load its inherited GUI."""
    repository_root = _launcher_root()
    api, bootstrap = _load_foundation(repository_root)
    contract_path = (
        repository_root
        / "reference"
        / "contracts"
        / "phase1-compatibility.json"
    )
    try:
        qualification = bootstrap.require_qualified_runtime(contract_path)
    except bootstrap.RuntimeQualificationError as error:
        blocked = {
            "schema_version": 1,
            "development_checkpoint": api.DEVELOPMENT_CHECKPOINT,
            "status": "blocked-before-composition",
            "compatibility_evaluation": error.evaluation,
            "document_mutation": False,
        }
        print(
            LAUNCH_SENTINEL
            + json.dumps(blocked, sort_keys=True, separators=(",", ":")),
            flush=True,
        )
        raise RuntimeError(str(error)) from error

    try:
        if not isinstance(launch_workflow, bool):
            raise ValueError("launch_workflow must be a boolean value.")
        session = None
        routing = None
        if launch_workflow:
            session, routing = _load_modular_transition_workflow(
                repository_root,
                api,
                bootstrap,
            )
    except (OSError, RuntimeError, ValueError) as error:
        blocked = {
            "schema_version": 1,
            "development_checkpoint": api.DEVELOPMENT_CHECKPOINT,
            "status": "blocked-before-workflow-composition",
            "diagnostic": str(error),
            "document_mutation": False,
        }
        print(
            LAUNCH_SENTINEL
            + json.dumps(blocked, sort_keys=True, separators=(",", ":")),
            flush=True,
        )
        raise RuntimeError(str(error)) from error

    if launch_workflow:
        _launch_workflow_with_rea_editor(session, qualification)

    result = {
        "schema_version": 1,
        "development_checkpoint": api.DEVELOPMENT_CHECKPOINT,
        "status": (
            "transition-workflow-launched"
            if launch_workflow
            else "modular-foundation-ready"
        ),
        "matched_profile_id": qualification["compatibility_evaluation"][
            "matched_profile_id"
        ],
        "public_api": list(api.__all__),
        "calculation_routing": "modular",
        "legacy_comparison_route_available": False,
        "workflow_host_loaded": bool(routing),
        "workflow_launched": bool(launch_workflow),
        "document_mutation": False if not launch_workflow else None,
    }
    if routing is not None:
        result.update(
            {
                "routed_function_names": routing["function_names"],
                "routed_caller_names": routing["caller_names"],
                "workflow_source_sha256": routing[
                    "workflow_source_sha256"
                ],
                "workflow_version": routing["workflow_version"],
                "mixed_calculation_routing": routing["mixed_route"],
                "core_layout_export_routing": (
                    session.core_layout_export_routing_record()
                ),
            }
        )
    print(
        LAUNCH_SENTINEL
        + json.dumps(result, sort_keys=True, separators=(",", ":")),
        flush=True,
    )
    return result


def activate_transition_editing(document=None):
    """Explicitly compose one reversible B16 Coin editing lifecycle."""
    repository_root = _launcher_root()
    api, bootstrap = _load_foundation(repository_root)
    qualification = bootstrap.require_qualified_runtime(
        repository_root
        / "reference"
        / "contracts"
        / "phase1-compatibility.json"
    )

    app = importlib.import_module("FreeCAD")
    gui = importlib.import_module("FreeCADGui")
    coin = importlib.import_module("pivy.coin")
    qt_widgets = importlib.import_module("PySide6.QtWidgets")
    adapter = importlib.import_module(
        "tracktemplate.adapters.freecad.transition_state"
    )
    attachment_module = importlib.import_module(
        "tracktemplate.presentation.transition_coin_attachment"
    )
    renderer = importlib.import_module(
        "tracktemplate.presentation.transition_coin"
    )
    editor = importlib.import_module(
        "tracktemplate.ui.transition_parameter_editor"
    )
    lifecycle_module = importlib.import_module(
        "tracktemplate.ui.transition_editing_lifecycle"
    )

    if document is None:
        document = app.ActiveDocument
    if document is None:
        raise RuntimeError(
            "Open a document with canonical Entry/Exit transitions before "
            "activating transition editing."
        )

    records = adapter.read_transition_objects(document)
    if not records:
        raise RuntimeError(
            "The active document contains no canonical transitions to attach."
        )
    unsupported = tuple(
        state.intent.transition_id
        for _obj, state in records
        if state.intent.end_name not in ("Entry", "Exit")
    )
    if unsupported:
        raise RuntimeError(
            "The bounded B16 lifecycle supports Entry/Exit transitions only: "
            + ", ".join(unsupported)
        )

    store = adapter.FreeCADTransitionStore(qualification)

    def attachment_factory():
        return attachment_module.TransitionCoinDocumentAttachmentFixture(
            document,
            record_loader=adapter.read_transition_objects,
            state_reader=adapter.read_transition_object,
            source_property_name=adapter.FREECAD_STATE_JSON_PROPERTY,
            specification=api.TransitionPreviewSpecification(
                segment_count=32
            ),
            style=renderer.TransitionCoinStyle(
                line_color_rgb=(0.9, 0.05, 0.02),
                line_width=6.0,
            ),
            coin_module=coin,
        )

    def selection_reader():
        try:
            selected = tuple(
                gui.Selection.getSelectionEx(str(document.Name))
            )
        except Exception:
            return None
        if len(selected) != 1:
            return None
        selected_record = selected[0]
        selected_object = selected_record.Object
        subelements = tuple(selected_record.SubElementNames)
        if len(subelements) != 1:
            return None
        try:
            proxy = selected_object.ViewObject.Proxy
            mapping = proxy.selection_for_element(subelements[0])
            state = adapter.read_transition_object(selected_object)
        except (AttributeError, TypeError, ValueError, RuntimeError):
            return None
        if mapping.domain_id != state.intent.transition_id:
            return None
        return editor.SelectedTransition(
            state,
            adapter.FreeCADTransitionEditPort(
                store,
                document,
                selected_object,
                proxy,
            ),
        )

    def dialog_factory(controller):
        return editor.TransitionParameterEditorDialog(
            controller,
            qt_widgets,
            parent=gui.getMainWindow(),
        )

    observer_holder = []

    def clear_document_selection():
        gui.Selection.clearSelection(str(document.Name))

    def remove_document_observer():
        if observer_holder:
            observer = observer_holder[0]
            app.removeDocumentObserver(observer)
            observer_holder.pop()

    class _SaveDeactivationObserver:
        def _deactivate_target(self, observed_document):
            if str(observed_document.Name) != str(document.Name):
                return
            if editing_lifecycle.state in ("active", "cleanup-failed"):
                editing_lifecycle.deactivate()

        def slotStartSaveDocument(self, observed_document, filename):
            self._deactivate_target(observed_document)

    editing_lifecycle = lifecycle_module.TransitionEditingLifecycle(
        attachment_factory=attachment_factory,
        selection_reader=selection_reader,
        selection_clearer=clear_document_selection,
        dialog_factory=dialog_factory,
        cleanup_callback=remove_document_observer,
    )
    editing_lifecycle.activate()
    observer = _SaveDeactivationObserver()
    observer_holder.append(observer)
    try:
        app.addDocumentObserver(observer)
    except Exception as registration_error:
        try:
            editing_lifecycle.deactivate()
        except lifecycle_module.TransitionEditingLifecycleError as error:
            failure = lifecycle_module.TransitionEditingLifecycleError(
                "transition-editing-observer-registration-failed",
                "{}; cleanup also failed: {}".format(
                    registration_error,
                    error,
                ),
            )
            failure.recovery_lifecycle = editing_lifecycle
            raise failure from registration_error
        raise lifecycle_module.TransitionEditingLifecycleError(
            "transition-editing-observer-registration-failed",
            str(registration_error),
        ) from registration_error
    return editing_lifecycle


FOUNDATION_RESULT = run_macro()
